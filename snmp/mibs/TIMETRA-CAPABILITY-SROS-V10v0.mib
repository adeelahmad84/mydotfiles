-- Extracted from version 1.100 of TIMETRA-CAPABILITY-SROS-V8v0.mib

--  A tmnxSROS*CapsV10v0 AGENT-CAPABILITIES statement contains object groups
--  and VARIATIONS that are implemented on all SROS platforms.  This is a
--  platform common capability statement.
--
--  The capabilities of SROS product variants are described using
--  tmnx%*CapsV10v0 AGENT-CAPABILITY statements, where % represents a
--  platform name (e.g. 7450).
--
--  The AGENT-CAPABILITY statements must be interpreted using the following
--  hierarchy:
--     tmnxSROS*CapsV10v0                 - All SROS products
--        tmnx7950*CapsV10v0          - 7950
--        tmnx7750*CapsV10v0          - 7750 (not 7750 SR-c4 or 7750 SR-c12)
--        tmnx7450*CapsV10v0          - 7450
--        tmnxSpr*CapsV10v0           - 7710 and 7750 SR-c4 and 7750 SR-c12
--           tmnx7710*CapsV10v0       - 7710
--           tmnx7750c*CapsV10v0      - 7750 SR-c4 and 7750 SR-c12
--              tmnx7750c4*CapsV10v0  - 7750 SR-c4
--              tmnx7750c12*CapsV10v0 - 7750 SR-c12
--
--  For example, the set of Chassis objects supported by a 7750 SR-c12
--  is the sum of the objects INCLUDEd in the tmnx7750c12ChassisCapsV10v0,
--  tmnx7750cChassisCapsV10v0, tmnxSprChassisCapsV10v0, and
--  tmnxSROSChassisCapsV10v0 AGENT-CAPABILITY statements.  If there are two or
--  more VARIATION statements for a particular object in the four
--  AGENT-CAPABILITY statements, the most deeply nested VARIATION must be used.
--
--      When a platform specific AGENT-CAPABILILTIES INCLUDES list contains a
--  EXCLUDE group statement, it indicates that the objects in that group are
--  not supported on that specific platform.  E.g.: tmnxSROSChassisCapsV10v0
--      EXCLUDEs tmnxChassisMixedModeIomV8v0Group because mixed mode is not
--  supported on the 7750.
--
--  When a platform specific AGENT-CAPABILITIES statement consists of a
--  commented out SUPPORTS statement with an empty INCLUDES list and no
--  VARIATION statements, it indicates that the feature is not implemented
--  on that specific platform.  An empty INCLUDES list contains no group
--  names and no EXCLUDE statements.  E.g.: tmnx7450IPsecCapsV10v0

TIMETRA-CAPABILITY-SROS-V10v0 DEFINITIONS ::= BEGIN

IMPORTS
    MODULE-IDENTITY, OBJECT-IDENTITY,
    enterprises, Integer32, Unsigned32      FROM SNMPv2-SMI
    RowStatus, TimeInterval                 FROM SNMPv2-TC

    AGENT-CAPABILITIES,
    MODULE-COMPLIANCE                       FROM SNMPv2-CONF

    DisplayString,
    TruthValue                              FROM SNMPv2-TC

    SnmpAdminString                         FROM SNMP-FRAMEWORK-MIB

    InterfaceIndex                          FROM IF-MIB

    DefaultMetric                           FROM ISIS-MIB

    Dot1agCfmMhfCreation,
    Dot1agCfmIdPermission                   FROM IEEE8021-CFM-MIB

    InetAddress, InetAddressPrefixLength,
    InetAddressType                         FROM INET-ADDRESS-MIB

    OwnerString                             FROM RMON-MIB

    TmnxBsxOperator,
    TmnxBsxActionStatus,
    TmnxBsxAaSubscriberType                 FROM TIMETRA-BSX-NG-MIB

    TmnxSETSRefSource, TmnxSSMQualityLevel,
    TmnxChassisMode, TmnxBITSIfType         FROM TIMETRA-CHASSIS-MIB

    TEntryId                                FROM TIMETRA-FILTER-MIB

    TmnxOtuAlarms                           FROM TIMETRA-OTU-MIB

    TmnxL2tpTunnelSessionLimit              FROM TIMETRA-L2TP-MIB

    timetraSROSCapModule,
    tmnxSROSV10v0                           FROM TIMETRA-GLOBAL-MIB

    TmnxPtpPriority                         FROM TIMETRA-PTP-MIB

    TmnxEnabledDisabled,
    TmnxServId, TNamedItemOrEmpty,
    TmnxSubRadServAlgorithm                 FROM TIMETRA-TC-MIB;

--
-- Capability statements for SROS release 10.0
--
--
 timetraSROSV10v0CapModule   MODULE-IDENTITY
        LAST-UPDATED "201111010000Z"
        ORGANIZATION "Alcatel-Lucent"
        CONTACT-INFO
            "Alcatel-Lucent SROS Support
             Web: http://support.alcatel-lucent.com "
        DESCRIPTION
        "This document is the SNMP MIB module for agent capability clauses
        defined under the Alcatel-Lucent timetra object identifier branch for
        the Alcatel-Lucent SROS release R10.0.  These capability clauses specify
        details about the SNMP agent implementation for this release.

        Copyright 2005-2012 Alcatel-Lucent. All rights reserved.
        Reproduction of this document is authorized on the condition
        that the foregoing copyright notice is included.

        This SNMP MIB module (Specification) embodies Alcatel-Lucent's
        proprietary intellectual property.  Alcatel-Lucent retains
        all title and ownership in the Specification, including any
        revisions.

        Alcatel-Lucent grants all interested parties a non-exclusive
        license to use and distribute an unmodified copy of this
        Specification in connection with management of Alcatel-Lucent
        products, and without fee, provided this copyright notice and
        license appear on all copies.

        This Specification is supplied as is, and Alcatel-Lucent
        makes no warranty, either express or implied, as to the use,
        operation, condition, or performance of the Specification."
--
--  Revision History
--
        REVISION        "1102010000Z"
        DESCRIPTION     "Rev 0.0                1 Feb 2011 00:00
                This is the initial version of the TIMETRA-CAPABILITY-SROS-V9v0
                mib for Alcatel-Lucent SROS Release 9.0."
        ::= { timetraSROSCapModule 8 }

--
--  sub-tree for ALcatel-Lucent SROS SNMP agent capability objects
--
--  tmnxSROSCapability      OBJECT IDENTIFIER ::= { tmnxProductCapability 1 }
--    tmnxSROSV10v0              OBJECT IDENTIFIER ::= { tmnxSROSCapability 7 }

--    tmnxCapsTestObjectV10v0         OBJECT IDENTIFIER ::= { tmnxSROSV10v0 1 }
--    tmnxSROSApsCapsV10v0            OBJECT IDENTIFIER ::= { tmnxSROSV10v0 2 }
--    tmnxSROSAtmCapsV10v0            OBJECT IDENTIFIER ::= { tmnxSROSV10v0 3 }
--    tmnxSROSBgpCapsV10v0            OBJECT IDENTIFIER ::= { tmnxSROSV10v0 4 }
--    tmnxSROSCflowdCapsV10v0         OBJECT IDENTIFIER ::= { tmnxSROSV10v0 5 }
--    tmnxSROSChassisCapsV10v0        OBJECT IDENTIFIER ::= { tmnxSROSV10v0 6 }
--    tmnxSROSClearCapsV10v0          OBJECT IDENTIFIER ::= { tmnxSROSV10v0 7 }
--    tmnxSROSDS0CapsV10v0            OBJECT IDENTIFIER ::= { tmnxSROSV10v0 9 }
--    tmnxSROSDS1CapsV10v0            OBJECT IDENTIFIER ::= { tmnxSROSV10v0 10 }
--    tmnxSROSDS3CapsV10v0            OBJECT IDENTIFIER ::= { tmnxSROSV10v0 11 }
--    tmnxSROSEtherLikeCapsV10v0      OBJECT IDENTIFIER ::= { tmnxSROSV10v0 12 }
--    tmnxSROSEtherWisCapsV10v0       OBJECT IDENTIFIER ::= { tmnxSROSV10v0 13 }
--    tmnxSROSFilterCapsV10v0         OBJECT IDENTIFIER ::= { tmnxSROSV10v0 14 }
--    tmnxSROSFrameRelayDTECapsV10v0  OBJECT IDENTIFIER ::= { tmnxSROSV10v0 15 }
--    tmnxSROSIEEE8021PaeCapsV10v0    OBJECT IDENTIFIER ::= { tmnxSROSV10v0 16 }
--    tmnxSROSIfCapsV10v0             OBJECT IDENTIFIER ::= { tmnxSROSV10v0 17 }
--    tmnxSROSIgmpCapsV10v0           OBJECT IDENTIFIER ::= { tmnxSROSV10v0 18 }
--    tmnxSROSIgmpSnoopingCapsV10v0   OBJECT IDENTIFIER ::= { tmnxSROSV10v0 19 }
--    tmnxSROSIPCapsV10v0             OBJECT IDENTIFIER ::= { tmnxSROSV10v0 20 }
--    tmnxSROSIsisCapsV10v0           OBJECT IDENTIFIER ::= { tmnxSROSV10v0 21 }
--    tmnxSROSLAGCapsV10v0            OBJECT IDENTIFIER ::= { tmnxSROSV10v0 22 }
--    tmnxSROSLdpCapsV10v0            OBJECT IDENTIFIER ::= { tmnxSROSV10v0 23 }
--    tmnxSROSLogCapsV10v0            OBJECT IDENTIFIER ::= { tmnxSROSV10v0 24 }
--    tmnxSROSMirrorCapsV10v0         OBJECT IDENTIFIER ::= { tmnxSROSV10v0 25 }
--    tmnxSROSMplsCapsV10v0           OBJECT IDENTIFIER ::= { tmnxSROSV10v0 26 }
--    tmnxSROSOamTestCapsV10v0        OBJECT IDENTIFIER ::= { tmnxSROSV10v0 27 }
--    tmnxSROSOspfCapsV10v0           OBJECT IDENTIFIER ::= { tmnxSROSV10v0 28 }
--    tmnxSROSPimCapsV10v0            OBJECT IDENTIFIER ::= { tmnxSROSV10v0 29 }
--    tmnxSROSPortCapsV10v0           OBJECT IDENTIFIER ::= { tmnxSROSV10v0 30 }
--    tmnxSROSPppCapsV10v0            OBJECT IDENTIFIER ::= { tmnxSROSV10v0 31 }
--    tmnxSROSQosCapsV10v0            OBJECT IDENTIFIER ::= { tmnxSROSV10v0 32 }
--    tmnxSROSRip2CapsV10v0           OBJECT IDENTIFIER ::= { tmnxSROSV10v0 33 }
--    tmnxSROSRmonCapsV10v0           OBJECT IDENTIFIER ::= { tmnxSROSV10v0 34 }
--    tmnxSROSRoutePolicyCapsV10v0    OBJECT IDENTIFIER ::= { tmnxSROSV10v0 35 }
--    tmnxSROSRsvpCapsV10v0           OBJECT IDENTIFIER ::= { tmnxSROSV10v0 36 }
--    tmnxSROSSecurityCapsV10v0       OBJECT IDENTIFIER ::= { tmnxSROSV10v0 37 }
--    tmnxSROSServicesCapsV10v0       OBJECT IDENTIFIER ::= { tmnxSROSV10v0 38 }
--    tmnxSROSSnmpCapsV10v0           OBJECT IDENTIFIER ::= { tmnxSROSV10v0 39 }
--    tmnxSROSSonetCapsV10v0          OBJECT IDENTIFIER ::= { tmnxSROSV10v0 40 }
--    tmnxSROSSystemCapsV10v0         OBJECT IDENTIFIER ::= { tmnxSROSV10v0 41 }
--    tmnxSROSVrrpCapsV10v0           OBJECT IDENTIFIER ::= { tmnxSROSV10v0 42 }
--    tmnxSROSVRtrCapsV10v0           OBJECT IDENTIFIER ::= { tmnxSROSV10v0 43 }
--    tmnxSROSNtpCapsV10v0            OBJECT IDENTIFIER ::= { tmnxSROSV10v0 44 }
--    tmnxSROSSubscrMgmtCapsV10v0     OBJECT IDENTIFIER ::= { tmnxSROSV10v0 45 }
--    tmnxSROSDismanCronCapsV10v0     OBJECT IDENTIFIER ::= { tmnxSROSV10v0 46 }
--    tmnxSROSMCastCACCapsV10v0       OBJECT IDENTIFIER ::= { tmnxSROSV10v0 50 }
--    tmnxSROSMsdpCapsV10v0           OBJECT IDENTIFIER ::= { tmnxSROSV10v0 51 }
--    tmnxSROSDot3OamCapsV10v0        OBJECT IDENTIFIER ::= { tmnxSROSV10v0 52 }
--    tmnxSROSMldSnoopingCapsV10v0    OBJECT IDENTIFIER ::= { tmnxSROSV10v0 53 }
--    tmnxSROSIPsecCapsV10v0          OBJECT IDENTIFIER ::= { tmnxSROSV10v0 54 }
--    tmnxSROSDhcpServerCapsV10v0     OBJECT IDENTIFIER ::= { tmnxSROSV10v0 55 }
--    tmnxSROSPPPoECapsV10v0          OBJECT IDENTIFIER ::= { tmnxSROSV10v0 56 }
--    tmnxSROSMldCapsV10v0            OBJECT IDENTIFIER ::= { tmnxSROSV10v0 57 }
--    tmnxSROSDot1agCfmCapsV10v0      OBJECT IDENTIFIER ::= { tmnxSROSV10v0 58 }
--    tmnxSROSMcastPathMgmtCapsV10v0  OBJECT IDENTIFIER ::= { tmnxSROSV10v0 59 }
--    tmnxSROSLocalUserDbCapsV10v0    OBJECT IDENTIFIER ::= { tmnxSROSV10v0 60 }
--    tmnxSROSPimSnoopingCapsV10v0    OBJECT IDENTIFIER ::= { tmnxSROSV10v0 61 }
--    tmnxSROSSapCapsV10v0            OBJECT IDENTIFIER ::= { tmnxSROSV10v0 62 }
--    tmnxSROSSdpCapsV10v0            OBJECT IDENTIFIER ::= { tmnxSROSV10v0 63 }
--    tmnxSROSBsxCapsV10v0            OBJECT IDENTIFIER ::= { tmnxSROSV10v0 64 }
--    tmnxSROSLLDPCapsV10v0           OBJECT IDENTIFIER ::= { tmnxSROSV10v0 65 }
--    tmnxSROSL2tpCapsV10v0           OBJECT IDENTIFIER ::= { tmnxSROSV10v0 66 }
--    tmnxSROSOTUCapsV10v0            OBJECT IDENTIFIER ::= { tmnxSROSV10v0 67 }
--    tmnxSROSEthTunnelV9v0           OBJECT IDENTIFIER ::= { tmnxSROSV10v0 68 }
--    tmnxSROSNatCapsV10v0            OBJECT IDENTIFIER ::= { tmnxSROSV10v0 69 }
--    tmnxSROSVideoCapsV10v0          OBJECT IDENTIFIER ::= { tmnxSROSV10v0 70 }
--    tmnxSROSElmiCapsV10v0           OBJECT IDENTIFIER ::= { tmnxSROSV10v0 71 }
--    tmnxSROSIPsecStaticSACapsV10v0  OBJECT IDENTIFIER ::= { tmnxSROSV10v0 72 }
--    tmnxSROSIFGrpHandlerCapsV10v0   OBJECT IDENTIFIER ::= { tmnxSROSV10v0 73 }
--    tmnxSROSEthRingCapsV10v0        OBJECT IDENTIFIER ::= { tmnxSROSV10v0 74 }
--    tmnxSROSDiameterCapsV10v0       OBJECT IDENTIFIER ::= { tmnxSROSV10v0 75 }
--    tmnxSROSConnProfCapsV10v0       OBJECT IDENTIFIER ::= { tmnxSROSV10v0 76 }
--    tmnxSROSTwampCapsV10v0          OBJECT IDENTIFIER ::= { tmnxSROSV10v0 77 }
--    tmnxSROSIpfixCapsV10v0          OBJECT IDENTIFIER ::= { tmnxSROSV10v0 78 }
--    tmnxSROSRadProxCapsV10v0        OBJECT IDENTIFIER ::= { tmnxSROSV10v0 79 }
--    tmnxSROSWppCapsV10v0            OBJECT IDENTIFIER ::= { tmnxSROSV10v0 80 }
--    tmnxSROSPTPCapsV10v0            OBJECT IDENTIFIER ::= { tmnxSROSV10v0 81 }
--    tmnxSROSWlanGwCapsV10v0         OBJECT IDENTIFIER ::= { tmnxSROSV10v0 82 }
--    tmnxSROSDaCapsV10v0             OBJECT IDENTIFIER ::= { tmnxSROSV10v0 83 }
tmnxCapsTestObjectV10v0  OBJECT IDENTIFIER ::= { tmnxSROSV10v0 1 }


--
--  APS CAPABILITIES
--
tmnxSROSApsCapsV10v0    AGENT-CAPABILITIES
    PRODUCT-RELEASE "Alcatel-Lucent SROS"
    STATUS          current
    DESCRIPTION     "Implementation of APS capabilities for
                     Alcatel-Lucent SROS release R10.0."

    SUPPORTS        APS-MIB
        INCLUDES    {
            apsConfigGeneral,
            apsConfigWtr,
            apsCommandOnePlusOne,
            apsStatusGeneral,
            apsChanGeneral,
            apsTotalsGroup,
            apsMapGroup,
            apsEventGroup
-- EXCLUDE  apsCommandOneToN,
-- EXCLUDE  apsChanOneToN,
        }

        VARIATION   apsNotificationEnable
            ACCESS  read-only
            DESCRIPTION
                    "apsNotificationEnable is implemented as read-only.

                    The generation of APS notifications is controlled by
                    tmnxEventTable in the TIMETRA-LOG-MIB."

        VARIATION   apsConfigEntry
            DESCRIPTION
                    "A Row creation/deletion in the apsConfigTable
                    creates/deletes an entry in the
                    TIMETRA-PORT-MIB::tmnxPortTable for a port of
                    type APS Group."

        VARIATION   apsConfigName
            DESCRIPTION
                    "The format of the apsConfigName string must be
                    'aps-<group-id>' where <group-id> is a numerical value
                    from 1 to the maximum number of supported APS groups for
                    the chassis type.  An attempt to use an apsConfigName
                    index that does not meet this format specification
                    results in a 'noCreation' or 'noSuchInstance' error."

        VARIATION   apsConfigRowStatus
            SYNTAX  INTEGER {
                        active      (1),
                        createAndGo (4),
                        destroy     (6)
                     }
            DESCRIPTION
                    "apsConfigRowStatus supports only the values 'active (1)',
                    'createAndGo (4)' and 'destroy (6)'."

        VARIATION   apsConfigMode
            SYNTAX  INTEGER {
                        onePlusOne(1),
                        -- oneToN(2),
                        -- onePlusOneCompatible(3),
                        onePlusOneOptimized(4)
                    }
            DESCRIPTION
                    "Only 'onePlusOne(1)' and 'onePlusOneOptimized(4)' are
                    supported."

        VARIATION   apsConfigDirection
            SYNTAX  INTEGER {
                        unidirectional  (1),
                        bidirectional   (2)
                    }
            DEFVAL  { bidirectional }
            DESCRIPTION
                    "The default value is bidirectional instead of
                    unidirectional."

        VARIATION   apsConfigExtraTraffic
            ACCESS  read-only
            DESCRIPTION
                    "apsConfigExtraTraffic cannot be modified and is
                    implemented as read-only."

        VARIATION   apsConfigSdBerThreshold
            ACCESS  not-implemented
            DESCRIPTION
                    "apsConfigSdBerThreshold is not implemented.

                    SD BER threshold of an APS physical port
                    (working/protection channel) can be set using the
                    tmnxSonetBerSdThreshold object of the TIMETRA-PORT-MIB."

        VARIATION   apsConfigSfBerThreshold
            ACCESS  not-implemented
            DESCRIPTION
                    "apsConfigSfBerThreshold is not implemented.

                    SF BER threshold of an APS physical port
                    (working/protection channel) can be set using the
                    tmnxSonetBerSfThreshold object of the TIMETRA-PORT-MIB."

        VARIATION   apsConfigWaitToRestore
            SYNTAX  Integer32 (0..3600)
            DESCRIPTION
                    "The maximum value of apsConfigWaitToRestore has been
                    increased from 720 to 3600 seconds.  This is consistent
                    with other Alcatel-Lucent wait-to-restore timer objects.

                    The value of apsConfigWaitToRestore will be set to the
                    default value 300 if the value of apsConfigMode is changed
                    by an operator."

        VARIATION   apsStatusK1K2Rcv
            DESCRIPTION
                    "For SDH framing mode, as defined in G.841, bits 6-8
                    of K2 would be 0 for either (unidirectional or
                    bidirectional) switching mode."

        VARIATION   apsStatusK1K2Trans
            DESCRIPTION
                    "For SDH framing mode, as defined in G.841, bits 6-8
                    of K2 would be set to 0 for either (unidirectional or
                    bidirectional) switching mode."

        VARIATION   apsCommandSwitch
            DESCRIPTION
                    "For an Multi-Chassis (MC) APS group
                    (i.e. tApsMcNeighborAddr object of the TIMETRA-APS-MIB
                    is non-zero), apsCommandSwitch object can be set/read
                    only from the protection router, i.e. MC router having
                    the protection circuit (apsChanConfigNumber is 0).
                    The switch commands can be set only if the MC-APS control
                    link (i.e. tApsMcApsCtlLinkState object of TIMETRA-APS-MIB)
                    is UP.  However a switch command can be cleared,
                    i.e. the value 'clear (1)' can be set, irrespective of
                    the MC-APS Control link state.

                    For APS Annex B, the following switch commands must be
                    interpreted as switch requests against the primary or
                    secondary channels instead of the working or protection
                    channels respectively:

                      'forcedSwitchWorkToProtect(4)'
                      'forcedSwitchProtectToWork(5)'
                      'manualSwitchWorkToProtect(6)'
                      'manualSwitchProtectToWork(7)'

                    For example, value 'forcedSwitchWorkToProtect(4)' specifies
                    a forced switch of the primary channel to the secondary
                    channel."

        VARIATION   apsChanConfigIfIndex
            DESCRIPTION
                    "apsChanConfigIfIndex object cannot be set with the
                    interface index of a SONET LTE that is part of a
                    channelized MDA that is not part of the ASAP channelized
                    MDA family (indicated by tmnxMdaTypeName object of the
                    TIMETRA-CHASSIS-MIB). For ASAP MDA family refer to
                    customer documentation for any further restrictions.

                    For an Multi-Chassis (MC) APS group
                    (i.e. tApsMcNeighborAddr object of the TIMETRA-APS-MIB
                    is non-zero), apsChanConfigIfIndex object can be set
                    only with the interface index of a SONET LTE that is
                    part of the ATM MDA family (indicated by tmnxMdaTypeName
                    object of the TIMETRA-CHASSIS-MIB)."

        VARIATION   apsChanConfigNumber
            DESCRIPTION
                    "For an Multi-Chassis (MC) APS group
                    (i.e. tApsMcNeighborAddr object of the TIMETRA-APS-MIB
                    is non-zero), an APS Group (indicated by
                    apsChanConfigGroupName object) can have only one channel,
                    i.e. apsChanConfigNumber can be set to either 0
                    (protection-circuit) or 1 (working-circuit) in an
                    APS Group."

        VARIATION   apsChanConfigRowStatus
            DESCRIPTION
                    "For an Multi-Chassis (MC) APS group
                    (i.e. tApsMcNeighborAddr object of the TIMETRA-APS-MIB
                    is non-zero), creation/deletion of a protection circuit
                    entry (i.e. apsChanConfigNumber 0) creates/deletes an
                    apsChanConfigEntry for the working circuit (with 1 as
                    apsChanConfigNumber and an invalid interface index
                    value as apsChanConfigIfIndex), and an apsChanConfigEntry
                    for the protection circuit (with the provided values of
                    apsChanConfigNumber and apsChanConfigIfIndex)."

        VARIATION   apsEventSwitchover
            DESCRIPTION
                    "For an Multi-Chassis (MC) APS group
                    (i.e. tApsMcNeighborAddr object of the TIMETRA-APS-MIB
                    is non-zero), apsEventSwitchover notification sent by
                    the protection router, i.e. MC router having
                    the protection circuit (apsChanConfigNumber is 0) should
                    be used to track an APS switchover event."

        VARIATION   apsStatusSwitchedChannel
            DESCRIPTION
                    "For APS Annex B, apsStatusSwitchedChannel is set to the
                    number of the channel that is currently switched to the
                    other channel. The value '0' indicates that no channel is
                    switched. The value '1' indicates that working channel 1 is
                    switched to working channel 2. The value '2' indicates that
                    working channel 2 is switched to working channel 1."

    SUPPORTS        TIMETRA-APS-MIB
        INCLUDES    {
            tmnxApsSwitchCommand,
            tmnxApsChanStatus,
            tmnxApsMcGroup,
            tmnxApsNotificationsV4v0,
            tmnxApsConfigGroup,
            tmnxApsConfigV8v0Group,
            tmnxApsGroupCommandV9v0Group,
            tmnxApsNotificationsV9v0Group
        }
        VARIATION   tmnxApsSwitchCommand
            DESCRIPTION
                    "For an Multi-Chassis (MC) APS group
                    (i.e. tApsMcNeighborAddr object of the TIMETRA-APS-MIB
                    is non-zero), the objects of this group can be set/read
                    only from the protection router, i.e. MC router having
                    the protection circuit (apsChanConfigNumber is 0)."

    ::= { tmnxSROSV10v0 2 }  -- APS

tmnx7710ApsCapsV10v0    AGENT-CAPABILITIES
    PRODUCT-RELEASE "Alcatel-Lucent SROS"
    STATUS          current
    DESCRIPTION     "Implementation of APS capabilities for
                     Alcatel-Lucent 7710 release R10.0."

    SUPPORTS        TIMETRA-APS-MIB
        INCLUDES    {
            tmnxApsConfigGroup,
            tmnxApsConfigV8v0Group
        }

        VARIATION   tApsProtectionType
            ACCESS  not-implemented
            DESCRIPTION
                "tApsProtectionType is not implemented on Alcatel-Lucent
                 7710 systems."

        VARIATION   tApsLineSFHoldTime
            ACCESS  not-implemented
            DESCRIPTION
                "tApsLineSFHoldTime is not implemented on Alcatel-Lucent
                 7710 systems."

        VARIATION   tApsLineSDHoldTime
            ACCESS  not-implemented
            DESCRIPTION
                "tApsLineSDHoldTime is not implemented on Alcatel-Lucent
                 7710 systems."

        VARIATION   tApsRdiAlarmGeneration
            ACCESS  not-implemented
            DESCRIPTION
                "tApsRdiAlarmGeneration is not implemented on Alcatel-Lucent
                 7710 systems."

    ::= { tmnxSROSApsCapsV10v0  1 }  -- 7710 APS

tmnx7950ApsCapsV10v0             AGENT-CAPABILITIES
    PRODUCT-RELEASE "Alcatel-Lucent SROS"
    STATUS          current
    DESCRIPTION     "Implementation of APS capabilities for
                     Alcatel-Lucent 7950 release R10.0."

--     SUPPORTS         APS-MIB
--         INCLUDES     { }
-- 
--     SUPPORTS         TIMETRA-APS-MIB
--         INCLUDES     { }

    ::= { tmnxSROSApsCapsV10v0 2 } -- 7950 APS

--
--  ATM CAPABILITIES
--
tmnxSROSAtmCapsV10v0    AGENT-CAPABILITIES
    PRODUCT-RELEASE "Alcatel-Lucent SROS"
    STATUS          current
    DESCRIPTION     "Implementation of ATM capabilities for
                     Alcatel-Lucent SROS release R10.0."

    SUPPORTS        ATM-MIB
        INCLUDES    {
            atmInterfaceTCGroup,
            aal5VccGroup,
            atmInterfaceConfGroup2,
            atmVccTerminationGroup2
-- EXCLUDE  atmVclCrossConnectGroup,
-- EXCLUDE  atmInterfaceConfGroup,
-- EXCLUDE  atmTrafficDescrGroup,
-- EXCLUDE  atmVpcTerminationGroup,
-- EXCLUDE  atmVccTerminationGroup,
-- EXCLUDE  atmVpCrossConnectGroup,
-- EXCLUDE  atmVcCrossConnectGroup,
-- EXCLUDE  atmInterfaceDs3PlcpGroup,
-- EXCLUDE  atmTrafficDescrGroup2,
-- EXCLUDE  atmVpcTerminationGroup2,
-- EXCLUDE  atmVplCrossConnectGroup,
-- EXCLUDE  atmVpPvcCrossConnectGroup,
-- EXCLUDE  atmVcPvcCrossConnectGroup
        }

        VARIATION   atmVccAal5CpcsTransmitSduSize
            ACCESS  not-implemented
            DESCRIPTION
                    "atmVccAal5CpcsTransmitSduSize is not implemented."

        VARIATION   atmVccAal5CpcsReceiveSduSize
            ACCESS  not-implemented
            DESCRIPTION
                    "atmVccAal5CpcsReceiveSduSize is not implemented."

        VARIATION   atmVccAal5EncapsType
            ACCESS  read-only
            DESCRIPTION
                    "Cannot be set on Alcatel-Lucent SROS systems."

        VARIATION   atmInterfaceMaxVpcs
            ACCESS  read-only
            DESCRIPTION
                    "Cannot be set on Alcatel-Lucent SROS systems."

        VARIATION   atmInterfaceMaxVccs
            ACCESS  read-only
            DESCRIPTION
                    "Cannot be set on Alcatel-Lucent SROS systems."

        VARIATION   atmInterfaceMaxActiveVpiBits
            ACCESS  read-only
            DESCRIPTION
                    "Cannot be set on Alcatel-Lucent SROS systems."

        VARIATION   atmInterfaceMaxActiveVciBits
            ACCESS  read-only
            DESCRIPTION
                    "Cannot be set on Alcatel-Lucent SROS systems."

        VARIATION   atmInterfaceMyNeighborIpAddress
            ACCESS  not-implemented
            DESCRIPTION
                    "atmInterfaceMyNeighborIpAddress is not implemented."

        VARIATION   atmInterfaceMyNeighborIfName
            ACCESS  not-implemented
            DESCRIPTION
                    "atmInterfaceMyNeighborIfName is not implemented."

        VARIATION   atmInterfaceSubscrAddress
            ACCESS  not-implemented
            DESCRIPTION
                    "atmInterfaceSubscrAddress is not implemented."

        VARIATION   atmInterfaceAddressType
            ACCESS  not-implemented
            DESCRIPTION
                    "Deprecated object."

        VARIATION   atmInterfaceAdminAddress
            ACCESS  not-implemented
            DESCRIPTION
                    "Deprecated object."

        VARIATION   atmVclAdminStatus
            ACCESS  read-only
            DESCRIPTION
                    "Cannot be set on Alcatel-Lucent SROS systems."

        VARIATION   atmVclReceiveTrafficDescrIndex
            ACCESS  read-only
            DESCRIPTION
                    "Cannot be set on Alcatel-Lucent SROS systems."

        VARIATION   atmVclTransmitTrafficDescrIndex
            ACCESS  read-only
            DESCRIPTION
                    "Cannot be set on Alcatel-Lucent SROS systems."

        VARIATION   atmVccAalType
            ACCESS  read-only
            DESCRIPTION
                    "Cannot be set on Alcatel-Lucent SROS systems."

        VARIATION   atmVclRowStatus
            ACCESS  read-only
            DESCRIPTION
                    "Cannot be set on Alcatel-Lucent SROS systems."

        VARIATION   atmVclCastType
            ACCESS  read-only
            DESCRIPTION
                    "Cannot be set on Alcatel-Lucent SROS systems."

        VARIATION   atmVclConnKind
            ACCESS  read-only
            DESCRIPTION
                    "Cannot be set on Alcatel-Lucent SROS systems."

        VARIATION   atmVclCrossConnectIdentifier
            ACCESS  not-implemented
            DESCRIPTION
                    "atmVclCrossConnectIdentifier is not implemented."

        VARIATION   atmVplAdminStatus
            ACCESS  read-only
            DESCRIPTION
                    "Cannot be set on Alcatel-Lucent SROS systems."

        VARIATION   atmVplReceiveTrafficDescrIndex
            ACCESS  read-only
            DESCRIPTION
                    "Cannot be set on Alcatel-Lucent SROS systems."

        VARIATION   atmVplTransmitTrafficDescrIndex
            ACCESS  read-only
            DESCRIPTION
                    "Cannot be set on Alcatel-Lucent SROS systems."

        VARIATION   atmVplRowStatus
            ACCESS  read-only
            DESCRIPTION
                    "Cannot be set on Alcatel-Lucent SROS systems."

        VARIATION   atmVplCastType
            ACCESS  read-only
            DESCRIPTION
                    "Cannot be set on Alcatel-Lucent SROS systems."

        VARIATION   atmVplConnKind
            ACCESS  read-only
            DESCRIPTION
                    "Cannot be set on Alcatel-Lucent SROS systems."

        VARIATION   atmVplCrossConnectIdentifier
            ACCESS  not-implemented
            DESCRIPTION
                    "atmVclCrossConnectIdentifier is not implemented."

        VARIATION   atmInterfaceIlmiVci
            ACCESS  read-only
            DESCRIPTION
                    "Cannot be set on Alcatel-Lucent SROS systems."

        VARIATION   atmInterfaceIlmiVpi
            ACCESS  read-only
            DESCRIPTION
                    "Cannot be set on Alcatel-Lucent SROS systems."

    SUPPORTS        TIMETRA-ATM-MIB
        INCLUDES    {
            tmnxAtmIntfConfV4v0Group,
            tmnxAtmIntfStatsV4v0Group,
            tmnxAtmIfcInfoGroup,
            tmnxAtmVclInfoGroup,
            tmnxAtmVclInfoGroupV9v0,
            tmnxAtmVclStatisticsGroup,
            tmnxAtmAal5VccStatisticsGroup,
            tmnxAtmCellVclStatisticsGroup,
            tmnxAtmVplInfoGroup,
            tmnxAtmVplStatisticsGroup,
            tmnxAtmVtlInfoGroup,
            tmnxAtmVtlStatisticsGroup,
            tmnxAtmIfcStatisticsGroup,
            tmnxAtmSysConfV4v0Group,
            tmnxAtmIlmiLinkGroup,
            tmnxAtmIlmiStatisticsGroup,
            tmnxAtmTCSublayerGroup,
            tmnxAtmNotificationsR4r0Group
-- EXCLUDE  tmnxAtmCpStatisticsGroup
        }

        VARIATION   tAtmIlmiLinkRowStatus
            SYNTAX  INTEGER {
                        active      (1),
                        createAndGo (4),
                        destroy     (6)
                     }
            DESCRIPTION
                    "tAtmIlmiLinkRowStatus supports only the values
                    'active (1)', 'createAndGo (4)' and 'destroy (6)'."

    ::= { tmnxSROSV10v0 3 }  -- ATM

tmnx7750AtmCapsV10v0    AGENT-CAPABILITIES
    PRODUCT-RELEASE "Alcatel-Lucent SROS"
    STATUS          current
    DESCRIPTION     "Implementation of ATM capabilities
                     for Alcatel-Lucent SROS 7750 release R10.0."

    SUPPORTS        TIMETRA-ATM-MIB
        INCLUDES    {
            tmnxAtmCpStatisticsGroup
        }

        VARIATION   tAtmCpStatsTotalCellsRxd
            DESCRIPTION
                    "tAtmCpStatsTotalCellsRxd is not supported on 7750 SR-1
                     systems."

        VARIATION   tAtmCpStatsTotalCellsRxdLo
            DESCRIPTION
                    "tAtmCpStatsTotalCellsRxdLo is not supported on 7750 SR-1
                     systems."

        VARIATION   tAtmCpStatsTotalCellsRxdHi
            DESCRIPTION
                    "tAtmCpStatsTotalCellsRxdHi is not supported on 7750 SR-1
                     systems."

        VARIATION   tAtmCpStatsTotalCellsTxd
            DESCRIPTION
                    "tAtmCpStatsTotalCellsTxd is not supported on 7750 SR-1
                     systems."

        VARIATION   tAtmCpStatsTotalCellsTxdLo
            DESCRIPTION
                    "tAtmCpStatsTotalCellsTxdLo is not supported on 7750 SR-1
                     systems."

        VARIATION   tAtmCpStatsTotalCellsTxdHi
            DESCRIPTION
                    "tAtmCpStatsTotalCellsTxdHi is not supported on 7750 SR-1
                     systems."

        VARIATION   tAtmCpStatsClp0CellsRxd
            DESCRIPTION
                    "tAtmCpStatsClp0CellsRxd is not supported on 7750 SR-1
                     systems."

        VARIATION   tAtmCpStatsClp0CellsRxdLo
            DESCRIPTION
                    "tAtmCpStatsClp0CellsRxdLo is not supported on 7750 SR-1
                     systems."

        VARIATION   tAtmCpStatsClp0CellsRxdHi
            DESCRIPTION
                    "tAtmCpStatsClp0CellsRxdHi is not supported on 7750 SR-1
                     systems."

        VARIATION   tAtmCpStatsClp0CellsTxd
            DESCRIPTION
                    "tAtmCpStatsClp0CellsTxd is not supported on 7750 SR-1
                     systems."

        VARIATION   tAtmCpStatsClp0CellsTxdLo
            DESCRIPTION
                    "tAtmCpStatsClp0CellsTxdLo is not supported on 7750 SR-1
                     systems."

        VARIATION   tAtmCpStatsClp0CellsTxdHi
            DESCRIPTION
                    "tAtmCpStatsClp0CellsTxdHi is not supported on 7750 SR-1
                     systems."

        VARIATION   tAtmCpStatsDrpCellsRxd
            DESCRIPTION
                    "tAtmCpStatsDrpCellsRxd is not supported on 7750 SR-1
                     systems."

        VARIATION   tAtmCpStatsDrpClp0CellsRxd
            DESCRIPTION
                    "tAtmCpStatsDrpClp0CellsRxd is not supported on 7750 SR-1
                     systems."

        VARIATION   tAtmCpStatsDrpClp0CellsTxd
            DESCRIPTION
                    "tAtmCpStatsDrpClp0CellsTxd is not supported on 7750 SR-1
                     systems."

        VARIATION   tAtmCpStatsTagCells
            DESCRIPTION
                    "tAtmCpStatsTagCells is not supported on 7750 SR-1
                     systems."

    ::= { tmnxSROSAtmCapsV10v0 1 }  -- 7750 ATM

tmnx7450AtmCapsV10v0    AGENT-CAPABILITIES
    PRODUCT-RELEASE "Alcatel-Lucent SROS"
    STATUS          current
    DESCRIPTION     "Implementation of ATM capabilities
                     for Alcatel-Lucent SROS 7450 release R10.0."

    SUPPORTS        TIMETRA-ATM-MIB
        INCLUDES    {
            tmnxAtmCpStatisticsGroup
        }

        VARIATION   tAtmCpStatsTotalCellsRxd
            DESCRIPTION
                    "tAtmCpStatsTotalCellsRxd is not supported on 7450 ESS-1,
                     ESS-6 or ESS-6V systems."

        VARIATION   tAtmCpStatsTotalCellsRxdLo
            DESCRIPTION
                    "tAtmCpStatsTotalCellsRxdLo is not supported on 7450 ESS-1,
                     ESS-6 or ESS-6V systems."

        VARIATION   tAtmCpStatsTotalCellsRxdHi
            DESCRIPTION
                    "tAtmCpStatsTotalCellsRxdHi is not supported on 7450 ESS-1,
                     ESS-6 or ESS-6V systems."

        VARIATION   tAtmCpStatsTotalCellsTxd
            DESCRIPTION
                    "tAtmCpStatsTotalCellsTxd is not supported on 7450 ESS-1,
                     ESS-6 or ESS-6V systems."

        VARIATION   tAtmCpStatsTotalCellsTxdLo
            DESCRIPTION
                    "tAtmCpStatsTotalCellsTxdLo is not supported on 7450 ESS-1,
                     ESS-6 or ESS-6V systems."

        VARIATION   tAtmCpStatsTotalCellsTxdHi
            DESCRIPTION
                    "tAtmCpStatsTotalCellsTxdHi is not supported on 7450 ESS-1,
                     ESS-6 or ESS-6V systems."

        VARIATION   tAtmCpStatsClp0CellsRxd
            DESCRIPTION
                    "tAtmCpStatsClp0CellsRxd is not supported on 7450 ESS-1,
                     ESS-6 or ESS-6V systems."

        VARIATION   tAtmCpStatsClp0CellsRxdLo
            DESCRIPTION
                    "tAtmCpStatsClp0CellsRxdLo is not supported on 7450 ESS-1,
                     ESS-6 or ESS-6V systems."

        VARIATION   tAtmCpStatsClp0CellsRxdHi
            DESCRIPTION
                    "tAtmCpStatsClp0CellsRxdHi is not supported on 7450 ESS-1,
                     ESS-6 or ESS-6V systems."

        VARIATION   tAtmCpStatsClp0CellsTxd
            DESCRIPTION
                    "tAtmCpStatsClp0CellsTxd is not supported on 7450 ESS-1,
                     ESS-6 or ESS-6V systems."

        VARIATION   tAtmCpStatsClp0CellsTxdLo
            DESCRIPTION
                    "tAtmCpStatsClp0CellsTxdLo is not supported on 7450 ESS-1,
                     ESS-6 or ESS-6V systems."

        VARIATION   tAtmCpStatsClp0CellsTxdHi
            DESCRIPTION
                    "tAtmCpStatsClp0CellsTxdHi is not supported on 7450 ESS-1,
                     ESS-6 or ESS-6V systems."

        VARIATION   tAtmCpStatsDrpCellsRxd
            DESCRIPTION
                    "tAtmCpStatsDrpCellsRxd is not supported on 7450 ESS-1,
                     ESS-6 or ESS-6V systems."

        VARIATION   tAtmCpStatsDrpClp0CellsRxd
            DESCRIPTION
                    "tAtmCpStatsDrpClp0CellsRxd is not supported on 7450 ESS-1,
                     ESS-6 or ESS-6V systems."

        VARIATION   tAtmCpStatsDrpClp0CellsTxd
            DESCRIPTION
                    "tAtmCpStatsDrpClp0CellsTxd is not supported on 7450 ESS-1,
                     ESS-6 or ESS-6V systems."

        VARIATION   tAtmCpStatsTagCells
            DESCRIPTION
                    "tAtmCpStatsTagCells is not supported on 7450 ESS-1,
                     ESS-6 or ESS-6V systems."

    ::= { tmnxSROSAtmCapsV10v0 2 }  -- 7450 ATM

tmnx7950AtmCapsV10v0             AGENT-CAPABILITIES
    PRODUCT-RELEASE "Alcatel-Lucent SROS"
    STATUS          current
    DESCRIPTION     "Implementation of ATM capabilities
                     for Alcatel-Lucent 7950 release R10.0."

--     SUPPORTS         ATM-MIB
--         INCLUDES     { }

--     SUPPORTS         TIMETRA-ATM-MIB
--         INCLUDES     { }

    ::= { tmnxSROSAtmCapsV10v0 3 } -- 7950 ATM

--
--  BGP CAPABILITIES
--
tmnxSROSBgpCapsV10v0    AGENT-CAPABILITIES
    PRODUCT-RELEASE "Alcatel-Lucent SROS"
    STATUS          current
    DESCRIPTION     "Implementation of BGP protocol capabilities for
                     Alcatel-Lucent SROS release R10.0."

    SUPPORTS        BGP4-MIB
        INCLUDES    {
            bgp4MIBGlobalsGroup,
            bgp4MIBPeerGroup,
            bgp4MIBPathAttrGroup,
            bgp4MIBNotificationGroup
        }

        VARIATION  bgpBackwardTransition
            DESCRIPTION
                    "The bgpBackwardTransition notification has vRtrID
                     appended to the variable list."

        VARIATION  bgpEstablished
            DESCRIPTION
                    "The bgpEstablished notification has vRtrID
                     appended to the variable list."

        VARIATION  bgpPeerMinRouteAdvertisementInterval
            SYNTAX     INTEGER (1..255)
            DESCRIPTION
                    "The maximum supported value for
                     bgpPeerMinRouteAdvertisementInterval is 255 seconds."

        VARIATION  bgpPeerMinASOriginationInterval
                SYNTAX     INTEGER (1..255)
                DESCRIPTION
                    "The maximum supported value for
                     bgpPeerMinASOriginationInterval is 255 seconds."

        VARIATION bgp4PathAttrASPathSegment
                SYNTAX     OCTET STRING (SIZE (0|2..255))
                DESCRIPTION
                        "An octet string of size 'zero' is returned if there are
                         no elements in the Autonomous System (AS) path
                         segments."

    SUPPORTS        TIMETRA-BGP-MIB
        INCLUDES    {
            tmnxBgpInstanceParamsV5v0Group,
            tmnxBgpPeerGroupParamsV5v0Group,
            tmnxBgpPeerParamsV5v0Group,
            tmnxBgp4PathAttrGroup,
            tmnxBgpNotificationV7v0Group,
            tmnxBgpNotifyObjsV7v0Group,
            tmnxBgpInstanceParamsV6v0Group,
            tmnxBgpInstanceV8v0Group,
            tmnxBgpInstanceV10v0Group,
            tmnxBgpPeerGroupParamsV6v0Group,
            tmnxBgpPeerParamsV6v0Group,
            tmnxBgp4ByteASNV7v0Group,
            tmnxBgpPeeringPolicyV10v0Group,
            tmnxBgpPeerGroupV10v0Group,
            tmnxBgpPeerV8v0Group,
            tmnxBgpPeerV10v0Group,
            tmnxBgpGlobalV8v0Group,
            tmnxBgpPeerV9v0Group,
            tmnxBgpGlobalV9v0Group,
            tmnxBgpAddPathV9v0R4Group,
            tmnxBgpFlowSpecV9v0Group,
            tmnxBgpDisableCapNegoV9v0Group,
            tmnxBgpNotifyObjsV9v0Group,
            tmnxBgpNotificationV9v0Group,
            tmnxBgpGlobalV10v0Group,
            tmnxBgpPeeringPlcyV10v0Group,
            tmnxBgpRTConstraintV10v0Group
        }

        VARIATION   tBgpInstanceGRAdminState
            ACCESS  not-implemented
            DESCRIPTION
                    "tBgpInstanceGRAdminState is not implemented."

        VARIATION   tBgpPeerGroupGRAdminState
            ACCESS  not-implemented
            DESCRIPTION
                    "tBgpPeerGroupGRAdminState is not implemented."

        VARIATION   tBgpPeerNgGRAdminState
            ACCESS  not-implemented
            DESCRIPTION
                    "tBgpPeerNgGRAdminState is not implemented."

        VARIATION   tBgpInstanceGROperState
            ACCESS  not-implemented
            DESCRIPTION
                    "tBgpInstanceGROperState is not implemented."

        VARIATION   tBgpPeerGroupGROperState
            ACCESS  not-implemented
            DESCRIPTION
                    "tBgpPeerGroupGROperState is not implemented."

        VARIATION   tBgpPeerNgGROperState
            ACCESS  not-implemented
            DESCRIPTION
                    "tBgpPeerNgGROperState is not implemented."

        VARIATION   tBgpPGTTLLogId
            ACCESS  not-implemented
            DESCRIPTION
                    "tBgpPGTTLLogId is not implemented."

        VARIATION   tBgpInstanceGRPathSelectDefer
            ACCESS  read-only
            DESCRIPTION
                    "tBgpInstanceGRPathSelectDefer is implemented as
                     read only."

        VARIATION   tBgpInstanceGRRestartTime
            ACCESS  read-only
            DESCRIPTION
                    "tBgpInstanceGRRestartTime is implemented as
                     read only."
        
        VARIATION   tBgpPeerGroupGRRestartTime
            ACCESS  read-only
            DESCRIPTION
                    "tBgpPeerGroupGRRestartTime is implemented as
                     read only."

        VARIATION   tBgpPeerNgGRRestartTime
            ACCESS  read-only
            DESCRIPTION
                    "tBgpPeerNgGRRestartTime is implemented as
                     read only."

        VARIATION  tBgpNgBackwardTransition
            DESCRIPTION
                    "The tBgpNgBackwardTransition notification has vRtrID
                     appended to the variable list."

        VARIATION  tBgpNgEstablished
            DESCRIPTION
                    "The tBgpNgEstablished notification has vRtrID
                     appended to the variable list."

        VARIATION   tBgpInstanceRapidUpdate
            SYNTAX  BITS {
                      -- unused    (0),
                      -- ipv4      (1),
                      -- vpnIpv4   (2),
                      -- ipv6      (3),
                      -- mcastIpv4 (4),
                      -- vpnIpv6   (5),
                      l2vpn        (6),
                      mvpnIpv4     (7),
                      mdtSafi      (8)
                    }
            DESCRIPTION
                    "tBgpInstanceRapidUpdate is supported only for l2vpn(6),
                     mvpnIPv4(7) and mdtSafi(8)address families.

                     An 'inconsistentValue' error is returned if an attempt 
                     is made to set tBgpInstanceRapidUpdate for non base 
                     router instance."

        VARIATION  tBgpPeerNgAdvertiseLdpPrefix
            DESCRIPTION
                    "tBgpPeerNgAdvertiseLdpPrefix is supported only when
                     tBgpPeerNgAdvLabelAddrFamily is set to 'ipv4'.

                     When tBgpPeerNgAdvLabelAddrFamily is set to 'ipv6', an
                     attempt to set tBgpPeerNgAdvertiseLdpPrefix to 'true'
                     results in an 'inconsistentValue' error."

        VARIATION   tBgpPrngPlcyMaxPrefixLogOnly
            ACCESS  read-only
            DESCRIPTION
                    "tBgpPrngPlcyMaxPrefixLogOnly is implemented as read only."

        VARIATION   tBgpPrngPlcyMaxPrefixThreshold
            ACCESS  read-only
            DESCRIPTION
                    "tBgpPrngPlcyMaxPrefixThreshold is implemented as
                     read only."

        VARIATION   tBgpInstanceAdvertiseExternal
            SYNTAX  BITS {
                      -- unused    (0),
                      ipv4         (1),
                      -- vpnIpv4   (2),
                      ipv6         (3)
                    }
            DESCRIPTION
                    "tBgpInstanceAdvertiseExternal is supported only for 'ipv4 (1)'
                     and 'ipv6 (3)' address families.

                     An 'inconsistentValue' error is returned if an attempt 
                     is made to set tBgpInstanceAdvertiseExternal for non base 
                     router instance."

        VARIATION   tBgpInstanceBackupPath
            SYNTAX  BITS {
                      -- unused    (0),
                      ipv4         (1),
                      -- vpnIpv4   (2),
                      ipv6         (3)
                    }
            DESCRIPTION
                    "tBgpInstanceBackupPath is supported only for 'ipv4 (1)'
                     and 'ipv6 (3)' address families."

        VARIATION   tBgpPGIpv4AddPathLimit
            SYNTAX  Integer32 (0..16)
            DESCRIPTION
                    "tBgpPGIpv4AddPathLimit does not support the value -1
                     in the current release."

        VARIATION   tBgpPGVpnIpv4AddPathLimit
            SYNTAX  Integer32 (0..16)
            DESCRIPTION
                    "tBgpPGVpnIpv4AddPathLimit does not support the value -1
                     in the current release."

        VARIATION   tBgpPGIpv6AddPathLimit
            SYNTAX  Integer32 (0..16)
            DESCRIPTION
                    "tBgpPGIpv4AddPathLimit does not support the value -1
                     in the current release."

        VARIATION   tBgpPGVpnIpv6AddPathLimit
            SYNTAX  Integer32 (0..16)
            DESCRIPTION
                    "tBgpPGVpnIpv6AddPathLimit does not support the value -1
                     in the current release."

        VARIATION   tBgpPeerNgIpv4AddPathLimit
            SYNTAX  Integer32 (0..16)
            DESCRIPTION
                    "tBgpPeerNgIpv4AddPathLimit does not support the value -1
                     in the current release."

        VARIATION   tBgpPeerNgVpnIpv4AddPathLimit
            SYNTAX  Integer32 (0..16)
            DESCRIPTION
                    "tBgpPeerNgVpnIpv4AddPathLimit does not support
                     the value -1 in the current release."

        VARIATION   tBgpPeerNgIpv6AddPathLimit
            SYNTAX  Integer32 (0..16)
            DESCRIPTION
                    "tBgpPeerNgIpv6AddPathLimit does not support the value -1
                     in the current release."

        VARIATION   tBgpPeerNgVpnIpv6AddPathLimit
            SYNTAX  Integer32 (0..16)
            DESCRIPTION
                    "tBgpPeerNgVpnIpv6AddPathLimit does not support
                     the value -1 in the current release."

        VARIATION   tBgpInstanceIpv4AddPathLimit
            SYNTAX  Integer32 (0..16)
            DESCRIPTION
                    "tBgpInstanceIpv4AddPathLimit does not support the value -1
                     in the current release."

        VARIATION   tBgpInstanceVpnIpv4AddPathLimit
            SYNTAX  Integer32 (0..16)
            DESCRIPTION
                    "tBgpInstanceVpnIpv4AddPathLimit does not support
                     the value -1 in the current release."

        VARIATION   tBgpInstanceIpv6AddPathLimit
            SYNTAX  Integer32 (0..16)
            DESCRIPTION
                    "tBgpInstanceIpv6AddPathLimit does not support the value -1
                     in the current release."

        VARIATION   tBgpInstanceVpnIpv6AddPathLimit
            SYNTAX  Integer32 (0..16)
            DESCRIPTION
                    "tBgpInstanceVpnIpv6AddPathLimit does not support
                     the value -1 in the current release."

        VARIATION   tBgpInstanceAsPathIgnoreFamily
            SYNTAX  BITS {
                      -- unused    (0),
                      ipv4      (1),
                      vpnIpv4   (2),
                      ipv6      (3),
                      mcastIpv4 (4),
                      vpnIpv6   (5),
                      l2vpn     (6),
                      mvpnIpv4  (7)
                    }
            DESCRIPTION
                    "tBgpInstanceAsPathIgnoreFamily is supported only for
                     'ipv4 (1)', 'vpnIpv4 (2)', 'ipv6 (3)', 'mcastIpv4 (4)',
                     'vpnIpv6 (5)', 'l2vpn (6)' and 'mvpnIpv4 (7)' address
                     families on base router instance.

                     tBgpInstanceAsPathIgnoreFamily is supported only for
                     'ipv4 (1)', and 'ipv6 (3)' address families for non-base
                     router instance. An 'inconsistentValue' error is returned
                     if an attempt is made to set the value of 
                     tBgpInstanceAsPathIgnoreFamily to an unsupported family 
                     for non-base router instance."

        VARIATION   tBgpInstanceDefaultOriginate 
            ACCESS  not-implemented
            DESCRIPTION
                    "tBgpInstanceDefaultOriginate is not implemented."

        VARIATION   tBgpPGDefaultOriginate
            ACCESS  not-implemented
            DESCRIPTION
                    "tBgpPGDefaultOriginate is not implemented."

        VARIATION   tBgpPeerNgDefaultOriginate
            ACCESS  not-implemented
            DESCRIPTION
                    "tBgpPeerNgDefaultOriginate is not implemented."
        
        VARIATION   tBgpInstanceIgpShortcut
            SYNTAX  BITS {
                      te    (0),
                      ldp   (1),
                   -- ip    (2),
                      mpls  (3)
                    }
            DESCRIPTION
                    "tBgpInstanceIgpShortcut dose not support 'ip (2)'.

                     tBgpInstanceIgpShortcut is only supported on base 
                     router instance. An 'inconsistentValue' error is returned
                     if an attempt is made to set tBgpInstanceIgpShortcut for 
                     non-base router instance."

        VARIATION   tBgpInstanceTransportTunnel
            DESCRIPTION
                    "tBgpInstanceTransportTunnel is only supported on base 
                     router instance. An 'inconsistentValue' error is returned
                     if an attempt is made to set tBgpInstanceTransportTunnel for 
                     non-base router instance."

        VARIATION   tBgpInstanceFamily
            DESCRIPTION
                    "tBgpInstanceFamily dose not support 'unused (0)'.

                     Only 'ipv4 (1)', 'ipv6 (3)' and 'mcastIpv4 (4)' address 
                     families are supported on non-base router instance.

                     An 'inconsistentValue' error is returned if an attempt 
                     is made to set tBgpInstanceFamily to families other than
                     'ipv4 (1)', 'ipv6 (3)' and 'mcastIpv4 (4)' for non-base 
                     router instance."

        VARIATION   tBgpPeerGroupFamily
            DESCRIPTION
                    "tBgpPeerGroupFamily dose not support 'unused (0)'.

                     Only 'ipv4 (1)', 'ipv6 (3)' and 'mcastIpv4 (4)' address 
                     families are supported on non-base router instance.
        
                     An 'inconsistentValue' error is returned if an attempt 
                     is made to set tBgpInstanceFamily to families other than
                     'ipv4 (1)', 'ipv6 (3)' and 'mcastIpv4 (4)' for non-base 
                     router instance."

        VARIATION  tBgpPeerNgFamily
            DESCRIPTION
                    "tBgpPeerNgFamily dose not support 'unused (0)'.

                     Only 'ipv4 (1)', 'ipv6 (3)' and 'mcastIpv4 (4)' address 
                     families are supported on non-base router instance.
        
                     An 'inconsistentValue' error is returned if an attempt 
                     is made to set tBgpInstanceFamily to families other than
                     'ipv4 (1)', 'ipv6 (3)' and 'mcastIpv4 (4)' for non-base 
                     router instance."

        VARIATION  tBgpPeerNgAdvLabelAddrFamily
            DESCRIPTION
                    "tBgpPeerNgAdvertiseLdpPrefix is supported only for 'ipv4 (2)'
                     family on non-base router instance.
        
                     An 'inconsistentValue' error is returned if an attempt 
                     is made to set tBgpPeerNgAdvertiseLdpPrefix to 'ipv6(1)' 
                     for non base router instance."

        VARIATION   tBgpPGAigp 
            ACCESS  not-implemented
            DESCRIPTION
                    "tBgpPGAigp is not implemented."

        VARIATION   tBgpPeerNgAigp 
            ACCESS  not-implemented
            DESCRIPTION
                    "tBgpPeerNgAigp is not implemented."

    ::= { tmnxSROSV10v0 4 }  -- BGP

tmnx7450BgpCapsV10v0    AGENT-CAPABILITIES
    PRODUCT-RELEASE "Alcatel-Lucent SROS"
    STATUS          current
    DESCRIPTION     "Implementation of BGP protocol capabilities for
                     Alcatel-Lucent SROS 7450 release R10.0."

    SUPPORTS        TIMETRA-BGP-MIB
        INCLUDES    {
                        tmnxBgpPeerGroupV10v0Group,
                        tmnxBgpInstanceV8v0Group,
                        tmnxBgpInstanceV10v0Group
        }
        VARIATION   tBgpInstanceFamily
            SYNTAX  BITS {
                      -- unused    (0),
                      ipv4      (1),
                      --  vpnIpv4   (2),
                      --  ipv6      (3),
                      --  mcastIpv4 (4),
                      --  vpnIpv6   (5),
                      l2vpn     (6),
                      --  mvpnIpv4  (7),
                      --  mdtSafi   (8),
                      mspw        (9)
                      -- flowIpv4    (10),
                      -- routeTarget (11)
                     }
            DESCRIPTION
                    "Only 'ipv4 (1)' and 'l2vpn (6)' and 'mspw (9)' families
                     are supported on the SROS 7450 platform."

        VARIATION tBgpPeerGroupFamily
            SYNTAX  BITS {
                      -- unused    (0),
                      ipv4      (1),
                      --  vpnIpv4   (2),
                      --  ipv6      (3),
                      --  mcastIpv4 (4),
                      --  vpnIpv6   (5),
                      l2vpn     (6),
                      --  mvpnIpv4  (7),
                      --  mdtSafi   (8),
                      mspw        (9)
                      -- flowIpv4    (10),
                      -- routeTarget (11)
                     }
            DESCRIPTION
                    "Only 'ipv4 (1)' and 'l2vpn (6)' and 'mspw (9)' families
                     are supported on the SROS 7450 platform."

        VARIATION tBgpPeerNgFamily
            SYNTAX  BITS {
                      -- unused    (0),
                      ipv4      (1),
                      --  vpnIpv4   (2),
                      --  ipv6      (3),
                      --  mcastIpv4 (4),
                      --  vpnIpv6   (5),
                      l2vpn     (6),
                      --  mvpnIpv4  (7),
                      --  mdtSafi   (8),
                      mspw        (9)
                      -- flowIpv4    (10),
                      -- routeTarget (11)
                     }
            DESCRIPTION
                    "Only 'ipv4 (1)' and 'l2vpn (6)' and 'mspw (9)' families
                     are supported on the SROS 7450 platform."

        VARIATION   tBgpInstanceRapidUpdate
            SYNTAX  BITS {
                    --  unused    (0),
                    --  ipv4      (1),
                    --  vpnIpv4   (2),
                    --  ipv6      (3),
                    --  mcastIpv4 (4),
                    --  vpnIpv6   (5),
                    l2vpn         (6)
                    --  mvpnIpv4  (7),
                    --  mdtSafi   (8)
                    }
            DESCRIPTION
                    "tBgpInstanceRapidUpdate supports only l2vpn(6)
                     address familiy on the SROS 7450 platform.

                     An 'inconsistentValue' error is returned if an attempt 
                     is made to set tBgpInstanceRapidUpdate for non base 
                     router instance."

        VARIATION   tBgpInstanceDefaultOriginate 
            ACCESS  not-implemented
            DESCRIPTION
                    "tBgpInstanceDefaultOriginate is not implemented."

        VARIATION   tBgpPGDefaultOriginate
            ACCESS  not-implemented
            DESCRIPTION
                    "tBgpPGDefaultOriginate is not implemented."

        VARIATION   tBgpPeerNgDefaultOriginate
            ACCESS  not-implemented
            DESCRIPTION
                    "tBgpPeerNgDefaultOriginate is not implemented."

        VARIATION   tBgpInstanceIgpShortcut
            SYNTAX  BITS {
                      te    (0),
                      ldp   (1),
                   -- ip    (2),
                      mpls  (3)
                    }
            DESCRIPTION
                    "tBgpInstanceIgpShortcut dose not support 'ip (2)'.

                     tBgpInstanceTransportTunnel is only supported on base 
                     router instance. An 'inconsistentValue' error is returned
                     if an attempt is made to set tBgpInstanceIgpShortcut for 
                     non-base router instance."

        VARIATION   tBgpInstanceTransportTunnel
            DESCRIPTION
                    "tBgpInstanceTransportTunnel is only supported on base 
                     router instance. An 'inconsistentValue' error is returned
                     if an attempt is made to set tBgpInstanceTransportTunnel
                     for non-base router instance."

    ::= { tmnxSROSBgpCapsV10v0 2 }  -- 7450 BGP

--
--  CFLOWD CAPABILITIES
--
tmnxSROSCflowdCapsV10v0    AGENT-CAPABILITIES
    PRODUCT-RELEASE "Alcatel-Lucent SROS"
    STATUS          current
    DESCRIPTION     "Implementation of CFLOWD protocol capabilities for
                    Alcatel-Lucent SROS release R10.0"

    SUPPORTS        TIMETRA-CFLOWD-MIB
        INCLUDES    {
            tmnxCflowdGlobalGroup,
            tmnxCflowdHostGroup,
            tmnxCflowdNotificationV8v0Group,
            tmnxCflowdGlobalGroupV6v0,
            tmnxCflowdGroupV8v0,
            tmnxCflowdStatisticsV10v0Group
        }

        VARIATION   tmnxCflowdMaxCollectors
            ACCESS  read-only
            DESCRIPTION
                    "tmnxCflowdMaxCollectors is implemented as
                     read only."

        VARIATION   tmnxCflowdFlowUnsuppProto
            ACCESS  not-implemented
            DESCRIPTION
                    "tmnxCflowdFlowUnsuppProto is not implemented."

       VARIATION    tmnxCFHostRowStatus
            SYNTAX  INTEGER {
                        active      (1),
                        createAndGo (4),
                        destroy     (6)
                     }
            DESCRIPTION
                    "The tmnxCFHostRowStatus supports only the values
                    'active (1)', 'createAndGo (4)' and 'destroy (6)'."


       VARIATION    tmnxCFHostVersion
            SYNTAX  Unsigned32 (0|5|8..9)
            DESCRIPTION
                    "tmnxCFHostVersion supports versions 5, 8, and 9 in
                     Alcatel-Lucent SROS release 8.0R1."

       VARIATION    tmnxCflowdTemplateFlowIndex
            SYNTAX  INTEGER {
                        ipv4 (1),
                        mpls (2)
                        -- ipv6 (3)
                    }
            DESCRIPTION
                    "tmnxCflowdTemplateFlowIndex supports 'ipv4' and 'mpls'
                     in Alcatel-Lucent SROS release 8.0R1."

    ::= { tmnxSROSV10v0 5 }  -- CFLOWD

--
--  CHASSIS CAPABILITIES
--
tmnxSROSChassisCapsV10v0    AGENT-CAPABILITIES
    PRODUCT-RELEASE "Alcatel-Lucent SROS"
    STATUS          current
    DESCRIPTION     "Implementation of CHASSIS or hardware capabilities for
                     Alcatel-Lucent SROS release R10.0"

    SUPPORTS        TIMETRA-CHASSIS-MIB
        INCLUDES    {
            tmnxAtmGroup,
            tmnxCardCamErrorV6v1Group,
            tmnxCardPchipV5v0Group,
            tmnxCardPchipV8v0Group,
            tmnxCardV3v0Group,
            tmnxCardV7v0Group,
            tmnxChassisHwV6v1Group,
            tmnxChassisHwV9v0Group,
            tmnxChassisNotificationV7v0Group,
            tmnxChassisNotificationV9v0Group,
            tmnxChassisUserModV7v0Group,
            tmnxChassisV5v0Group,
            tmnxChassisV6v1Group,
            tmnxChassisV8v0Group,
-- EXCLUDE  tmnxChassisV10v0Group,
            tmnxIPsecNotifV7v0Group,
            tmnxIPsecV7v0Group,
            tmnxMDAV6v1Group,
            tmnxMdaXplV5v0Group,
            tmnxMDAV9v0Group,
            tmnxSyncIfTimingNotifV8v0Group,
            tmnxSyncIfTimingV8v0Group,
            tmnxSyncV6v0Group,
            tmnxSyncIfTimingNotifyV9v0Group,
            tmnxCardV10v0Group,
            tmnxIpsecV10v0Group,
-- EXCLUDE  tmnxChassisNotifyV10v0Group,
            tmnxFPQGrpGroup,
            tmnxMdaHsmdaPoolV10v0Group,
-- EXCLUDE  tmnxMdaV10v0Group                for 10.0R4
            tmnxFPQGrpV10v0R4Group
-- EXCLUDE  tmnx7710HwV3v0Group
-- EXCLUDE  tmnx7710SETSRefSrcHwV6v0Group
-- EXCLUDE  tmnx77x0CESMDAV6v0Group
-- EXCLUDE  tmnxCardV6v0NamedPoolPlcyGroup
-- EXCLUDE  tmnxChassisMixedModeIomV8v0Group
-- EXCLUDE  tmnxChassisV7v0Group
-- EXCLUDE  tmnxFPMcPathMgmtV6v1Group
-- EXCLUDE  tmnxFPWredV7v0Group
-- EXCLUDE  tmnxIPsecIsaGrpV6v0Group
-- EXCLUDE  tmnxMDACcagV6v1Group
-- EXCLUDE  tmnxMDAMcPathMgmtV6v0Group
        }

        VARIATION   tmnxChassisRowStatus
            ACCESS  read-only
            DESCRIPTION
                    "tmnxChassisRowStatus is supported as read-only.
                    Row entries cannot be created by SNMP SET requests.
                    Multiple chassis's are not supported on Alcatel-Lucent
                    SROS systems."

        VARIATION   tmnxHwContainedIndex
            ACCESS  not-implemented
            DESCRIPTION
                    "The tmnxHwContainsTable is not implemented."

        VARIATION   tmnxCardAllowedTypes
            ACCESS  not-implemented
            DESCRIPTION
                    "tmnxCardAllowedTypes object is not implemented.
                    This object was made obsolete in the 3.0 release.

                    A bit-mask that specifies what IOM card types the
                    administrator has designated be allowed to be inserted
                    into this slot.If the slot has not-been pre-provisioned
                    and a card that does not match one of the allowed types
                    is inserted into this slot, a mis-match alarm is
                    raised.  If a specific value has not yet been SET by the
                    manager, tmnxCardAllowedTypes returns the same
                    value to a GET request as tmnxCardSupportedTypes."

        VARIATION   tmnxCpmCardAllowedTypes
            ACCESS  not-implemented
            DESCRIPTION
                    "tmnxCpmCardAllowedTypes object is not implemented.
                    This object was made obsolete in the 3.0 release.

                    A bit-mask that specified what CPM card types the
                    administrator has designated be allowed to be inserted
                    into this slot.  If the slot has not-been pre-provisioned
                    and a card that does not match one of the allowed types is
                    inserted into this slot, a mis-match alarm would be raised.

                    If a specific value had not yet been SET by the
                    manager, tmnxCpmCardAllowedTypes would return the same
                    value to a GET request as tmnxCpmCardSupportedTypes."

        VARIATION   tmnxCpmCardAssignedType
            ACCESS  read-only
            DESCRIPTION
                    "tmnxCpmCardAssignedType is supported as read-only.
                    Multiple CPM card types are not supported on Alcatel-Lucent
                    SROS systems."

        VARIATION   tmnxMDAAllowedTypes
            ACCESS  not-implemented
            DESCRIPTION
                    "tmnxMDAAllowedTypes object is not implemented.
                    This object was made obsolete in the 3.0 release.

                    A bit-mask specified what MDA card types the
                    administrator has designated be allowed to be inserted
                    into this slot. If the slot has not-been pre-provisioned
                    and a MDA card that does not match one of the allowed
                    types is inserted into this slot, a mis-match alarm would
                    be raised.  If a specific value has not yet been SET by
                    the manager, a GET to tmnxMDAAllowedTypes returned the
                    same value as tmnxMDASupportedTypes."

        VARIATION   tmnxMDAEquippedPorts
            DESCRIPTION
                    "The value of tmnxMDAEquippedPorts indicates the number
                    of ports equipped on this MDA card. Previous to the 3.0
                    release this object was defined to be a bit-mask of
                    equipped ports.  However, the code implementation has
                    always returned a value that is just the total number of
                    equipped ports."

        VARIATION   tmnxHwConfigChange
            ACCESS  not-implemented
            DESCRIPTION
                    "tmnxHwConfigChange notification is not implemented.
                    This notification was made obsolete in the 2.1 release.

                    The tmnxHwConfigChange notification has been replaced
                    with the generic change notifications from the
                    TIMETRA-SYSTEM-MIB: tmnxConfigModify, tmnxConfigCreate,
                    tmnxConfigDelete, tmnxStateChange."

        VARIATION   tmnxEqCpuFailure
            ACCESS  not-implemented
            DESCRIPTION
                    "tmnxEqCpuFailure notification is not implemented.
                    This notification was made obsolete in the 2.1 release.

                    A cpu failure on a CPM card is detected by the hardware
                    bootup and is indicated by the boot diagnostic display.
                    If there is no working redundant CPM card, the system
                    does not come up.

                    A failure of an IOM card or standby redundant CPM card
                    causes the tmnxEqCardFailure notification to be sent."

        VARIATION   tmnxEqMemoryFailure
            ACCESS  not-implemented
            DESCRIPTION
                    "tmnxEqMemoryFailure notification is not implemented.
                    This notification was made obsolete in the 2.1 release.

                    A failure of the memory device is detected by the
                    hardware bootup and is indicated by the boot diagnostic
                    display.  If there is no working redundant CPM card,
                    the system does not come up.

                    A failure of the memory device during run-time causes
                    the system to fail and the 'admin tech-support'
                    information to be saved.

                    A failure of an IOM card or standby redundant CPM card
                    causes the tmnxEqCardFailure notification to be sent."

        VARIATION   tmnxEqBackdoorBusFailure
            ACCESS  not-implemented
            DESCRIPTION
                    "tmnxEqBackdoorBusFailure notification is not implemented.
                    This notification was made obsolete in the 2.1 release."

        VARIATION   tmnxPeSoftwareError
            ACCESS  not-implemented
            DESCRIPTION
                    "tmnxPeSoftwareError notification is not implemented.
                    This notification was made obsolete in the 2.1 release.

                    Many of the other notifications more specifically
                    indicate detection of some type of software error.

                    Also, there are TRACE_* MACROs throughout the code that
                    developers use to trap failures that might result in a
                    software crash.  The highest severity event, TRACE_ERROR,
                    prints directly to the CONSOLE and in release software
                    causes the system to reboot.  Ideally, the customer
                    never sees TRACE_ERROR messages.  The 'admin tech-support'
                    information includes a log of TRACE messages to help
                    developers diagnose a failure of the software in the
                    field."

        VARIATION   tmnxPeSoftwareAbnormalHalt
            ACCESS  not-implemented
            DESCRIPTION
                    "tmnxPeSoftwareAbnormalHalt notification is not
                    implemented.  This notification was made obsolete in
                    the 2.1 release.

                    Many of the other notifications more specifically
                    indicate detection of some type of software error.

                    Also, there are TRACE_* MACROs throughout the code that
                    developers use to trap failures that might result in a
                    software crash.  The highest severity event, TRACE_ERROR,
                    prints directly to the CONSOLE and in release software
                    causes the system to reboot.  Ideally, the customer
                    never sees TRACE_ERROR messages.  The 'admin tech-support'
                    information includes a log of TRACE messages to help
                    developers diagnose a failure of the software in the
                    field."

        VARIATION   tmnxPeOutOfMemory
            ACCESS  not-implemented
            DESCRIPTION
                    "tmnxPeOutOfMemory notification is not implemented.
                    This notification was made obsolete in the 2.1 release.

                    The tmnxPeOutOfMemory notification has been replaced
                    with the module specific notification from the
                    TIMETRA-SYSTEM-MIB: tmnxModuleMallocFailed."

        VARIATION   tmnxPeConfigurationError
            ACCESS  not-implemented
            DESCRIPTION
                    "tmnxPeConfigurationError notification is not implemented.
                    This notification was made obsolete in the 2.1 release.

                    Many other notifications more specifically indicate
                    detection of a configuration error.  In most cases the
                    SNMP SET request that tries to make an invalid
                    configuration results in an error response.

                    In some cases the configuration parameters are valid
                    and the SNMP SET request succeeds but the system cannot
                    successfully apply the new parameters.  The affected
                    object may then put into an operational 'down' state.
                    A state change notification such as tmnxStateChange or
                    a more specific notification is sent to alert about the
                    problem.

                    For example, an attempt to create an event log with a
                    file-type destination when the specified cflash media is
                    full or not present results in TIMETRA-LOG-MIB
                    notifications tmnxLogSpaceContention,
                    tmnxLogAdminLocFailed, or tmnxLogBackupLocFailed."

        VARIATION   tmnxPeStorageProblem
            ACCESS  not-implemented
            DESCRIPTION
                    "tmnxPeStorageProblem notification is not implemented.
                    This notification was made obsolete in the 2.1 release.

                    The only 'storage' devices on the SROS are the cflash
                    drives.  Cflash write errors cause a tmnxEqFlashDataLoss
                    notification to be sent.  The tmnxEqFlashDiskFull
                    notification is sent when the driver detects that the
                    cflash device is full."

        VARIATION   tmnxPeCpuCyclesExceeded
            ACCESS  not-implemented
            DESCRIPTION
                    "tmnxPeCpuCyclesExceeded notification is not implemented.
                    This notification was made obsolete in the 2.1 release.

                    It does not apply. The SROS software architecture does
                    not restrict CPU cycles used by a specific code module."

        VARIATION   tmnxRedSecondaryCPMStatusChange
            ACCESS  not-implemented
            DESCRIPTION
                    "tmnxRedSecondaryCPMStatusChange notification is not
                    implemented.  This notification was made obsolete in
                    the 2.1 release.

                    There is no way to administratively enable or disable
                    CPM cards so there is no need for a status change event
                    for administrative state changes.

                    Operational changes detected about the Secondary CPM
                    card are indicated by more specific notifications such
                    as tmnxEqCardFailure, tmnxEqCardRemoved, and
                    tmnxEqCardInserted."

        VARIATION   tmnxRedRestoreSuccess
            ACCESS  not-implemented
            DESCRIPTION
                    "tmnxRedRestoreSuccess notification is not implemented.
                    This notification was made obsolete in the 2.1 release.

                    It does not apply. This event was originally created
                    for an early redundancy mechanism that was never
                    released.  This event should be removed.

                    When the secondary CPM card takes over following a
                    reboot or failure of the active CPM, sbiBootConfig
                    and sbiBootSnmpd events from the TIMETRA-SYSTEM-MIB
                    are generated to indicate that the secondary card
                    has successfully taken control of the system."

        VARIATION   tmnxRedRestoreFail
            ACCESS  not-implemented
            DESCRIPTION
                    "tmnxRedRestoreFail notification is not implemented.
                    This notification was made obsolete in the 2.1 release.

                    It does not apply. This event was originally created
                    for an early redundancy mechanism that was never
                    released.  This event should be removed."

        VARIATION   tmnxHwOperState
            SYNTAX  INTEGER {
                        unknown         (1),
                        inService       (2),
                        outOfService    (3),
                        diagnosing      (4),
                        failed          (5),
                        booting         (6),
                        empty           (7),
                        provisioned     (8),
                        unprovisioned   (9),
                        upgrade         (10),
                        downgrade       (11)
                        -- inServiceUpgrage     (12),
                        -- inServiceDowngrade   (13),
                        -- resetPending         (14)
                    }
            DESCRIPTION
                    "The enumerations 'inServiceUpgrade (12)',
                    'inServiceDowngrade (13)', and 'resetPending (14)' are no
                    longer supported."

        VARIATION   tSyncIfTimingAdmRefOrder1
            SYNTAX  TmnxSETSRefSource {
                     -- otherCPM    (0)
                        reference1  (1),
                        reference2  (2),
                        bits        (3)
                     -- bits2       (4)
                     -- ptp         (5)
                        -- noReference (6)
                    }
            DESCRIPTION
                    "The tSyncIfTimingAdmRefOrder1 supports only the values
                     'reference1 (1)', 'reference (2)', and 'bits (3)'."

        VARIATION   tSyncIfTimingAdmRefOrder2
            SYNTAX  TmnxSETSRefSource {
                     -- otherCPM    (0)
                        reference1  (1),
                        reference2  (2),
                        bits        (3)
                     -- bits2       (4)
                     -- ptp         (5)
                        -- noReference (6)
                    }
            DESCRIPTION
                    "The tSyncIfTimingAdmRefOrder2 supports only the values
                     'reference1 (1)', 'reference (2)', and 'bits (3)'."

        VARIATION   tSyncIfTimingAdmRefOrder3
            SYNTAX  TmnxSETSRefSource {
                     -- otherCPM    (0)
                        reference1  (1),
                        reference2  (2),
                        bits        (3)
                     -- bits2       (4)
                     -- ptp         (5)
                        -- noReference (6)
                    }
            DESCRIPTION
                    "The tSyncIfTimingAdmRefOrder1 supports only the values
                     'reference1 (1)', 'reference (2)', and 'bits (3)'."

        VARIATION   tSyncIfTimingAdmRef1CfgQltyLevel
            SYNTAX  TmnxSSMQualityLevel {
                        unknown    (0),
                        prs        (1),
                        stu        (2),
                        st2        (3),
                        tnc        (4),
                        st3e       (5),
                        st3        (6),
                     -- smc     (7)
                     -- st4     (8)
                     -- dus     (9)
                        prc       (10),
                        ssua      (11),
                        ssub      (12),
                        sec       (13),
                     -- dnu    (14)
                     -- inv    (15)
                     -- pno    (16)
                        eec1      (17),
                        eec2      (18)
                        -- failed (19)
                    }
            DESCRIPTION
                    "The tSyncIfTimingAdmRef1CfgQltyLevel does not support the
                     values 'smc (7)', 'st4 (8)', 'dus (9)', 'dnu (14)',
                     'inc (15)', 'pno (16)', or 'failed (19)'."

        VARIATION   tSyncIfTimingAdmRef2CfgQltyLevel
            SYNTAX  TmnxSSMQualityLevel {
                        unknown    (0),
                        prs        (1),
                        stu        (2),
                        st2        (3),
                        tnc        (4),
                        st3e       (5),
                        st3        (6),
                     -- smc     (7)
                     -- st4     (8)
                     -- dus     (9)
                        prc       (10),
                        ssua      (11),
                        ssub      (12),
                        sec       (13),
                     -- dnu    (14)
                     -- inv    (15)
                     -- pno    (16)
                        eec1      (17),
                        eec2      (18)
                        -- failed (19)
                    }
            DESCRIPTION
                    "The tSyncIfTimingAdmRef2CfgQltyLevel does not support the
                     values 'smc (7)', 'st4 (8)', 'dus (9)', 'dnu (14)',
                     'inc (15)', 'pno (16)', or 'failed (19)'."

        VARIATION   tSyncIfTimingAdmBITSCfgQltyLevel
            SYNTAX  TmnxSSMQualityLevel {
                        unknown    (0),
                        prs        (1),
                        stu        (2),
                        st2        (3),
                        tnc        (4),
                        st3e       (5),
                        st3        (6),
                     -- smc     (7)
                     -- st4     (8)
                     -- dus     (9)
                        prc       (10),
                        ssua      (11),
                        ssub      (12),
                        sec       (13),
                     -- dnu    (14)
                     -- inv    (15)
                     -- pno    (16)
                        eec1      (17),
                        eec2      (18)
                        -- failed (19)
                    }
            DESCRIPTION
                    "The tSyncIfTimingAdmBITSCfgQltyLevel does not support the
                     values 'smc (7)', 'st4 (8)', 'dus (9)', 'dnu (14)',
                     'inc (15)', 'pno (16)', or 'failed (19)'."

        VARIATION   tmnxHwLastAlarmEvent
            DESCRIPTION
                    "tmnxHwLastAlarmEvent is not supported on Alcatel-Lucent
                     SROS systems. The value of tmnxHwLastAlarmEvent is always
                     '0.0'."

    ::= { tmnxSROSV10v0 6 }  -- CHASSIS

tmnx7750ChassisCapsV10v0    AGENT-CAPABILITIES
    PRODUCT-RELEASE "Alcatel-Lucent SROS"
    STATUS          current
    DESCRIPTION     "Implementation of specific CHASSIS or hardware
                     capabilities for Alcatel-Lucent SROS 7750 release R10.0"

    SUPPORTS        TIMETRA-CHASSIS-MIB
        INCLUDES    {
            tmnx77x0CESMDAV6v0Group,
            tmnxCardV6v0NamedPoolPlcyGroup,
            tmnxChassisV5v0Group,
            tmnxFPMcPathMgmtV6v1Group,
            tmnxFPWredV7v0Group,
            tmnxIPsecIsaGrpV6v0Group,
            tmnxMDACcagV6v1Group,
            tmnxMDAMcPathMgmtV6v0Group,
            tmnxSyncIfTimingV9v0Group
        }

        VARIATION   tmnxIPsecIsaGrpRowStatus
            SYNTAX  INTEGER {
                        active      (1),
                        createAndGo (4),
                        destroy     (6)
                     }
            DESCRIPTION
                    "The tmnxIPsecIsaGrpRowStatus supports only the values
                    'active (1)', 'createAndGo (4)' and 'destroy (6)'."

        VARIATION   tmnxIPsecIsaGrpAdminState
            SYNTAX  INTEGER {
                        -- noop         (1),
                        inService       (2),
                        outOfService    (3)
                    }
            DESCRIPTION
                    "The tmnxIPsecIsaGrpAdminState supports only the values
                     'inService (2)' and 'outOfService (3)'."

        VARIATION   tmnxIPsecIsaGrpIsaChassis
            DESCRIPTION
                    "The tmnxIPsecIsaGrpIsaChassis supports only the value 1.
                     An attempt to set it to any other value results in
                     a 'wrongValue' error."

        VARIATION   tSyncIfTimingAdmBITSIfType
            SYNTAX  TmnxBITSIfType {
                        -- none (0),
                        t1-esf (1),
                        t1-sf (2),
                        e1-pcm30crc (3),
                        e1-pcm31crc (4)
                    }
            DESCRIPTION
                    "tSyncIfTimingAdmBITSIfType does not support the value
                     'none (0).'"

        VARIATION   tSyncIfTimingAdmRef1BITSIfType
            SYNTAX  TmnxBITSIfType {
                        -- none (0),
                        t1-esf (1),
                        t1-sf (2),
                        e1-pcm30crc (3),
                        e1-pcm31crc (4)
                    }
            DESCRIPTION
                    "tSyncIfTimingAdmRef1BITSIfType does not support the value
                     'none (0).'"

        VARIATION   tSyncIfTimingAdmRef2BITSIfType
            SYNTAX  TmnxBITSIfType {
                        -- none (0),
                        t1-esf (1),
                        t1-sf (2),
                        e1-pcm30crc (3),
                        e1-pcm31crc (4)
                    }
            DESCRIPTION
                    "tSyncIfTimingAdmRef2BITSIfType does not support the value
                     'none (0).'"

        VARIATION    tSyncIfTimingAdmRef1NationalUse
            ACCESS   not-implemented
            DESCRIPTION
                    "tSyncIfTimingAdmRef1NationalUse is not implemented on
                     SROS 7750 systems."

        VARIATION    tSyncIfTimingAdmRef2NationalUse
            ACCESS   not-implemented
            DESCRIPTION
                    "tSyncIfTimingAdmRef2NationalUse is not implemented on
                     SROS 7750 systems."

        VARIATION    tmnxSyncIfTimingRef1NationalUse
            ACCESS   not-implemented
            DESCRIPTION
                    "tmnxSyncIfTimingRef1NationalUse is not implemented on
                     SROS 7750 systems."

        VARIATION    tmnxSyncIfTimingRef2NationalUse
            ACCESS   not-implemented
            DESCRIPTION
                    "tmnxSyncIfTimingRef2NationalUse is not implemented on
                     SROS 7750 systems."

        VARIATION   tmnxSyncIfTimingBITS2InUse
            ACCESS  not-implemented
            DESCRIPTION
                    "tmnxSyncIfTimingBITS2InUse is not implemented on
                     SROS 7750 systems."

        VARIATION   tmnxSyncIfTimingBITS2Qualified
            ACCESS  not-implemented
            DESCRIPTION
                    "tmnxSyncIfTimingBITS2Qualified is not implemented on
                     SROS 7750 systems."

        VARIATION   tmnxSyncIfTimingBITS2Alarm
            ACCESS  not-implemented
            DESCRIPTION
                    "tmnxSyncIfTimingBITS2Alarm is not implemented on
                     SROS 7750 systems."

        VARIATION   tmnxSyncIfTimingBITS2RxQltyLevel
            ACCESS  not-implemented
            DESCRIPTION
                    "tmnxSyncIfTimingBITS2RxQltyLevel is not implemented on
                     SROS 7750 systems."

        VARIATION   tmnxSyncIfTimingBITS2State
            ACCESS  not-implemented
            DESCRIPTION
                    "tmnxSyncIfTimingBITS2State is not implemented on
                     SROS 7750 systems."

        VARIATION   tmnxSyncIfTimingBITS2AdminStatus
            ACCESS  not-implemented
            DESCRIPTION
                    "tmnxSyncIfTimingBITS2AdminStatus is not implemented on
                     SROS 7750 systems."

        VARIATION   tmnxSyncIfTimingRefOrder4
            DESCRIPTION
                    "tmnxSyncIfTimingRefOrder4 is only supported on
                     Alcatel-Lucent SROS systems with an active CPM3/SFM3 and on
                     7750-c4 systems. Otherwise, this object is
                     not-implemented."

        VARIATION   tSyncIfTimingAdmRefOrder4
            DESCRIPTION
                    "tSyncIfTimingAdmRefOrder4 is only supported on
                     Alcatel-Lucent SROS systems with an active CPM3/SFM3 and on
                     7750-c4 systems. Otherwise, this object is
                     not-implemented."

        VARIATION   tmnxSyncIfTimingPTPAdminStatus
            DESCRIPTION
                    "tmnxSyncIfTimingPTPAdminStatus is only supported on
                     Alcatel-Lucent SROS systems with an active CPM3/SFM3."

        VARIATION   tSyncIfTimingAdmPTPAdminStatus
            DESCRIPTION
                    "tSyncIfTimingAdmPTPAdminStatus is only supported on
                     Alcatel-Lucent SROS systems with an active CPM3/SFM3."

        VARIATION   tmnxSyncIfTimingPTPInUse
            DESCRIPTION
                    "tmnxSyncIfTimingPTPInUse is only supported on
                     Alcatel-Lucent SROS systems with an active CPM3/SFM3."

        VARIATION   tmnxSyncIfTimingPTPQualified
            DESCRIPTION
                    "tmnxSyncIfTimingPTPQualified is only supported on
                     Alcatel-Lucent SROS systems with an active CPM3/SFM3."

        VARIATION   tmnxSyncIfTimingPTPAlarm
            DESCRIPTION
                    "tmnxSyncIfTimingPTPAlarm is only supported on
                     Alcatel-Lucent SROS systems with an active CPM3/SFM3."

        VARIATION   tmnxSyncIfTimingPTPCfgQltyLevel
            DESCRIPTION
                    "tmnxSyncIfTimingPTPCfgQltyLevel is only supported on
                     Alcatel-Lucent SROS systems with an active CPM3/SFM3."

        VARIATION   tSyncIfTimingAdmPTPCfgQltyLevel
            DESCRIPTION
                    "tSyncIfTimingAdmPTPCfgQltyLevel is only supported on
                     Alcatel-Lucent SROS systems with an active CPM3/SFM3."

        VARIATION   tmnxSyncIfTimingPTPRxQltyLevel
            DESCRIPTION
                    "tmnxSyncIfTimingPTPRxQltyLevel is only supported on
                     Alcatel-Lucent SROS systems with an active CPM3/SFM3."

        VARIATION   tmnxSyncIfTimingPTPState
            DESCRIPTION
                    "tmnxSyncIfTimingPTPState is only supported on
                     Alcatel-Lucent SROS systems with an active CPM3/SFM3."

        VARIATION   tmnxEqSyncIfTimingPTPQuality
            DESCRIPTION
                    "tmnxEqSyncIfTimingPTPQuality is only supported on
                     Alcatel-Lucent SROS systems with an active CPM3/SFM3."

        VARIATION   tmnxEqSyncIfTimingPTPAlarm
            DESCRIPTION
                    "tmnxEqSyncIfTimingPTPAlarm is only supported on
                     Alcatel-Lucent SROS systems with an active CPM3/SFM3."

        VARIATION   tmnxEqSyncIfTimingPTPAlarmClear
            DESCRIPTION
                    "tmnxEqSyncIfTimingPTPAlarmClear is only supported on
                     Alcatel-Lucent SROS systems with an active CPM3/SFM3."

    ::= { tmnxSROSChassisCapsV10v0 1 }  -- 7750 CHASSIS

tmnx7450ChassisCapsV10v0    AGENT-CAPABILITIES
    PRODUCT-RELEASE "Alcatel-Lucent SROS"
    STATUS          current
    DESCRIPTION     "Implementation of specific CHASSIS or hardware
                     capabilities for Alcatel-Lucent SROS 7450 release R10.0"

    SUPPORTS        TIMETRA-CHASSIS-MIB
        INCLUDES    {
            tmnxCardV6v0NamedPoolPlcyGroup,
            tmnxChassisMixedModeIomV8v0Group,
            tmnxChassisV5v0Group,
            tmnxFPMcPathMgmtV6v1Group,
            tmnxFPWredV7v0Group,
            tmnxIPsecIsaGrpV6v0Group,
            tmnxMDACcagV6v1Group,
            tmnxMDAMcPathMgmtV6v0Group,
            tmnxSyncIfTimingV9v0Group
        }

        VARIATION   tmnxChassisAdminMode
            SYNTAX  INTEGER {
                        modeA     (1),
                        modeB     (2),
                     -- modeC  (3)      - No modeC on 7450
                        modeD     (4)
                    }
            DESCRIPTION
                    "The value 'modeC (3)' is invalid on a 7450 system,
                    because scaling and features corresponding to the
                    IOM2-20g card are not supported on Alcatel-lucent
                    SROS 7450 systems."

        VARIATION   tSyncIfTimingAdmBITSIfType
            SYNTAX  TmnxBITSIfType {
                     -- none        (0)
                        t1-esf (1),
                        t1-sf (2),
                        e1-pcm30crc (3),
                        e1-pcm31crc (4)
                    }
            DESCRIPTION
                    "tSyncIfTimingAdmBITSIfType does not support the value
                     'none (0).'"

        VARIATION   tSyncIfTimingAdmRef1BITSIfType
            SYNTAX  TmnxBITSIfType {
                     -- none        (0)
                        t1-esf (1),
                        t1-sf (2),
                        e1-pcm30crc (3),
                        e1-pcm31crc (4)
                    }
            DESCRIPTION
                    "tSyncIfTimingAdmRef1BITSIfType does not support the value
                     'none (0).'"

        VARIATION   tSyncIfTimingAdmRef2BITSIfType
            SYNTAX  TmnxBITSIfType {
                     -- none        (0)
                        t1-esf (1),
                        t1-sf (2),
                        e1-pcm30crc (3),
                        e1-pcm31crc (4)
                    }
            DESCRIPTION
                    "tSyncIfTimingAdmRef2BITSIfType does not support the value
                     'none (0).'"

        VARIATION    tSyncIfTimingAdmRef1NationalUse
            ACCESS   not-implemented
            DESCRIPTION
                    "tSyncIfTimingAdmRef1NationalUse is not implemented on
                     SROS 7450 systems."

        VARIATION    tSyncIfTimingAdmRef2NationalUse
            ACCESS   not-implemented
            DESCRIPTION
                    "tSyncIfTimingAdmRef2NationalUse is not implemented on
                     SROS 7450 systems."

        VARIATION    tmnxSyncIfTimingRef1NationalUse
            ACCESS   not-implemented
            DESCRIPTION
                    "tmnxSyncIfTimingRef1NationalUse is not implemented on
                     SROS 7450 systems."

        VARIATION    tmnxSyncIfTimingRef2NationalUse
            ACCESS   not-implemented
            DESCRIPTION
                    "tmnxSyncIfTimingRef2NationalUse is not implemented on
                     SROS 7450 systems."

        VARIATION   tmnxSyncIfTimingBITS2InUse
            ACCESS  not-implemented
            DESCRIPTION
                    "tmnxSyncIfTimingBITS2InUse is not implemented on
                     SROS 7450 systems."

        VARIATION   tmnxSyncIfTimingBITS2Qualified
            ACCESS  not-implemented
            DESCRIPTION
                    "tmnxSyncIfTimingBITS2Qualified is not implemented on
                     SROS 7450 systems."

        VARIATION   tmnxSyncIfTimingBITS2Alarm
            ACCESS  not-implemented
            DESCRIPTION
                    "tmnxSyncIfTimingBITS2Alarm is not implemented on
                     SROS 7450 systems."

        VARIATION   tmnxSyncIfTimingBITS2RxQltyLevel
            ACCESS  not-implemented
            DESCRIPTION
                    "tmnxSyncIfTimingBITS2RxQltyLevel is not implemented on
                     SROS 7450 systems."

        VARIATION   tmnxSyncIfTimingBITS2State
            ACCESS  not-implemented
            DESCRIPTION
                    "tmnxSyncIfTimingBITS2State is not implemented on
                     SROS 7450 systems."

        VARIATION   tmnxSyncIfTimingBITS2AdminStatus
            ACCESS  not-implemented
            DESCRIPTION
                    "tmnxSyncIfTimingBITS2AdminStatus is not implemented on
                     SROS 7450 systems."

        VARIATION   tmnxSyncIfTimingRefOrder4
            DESCRIPTION
                    "tmnxSyncIfTimingRefOrder4 is only supported on
                     Alcatel-Lucent SROS systems with an active CPM3/SFM3."

        VARIATION   tSyncIfTimingAdmRefOrder4
            DESCRIPTION
                    "tSyncIfTimingAdmRefOrder4 is only supported on
                     Alcatel-Lucent SROS systems with an active CPM3/SFM3."

        VARIATION   tmnxSyncIfTimingPTPAdminStatus
            DESCRIPTION
                    "tmnxSyncIfTimingPTPAdminStatus is only supported on
                     Alcatel-Lucent SROS systems with an active CPM3/SFM3."

        VARIATION   tSyncIfTimingAdmPTPAdminStatus
            DESCRIPTION
                    "tSyncIfTimingAdmPTPAdminStatus is only supported on
                     Alcatel-Lucent SROS systems with an active CPM3/SFM3."

        VARIATION   tmnxSyncIfTimingPTPInUse
            DESCRIPTION
                    "tmnxSyncIfTimingPTPInUse is only supported on
                     Alcatel-Lucent SROS systems with an active CPM3/SFM3."

        VARIATION   tmnxSyncIfTimingPTPQualified
            DESCRIPTION
                    "tmnxSyncIfTimingPTPQualified is only supported on
                     Alcatel-Lucent SROS systems with an active CPM3/SFM3."

        VARIATION   tmnxSyncIfTimingPTPAlarm
            DESCRIPTION
                    "tmnxSyncIfTimingPTPAlarm is only supported on
                     Alcatel-Lucent SROS systems with an active CPM3/SFM3."

        VARIATION   tmnxSyncIfTimingPTPCfgQltyLevel
            DESCRIPTION
                    "tmnxSyncIfTimingPTPCfgQltyLevel is only supported on
                     Alcatel-Lucent SROS systems with an active CPM3/SFM3."

        VARIATION   tSyncIfTimingAdmPTPCfgQltyLevel
            DESCRIPTION
                    "tSyncIfTimingAdmPTPCfgQltyLevel is only supported on
                     Alcatel-Lucent SROS systems with an active CPM3/SFM3."

        VARIATION   tmnxSyncIfTimingPTPRxQltyLevel
            DESCRIPTION
                    "tmnxSyncIfTimingPTPRxQltyLevel is only supported on
                     Alcatel-Lucent SROS systems with an active CPM3/SFM3."

        VARIATION   tmnxSyncIfTimingPTPState
            DESCRIPTION
                    "tmnxSyncIfTimingPTPState is only supported on
                     Alcatel-Lucent SROS systems with an active CPM3/SFM3."

        VARIATION   tmnxEqSyncIfTimingPTPQuality
            DESCRIPTION
                    "tmnxEqSyncIfTimingPTPQuality is only supported on
                     Alcatel-Lucent SROS systems with an active CPM3/SFM3."

        VARIATION   tmnxEqSyncIfTimingPTPAlarm
            DESCRIPTION
                    "tmnxEqSyncIfTimingPTPAlarm is only supported on
                     Alcatel-Lucent SROS systems with an active CPM3/SFM3."

        VARIATION   tmnxEqSyncIfTimingPTPAlarmClear
            DESCRIPTION
                    "tmnxEqSyncIfTimingPTPAlarmClear is only supported on
                     Alcatel-Lucent SROS systems with an active CPM3/SFM3."

    ::= { tmnxSROSChassisCapsV10v0 2 }  -- 7450 CHASSIS

tmnxSprChassisCapsV10v0    AGENT-CAPABILITIES
    PRODUCT-RELEASE "Alcatel-Lucent SROS"
    STATUS          current
    DESCRIPTION     "Implementation of specific CHASSIS or hardware
                     capabilities for Alcatel-Lucent SROS SPR products, release
                     R9.0"

    SUPPORTS        TIMETRA-CHASSIS-MIB
        INCLUDES    {
            tmnxChassisV5v0Group,
            tmnxCardV3v0Group,
            tmnx77x0CESMDAV6v0Group,
            tmnx7710HwV3v0Group,
            tmnx7710SETSRefSrcHwV6v0Group
        }

        VARIATION   tSyncIfTimingAdmRef1BITSIfType
            SYNTAX  TmnxBITSIfType {
                     -- none        (0)
                        t1-esf (1),
                        t1-sf (2),
                        e1-pcm30crc (3),
                        e1-pcm31crc (4)
                    }
            DESCRIPTION
                    "tSyncIfTimingAdmRef1BITSIfType does not support the value
                     'none (0).'"

        VARIATION   tSyncIfTimingAdmRef2BITSIfType
            SYNTAX  TmnxBITSIfType {
                     -- none        (0)
                        t1-esf (1),
                        t1-sf (2),
                        e1-pcm30crc (3),
                        e1-pcm31crc (4)
                    }
            DESCRIPTION
                    "tSyncIfTimingAdmRef2BITSIfType does not support the value
                     'none (0).'"

        VARIATION   tSyncIfTimingAdmRefOrder1
            SYNTAX  INTEGER {
                        reference1 (1),
                        reference2 (2)
                     -- bits        (3)
                     -- bits2       (4)
                     -- ptp         (5)
                        -- noReference (6)
                    }
            DEFVAL  { reference1 }
            DESCRIPTION
                    "The only values supported for tSyncIfTimingAdmRefOrder1
                     on SROS SPR systems are 'reference1 (1)' and
                     'reference2 (2)'.

                     An attempt to set
                     tSyncIfTimingAdmRefOrder1 to the value 'bits (3)' will
                     result in a 'wrongValue' error. The default Value is
                     'reference1' instead of 'bits'."

        VARIATION   tSyncIfTimingAdmRefOrder2
            SYNTAX  INTEGER {
                        reference1 (1),
                        reference2 (2)
                     -- bits        (3)
                     -- bits2       (4)
                     -- ptp         (5)
                        -- noReference (6)
                    }
            DEFVAL  { reference2 }
            DESCRIPTION
                    "The only values supported for tSyncIfTimingAdmRefOrder2
                     on SROS SPR systems are 'reference1 (1)' and
                     'reference2 (2)'.

                     An attempt to set
                     tSyncIfTimingAdmRefOrder2 to the value 'bits (3)' will
                     result in a 'wrongValue' error. The default Value is
                     'reference2' instead of 'bits'."

        VARIATION   tSyncIfTimingAdmRefOrder3
            ACCESS  not-implemented
            DESCRIPTION
                    "tSyncIfTimingAdmRefOrder3 is not implemented on
                     SROS SPR systems."

        VARIATION   tmnxSyncIfTimingRefOrder3
            ACCESS  not-implemented
            DESCRIPTION
                    "tmnxSyncIfTimingRefOrder3 is not implemented on
                     SROS SPR systems."

        VARIATION   tSyncIfTimingAdmRefOrder4
            ACCESS  not-implemented
            DESCRIPTION
                    "tSyncIfTimingAdmRefOrder4 is not implemented on
                     SROS SPR systems."

        VARIATION   tmnxSyncIfTimingRefOrder4
            ACCESS  not-implemented
            DESCRIPTION
                    "tmnxSyncIfTimingRefOrder4 is not implemented on
                     SROS SPR systems."

        VARIATION   tmnxMDAIngNamedPoolPolicy
           ACCESS   not-implemented
           DESCRIPTION
                    "tmnxMDAIngNamedPoolPolicy is not implemented on
                     SROS SPR systems."

        VARIATION   tmnxMDAEgrNamedPoolPolicy
            ACCESS  not-implemented
            DESCRIPTION
                    "tmnxMDAEgrNamedPoolPolicy is not implemented on
                     SROS SPR systems."

    ::= { tmnxSROSChassisCapsV10v0 3 }  -- SPR CHASSIS

tmnx7750cChassisCapsV10v0    AGENT-CAPABILITIES
    PRODUCT-RELEASE "Alcatel-Lucent SROS"
    STATUS          current
    DESCRIPTION
        "Implementation of specific CHASSIS or hardware
         capabilities for Alcatel-Lucent SROS 7750c products,
         release R10.0"

    SUPPORTS        TIMETRA-CHASSIS-MIB
        INCLUDES    {
            tmnxChassisV5v0Group,
            tmnxChassisV7v0Group,
            tmnxFPWredV7v0Group,
            tmnxSyncIfTimingV9v0Group
        }

        VARIATION   tmnxChassisAdminMode
            SYNTAX  TmnxChassisMode {
                        -- modeA   (1)
                        -- modeB   (2)
                        -- modeC   (3)
                           modeD   (4)
                    }
            DESCRIPTION
                "The only value supported for tmnxChassisAdminMode on
                 SROS 7750c systems is 'modeD(4)'."

        VARIATION   tmnxSyncIfTimingRef1SrcHw
            DESCRIPTION
                    "tmnxSyncIfTimingRef1SrcHw is not implemented on
                     SROS 7750-c4 systems."

        VARIATION   tmnxSyncIfTimingRef1BITSIfType
            DESCRIPTION
                    "tmnxSyncIfTimingRef1BITSIfType is not implemented on
                     SROS 7750-c4 systems."

        VARIATION   tmnxSyncIfTimingRef2SrcHw
            DESCRIPTION
                    "tmnxSyncIfTimingRef2SrcHw is not implemented on
                     SROS 7750-c4 systems."

        VARIATION   tmnxSyncIfTimingRef2BITSIfType
            DESCRIPTION
                    "tmnxSyncIfTimingRef2BITSIfType is not implemented on
                     SROS 7750-c4 systems."

        VARIATION   tSyncIfTimingAdmRef1SrcHw
            DESCRIPTION
                    "tSyncIfTimingAdmRef1SrcHw is not implemented on
                     SROS 7750-c4 systems."

        VARIATION   tSyncIfTimingAdmRef1BITSIfType
            DESCRIPTION
                    "tSyncIfTimingAdmRef1BITSIfType is not implemented on
                     SROS 7750-c4 systems."

        VARIATION   tSyncIfTimingAdmRef2SrcHw
            DESCRIPTION
                    "tSyncIfTimingAdmRef2SrcHw is not implemented on
                     SROS 7750-c4 systems."

        VARIATION   tSyncIfTimingAdmRef2BITSIfType
            DESCRIPTION
                    "tSyncIfTimingAdmRef2BITSIfType is not implemented on
                     SROS 7750-c4 systems."

        VARIATION    tSyncIfTimingAdmBITSNationalUse
            DESCRIPTION
                    "tSyncIfTimingAdmBITSNationalUse is only implemented on
                     SROS 7750-c4 systems."

        VARIATION    tmnxSyncIfTimingBITSNationalUse
            DESCRIPTION
                    "tmnxSyncIfTimingBITSNationalUse is only implemented on
                     SROS 7750-c4 systems."

        VARIATION   tmnxSyncIfTimingBITS2InUse
            DESCRIPTION
                    "tmnxSyncIfTimingBITS2InUse is only implemented on
                     SROS 7750-c4 systems."

        VARIATION   tmnxSyncIfTimingBITS2Qualified
            DESCRIPTION
                    "tmnxSyncIfTimingBITS2Qualified is only implemented on
                     SROS 7750-c4 systems."

        VARIATION   tmnxSyncIfTimingBITS2Alarm
            DESCRIPTION
                    "tmnxSyncIfTimingBITS2Alarm is only implemented on
                     SROS 7750-c4 systems."

        VARIATION   tmnxSyncIfTimingBITS2RxQltyLevel
            DESCRIPTION
                    "tmnxSyncIfTimingBITS2RxQltyLevel is only implemented on
                     SROS 7750-c4 systems."

        VARIATION   tmnxSyncIfTimingBITS2State
            DESCRIPTION
                    "tmnxSyncIfTimingBITS2State is only implemented on
                     SROS 7750-c4 systems."

        VARIATION    tmnxSyncIfTimingBITSTxQltyLevel
            DESCRIPTION
                    "tmnxSyncIfTimingBITSTxQltyLevel is only implemented on
                     SROS 7750-c4 systems."

        VARIATION   tmnxSyncIfTimingBITS2AdminStatus
            DESCRIPTION
                    "tmnxSyncIfTimingBITS2AdminStatus is only implemented on
                     SROS 7750-c4 systems."

        VARIATION   tmnxSyncIfTimingRefOrder4
            DESCRIPTION
                    "tmnxSyncIfTimingRefOrder4 is only supported on
                     Alcatel-Lucent SROS systems with an active CPM3/SFM3 and on
                     7750-c4 systems. Otherwise, this object is
                     not-implemented."

        VARIATION   tSyncIfTimingAdmRefOrder4
            DESCRIPTION
                    "tSyncIfTimingAdmRefOrder4 is only supported on
                     Alcatel-Lucent SROS systems with an active CPM3/SFM3 and on
                     7750-c4 systems. Otherwise, this object is
                     not-implemented."

        VARIATION   tmnxSyncIfTimingPTPAdminStatus
            DESCRIPTION
                    "tmnxSyncIfTimingPTPAdminStatus is only supported on
                     Alcatel-Lucent 7750-c4 systems."

        VARIATION   tSyncIfTimingAdmPTPAdminStatus
            DESCRIPTION
                    "tSyncIfTimingAdmPTPAdminStatus is only supported on
                     Alcatel-Lucent 7750-c4 systems."

        VARIATION   tmnxSyncIfTimingPTPInUse
            DESCRIPTION
                    "tmnxSyncIfTimingPTPInUse is only supported on
                     Alcatel-Lucent 7750-c4 systems."

        VARIATION   tmnxSyncIfTimingPTPQualified
            DESCRIPTION
                    "tmnxSyncIfTimingPTPQualified is only supported on
                     Alcatel-Lucent 7750-c4 systems."

        VARIATION   tmnxSyncIfTimingPTPAlarm
            DESCRIPTION
                    "tmnxSyncIfTimingPTPAlarm is only supported on
                     Alcatel-Lucent 7750-c4 systems."

        VARIATION   tmnxSyncIfTimingPTPCfgQltyLevel
            DESCRIPTION
                    "tmnxSyncIfTimingPTPCfgQltyLevel is only supported on
                     Alcatel-Lucent 7750-c4 systems."

        VARIATION   tSyncIfTimingAdmPTPCfgQltyLevel
            DESCRIPTION
                    "tSyncIfTimingAdmPTPCfgQltyLevel is only supported on
                     Alcatel-Lucent 7750-c4 systems."

        VARIATION   tmnxSyncIfTimingPTPRxQltyLevel
            DESCRIPTION
                    "tmnxSyncIfTimingPTPRxQltyLevel is only supported on
                     Alcatel-Lucent 7750-c4 systems."

        VARIATION   tmnxSyncIfTimingPTPState
            DESCRIPTION
                    "tmnxSyncIfTimingPTPState is only supported on
                     Alcatel-Lucent 7750-c4 systems."

        VARIATION   tmnxEqSyncIfTimingPTPQuality
            DESCRIPTION
                    "tmnxEqSyncIfTimingPTPQuality is only supported on
                     Alcatel-Lucent 7750-c4 systems."

        VARIATION   tmnxEqSyncIfTimingPTPAlarm
            DESCRIPTION
                    "tmnxEqSyncIfTimingPTPAlarm is only supported on
                     Alcatel-Lucent 7750-c4 systems."

        VARIATION   tmnxEqSyncIfTimingPTPAlarmClear
            DESCRIPTION
                    "tmnxEqSyncIfTimingPTPAlarmClear is only supported on
                     Alcatel-Lucent 7750-c4 systems."

    ::= { tmnxSROSChassisCapsV10v0 4 }  -- 7750c CHASSIS

tmnx7710ChassisCapsV10v0    AGENT-CAPABILITIES
    PRODUCT-RELEASE "Alcatel-Lucent SROS"
    STATUS          current
    DESCRIPTION     "Implementation of specific CHASSIS or hardware
                     capabilities for Alcatel-Lucent SROS 7710 products,
                     release R10.0"

    SUPPORTS        TIMETRA-CHASSIS-MIB
        INCLUDES    {
            tmnxChassisV5v0Group,
            tmnxSyncIfTimingV9v0Group
        }

        VARIATION   tmnxChassisAdminMode
            SYNTAX  TmnxChassisMode {
                        -- modeA   (1)
                        -- modeB   (2)
                           modeC   (3)
                        -- modeD   (4)
                    }
            DESCRIPTION
                "The only value supported for tmnxChassisAdminMode on
                 SROS 7710 systems is 'modeC(3)'."

        VARIATION    tSyncIfTimingAdmBITSNationalUse
            ACCESS   not-implemented
            DESCRIPTION
                    "tSyncIfTimingAdmBITSNationalUse is not implemented on
                     SROS 7710 systems."

        VARIATION    tmnxSyncIfTimingBITSNationalUse
            ACCESS   not-implemented
            DESCRIPTION
                    "tmnxSyncIfTimingBITSNationalUse is not implemented on
                     SROS 7710 systems."

        VARIATION   tmnxSyncIfTimingBITS2InUse
            ACCESS  not-implemented
            DESCRIPTION
                    "tmnxSyncIfTimingBITS2InUse is not implemented on
                     SROS 7710 systems."

        VARIATION   tmnxSyncIfTimingBITS2Qualified
            ACCESS  not-implemented
            DESCRIPTION
                    "tmnxSyncIfTimingBITS2Qualified is not implemented on
                     SROS 7710 systems."

        VARIATION   tmnxSyncIfTimingBITS2Alarm
            ACCESS  not-implemented
            DESCRIPTION
                    "tmnxSyncIfTimingBITS2Alarm is not implemented on
                     SROS 7710 systems."

        VARIATION   tmnxSyncIfTimingBITS2RxQltyLevel
            ACCESS  not-implemented
            DESCRIPTION
                    "tmnxSyncIfTimingBITS2RxQltyLevel is not implemented on
                     SROS 7710 systems."

        VARIATION   tmnxSyncIfTimingBITS2State
            ACCESS  not-implemented
            DESCRIPTION
                    "tmnxSyncIfTimingBITS2State is not implemented on
                     SROS 7710 systems."

        VARIATION   tmnxSyncIfTimingBITS2AdminStatus
            ACCESS  not-implemented
            DESCRIPTION
                    "tmnxSyncIfTimingBITS2AdminStatus is not implemented on
                     SROS 7710 systems."

        VARIATION    tmnxSyncIfTimingBITSTxQltyLevel
            ACCESS   not-implemented
            DESCRIPTION
                    "tmnxSyncIfTimingBITSTxQltyLevel is not implemented on
                     SROS 7710 systems."

        VARIATION   tSyncIfTimingAdmBITSCfgQltyLevel
            ACCESS  not-implemented
            DESCRIPTION
                    "tSyncIfTimingAdmBITSCfgQltyLevel is not implemented on
                     SROS 7710 systems."

        VARIATION   tSyncIfTimingAdmBITSOutAdmStatus
            ACCESS  not-implemented
            DESCRIPTION
                    "tSyncIfTimingAdmBITSOutAdmStatus is not implemented on
                     SROS 7710 systems."

        VARIATION   tSyncIfTimingAdmBITSOutLineLen
            ACCESS  not-implemented
            DESCRIPTION
                    "tSyncIfTimingAdmBITSOutLineLen is not implemented on
                     SROS 7710 systems."

        VARIATION   tSyncIfTimingAdmBITSOutSource
            ACCESS  not-implemented
            DESCRIPTION
                    "tSyncIfTimingAdmBITSOutSource is not implemented on
                     SROS 7710 systems."

        VARIATION   tmnxSyncIfTimingBITSCfgQltyLevel
            ACCESS  not-implemented
            DESCRIPTION
                    "tmnxSyncIfTimingBITSCfgQltyLevel is not implemented on
                     SROS 7710 systems."

        VARIATION   tmnxSyncIfTimingBITSOutAdmStatus
            ACCESS  not-implemented
            DESCRIPTION
                    "tmnxSyncIfTimingBITSOutAdmStatus is not implemented on
                     SROS 7710 systems."

        VARIATION   tmnxSyncIfTimingBITSOutLineLen
            ACCESS  not-implemented
            DESCRIPTION
                    "tmnxSyncIfTimingBITSOutLineLen is not implemented on
                     SROS 7710 systems."

        VARIATION   tmnxSyncIfTimingBITSOutRefSel
            ACCESS  not-implemented
            DESCRIPTION
                    "tmnxSyncIfTimingBITSOutRefSel is not implemented on
                     SROS 7710 systems."

        VARIATION   tmnxSyncIfTimingBITSOutSource
            ACCESS  not-implemented
            DESCRIPTION
                    "tmnxSyncIfTimingBITSOutSource is not implemented on
                     SROS 7710 systems."

        VARIATION   tmnxSyncIfTimingBITSRxQltyLevel
            ACCESS  not-implemented
            DESCRIPTION
                    "tmnxSyncIfTimingBITSRxQltyLevel is not implemented on
                     SROS 7710 systems."

    ::= { tmnxSROSChassisCapsV10v0 5 }  -- 7710 CHASSIS

 tmnx7950ChassisCapsV10v0    AGENT-CAPABILITIES
    PRODUCT-RELEASE "Alcatel-Lucent SROS"
    STATUS          current
    DESCRIPTION
        "Implementation of specific CHASSIS or hardware
         capabilities for Alcatel-Lucent SROS 7950 products,
         release R10.0"

    SUPPORTS        TIMETRA-CHASSIS-MIB
        INCLUDES    {
            tmnxChassisV5v0Group,
            tmnxChassisV10v0Group,
            tmnxSyncIfTimingV9v0Group
        }

        VARIATION   tmnxChassisAdminMode
            SYNTAX  TmnxChassisMode {
                     -- modeA   (1)
                     -- modeB   (2)
                     -- modeC   (3)
                        modeD   (4)
                    }
            DESCRIPTION
                    "The only value supported for tmnxChassisAdminMode on
                     SROS 7950 systems is 'modeD(4)'."

        VARIATION   tmnxChassisPowerSupplyAssignedType
            DESCRIPTION
                    "tmnxChassisPowerSupplyAssignedType is not implemented on
                     Alcatel-Lucent 7950 systems."

        VARIATION   tmnxSyncIfTimingPTPAdminStatus
            DESCRIPTION
                    "tmnxSyncIfTimingPTPAdminStatus is not implemented on
                     Alcatel-Lucent 7950 systems."

        VARIATION   tSyncIfTimingAdmPTPAdminStatus
            DESCRIPTION
                    "tSyncIfTimingAdmPTPAdminStatus is not implemented on
                     Alcatel-Lucent 7950 systems."

        VARIATION   tmnxSyncIfTimingPTPInUse
            DESCRIPTION
                    "tmnxSyncIfTimingPTPInUse is not implemented on
                     Alcatel-Lucent 7950 systems."

        VARIATION   tmnxSyncIfTimingPTPQualified
            DESCRIPTION
                    "tmnxSyncIfTimingPTPQualified is not implemented on
                     Alcatel-Lucent 7950 systems."

        VARIATION   tmnxSyncIfTimingPTPAlarm
            DESCRIPTION
                    "tmnxSyncIfTimingPTPAlarm is not implemented on
                     Alcatel-Lucent 7950 systems."

        VARIATION   tmnxSyncIfTimingPTPCfgQltyLevel
            DESCRIPTION
                    "tmnxSyncIfTimingPTPCfgQltyLevel is not implemented on
                     Alcatel-Lucent 7950 systems."

        VARIATION   tSyncIfTimingAdmPTPCfgQltyLevel
            DESCRIPTION
                    "tSyncIfTimingAdmPTPCfgQltyLevel is not implemented on
                     Alcatel-Lucent 7950 systems."

        VARIATION   tmnxSyncIfTimingPTPRxQltyLevel
            DESCRIPTION
                    "tmnxSyncIfTimingPTPRxQltyLevel is not implemented on
                     Alcatel-Lucent 7950 systems."

        VARIATION   tmnxSyncIfTimingPTPState
            DESCRIPTION
                    "tmnxSyncIfTimingPTPState is not implemented on
                     Alcatel-Lucent 7950 systems."

        VARIATION   tmnxEqSyncIfTimingPTPQuality
            DESCRIPTION
                    "tmnxEqSyncIfTimingPTPQuality is not implemented on
                     Alcatel-Lucent 7950 systems."

        VARIATION   tmnxEqSyncIfTimingPTPAlarm
            DESCRIPTION
                    "tmnxEqSyncIfTimingPTPAlarm is not implemented on
                     Alcatel-Lucent 7950 systems."

        VARIATION   tmnxEqSyncIfTimingPTPAlarmClear
            DESCRIPTION
                    "tmnxEqSyncIfTimingPTPAlarmClear not implemented on
                     Alcatel-Lucent 7950 systems."

    ::= { tmnxSROSChassisCapsV10v0 6 }  -- 7950 CHASSIS

--
--  CLEAR CAPABILITIES
--
tmnxSROSClearCapsV10v0    AGENT-CAPABILITIES
    PRODUCT-RELEASE "Alcatel-Lucent SROS"
    STATUS          current
    DESCRIPTION     "Implementation of clear and reset capabilities for
                     Alcatel-Lucent SROS release R10.0"

    SUPPORTS        TIMETRA-CLEAR-MIB
        INCLUDES    {
            tmnxClearGroup,
            tmnxClearNotificationGroup
        }

    ::= { tmnxSROSV10v0 7 }  -- CLEAR

--
--  DS0 CAPABILITIES
--
tmnxSROSDS0CapsV10v0    AGENT-CAPABILITIES
    PRODUCT-RELEASE "Alcatel-Lucent SROS"
    STATUS          current
    DESCRIPTION     "Implementation of DS0 Interface Types
                     capabilities for Alcatel-Lucent SROS release R10.0"

    SUPPORTS        DS0-MIB
        INCLUDES    {
            ds0ConfigGroup
        }

        VARIATION   dsx0RobbedBitSignalling
            ACCESS  read-only
            DESCRIPTION
                    "dsx0ConfigTable is implemented as read-only."

        VARIATION   dsx0CircuitIdentifier
            ACCESS  read-only
            DESCRIPTION
                    "dsx0ConfigTable is implemented as read-only."

        VARIATION   dsx0IdleCode
            ACCESS  read-only
            DESCRIPTION
                    "dsx0ConfigTable is implemented as read-only."

        VARIATION   dsx0SeizedCode
            ACCESS  read-only
            DESCRIPTION
                    "dsx0ConfigTable is implemented as read-only."

        VARIATION   dsx0TransmitCodesEnable
            ACCESS  read-only
            DESCRIPTION
                    "dsx0ConfigTable is implemented as read-only."

    ::= { tmnxSROSV10v0 9 }  -- DS0

--
--  DS1 CAPABILITIES
--
tmnxSROSDS1CapsV10v0    AGENT-CAPABILITIES
    PRODUCT-RELEASE "Alcatel-Lucent SROS"
    STATUS          current
    DESCRIPTION     "Implementation of DS1, E1, DS2 and E2 Interface Types
                     capabilities for Alcatel-Lucent SROS release R10.0"

    SUPPORTS        DS1-MIB
        INCLUDES    {
            ds1NearEndConfigurationGroup,
            ds1NearEndStatisticsGroup,
            ds1FarEndGroup,
            ds1NearEndOptionalConfigGroup,
            ds1TransStatsGroup,
            ds1ChanMappingGroup,
            ds1NearEndOptionalTrapGroup
        }

        VARIATION   dsx1LineType
            ACCESS  read-only
            DESCRIPTION
                    "dsx1ConfigTable is implemented as read-only."

        VARIATION   dsx1LineCoding
            ACCESS  read-only
            DESCRIPTION
                    "dsx1ConfigTable is implemented as read-only."

        VARIATION   dsx1SendCode
            ACCESS  read-only
            DESCRIPTION
                    "dsx1ConfigTable is implemented as read-only."

        VARIATION   dsx1CircuitIdentifier
            ACCESS  read-only
            DESCRIPTION
                    "dsx1ConfigTable is implemented as read-only."

        VARIATION   dsx1LoopbackConfig
            ACCESS  read-only
            DESCRIPTION
                    "dsx1ConfigTable is implemented as read-only."

        VARIATION   dsx1SignalMode
            ACCESS  read-only
            DESCRIPTION
                    "dsx1ConfigTable is implemented as read-only."

        VARIATION   dsx1TransmitClockSource
            ACCESS  read-only
            DESCRIPTION
                    "dsx1ConfigTable is implemented as read-only."

        VARIATION   dsx1Fdl
            ACCESS  read-only
            DESCRIPTION
                    "dsx1ConfigTable is implemented as read-only."

        VARIATION   dsx1LineLength
            ACCESS  read-only
            DESCRIPTION
                    "dsx1ConfigTable is implemented as read-only."

        VARIATION   dsx1LineStatusChangeTrapEnable
            ACCESS  read-only
            DESCRIPTION
                    "dsx1ConfigTable is implemented as read-only."

        VARIATION   dsx1Channelization
            ACCESS  read-only
            DESCRIPTION
                    "dsx1ConfigTable is implemented as read-only."

        VARIATION   dsx1IfIndex
            ACCESS  not-implemented
            DESCRIPTION
                    "Deprecated object"

        VARIATION   dsx1LineStatusChange
            ACCESS  not-implemented
            DESCRIPTION
                    "dsx1LineStatusChange notification is not implemented."

        VARIATION   dsx1LineMode
            ACCESS  not-implemented
            DESCRIPTION
                    "dsx1LineMode notification is not implemented."

        VARIATION   dsx1LineBuildOut
            ACCESS  not-implemented
            DESCRIPTION
                    "dsx1LineBuildOut notification is not implemented."

    ::= { tmnxSROSV10v0 10 }  -- DS1

--
--  DS3 CAPABILITIES
--
tmnxSROSDS3CapsV10v0    AGENT-CAPABILITIES
    PRODUCT-RELEASE "Alcatel-Lucent SROS"
    STATUS          current
    DESCRIPTION     "Implementation of DS3 and E3 Interface Types
                     capabilities for Alcatel-Lucent SROS release R10.0"

    SUPPORTS        DS3-MIB
        INCLUDES    {
            ds3NearEndConfigGroup,
            ds3NearEndStatisticsGroup,
            ds3FarEndGroup,
            ds3NearEndOptionalConfigGroup,
            ds3NearEndOptionalTrapGroup
        }

        VARIATION   dsx3LineType
            ACCESS  read-only
            DESCRIPTION
                    "dsx3ConfigTable is implemented as read-only."

        VARIATION   dsx3LineCoding
            ACCESS  read-only
            DESCRIPTION
                    "dsx3ConfigTable is implemented as read-only."

        VARIATION   dsx3SendCode
            ACCESS  read-only
            DESCRIPTION
                    "dsx3ConfigTable is implemented as read-only."

        VARIATION   dsx3CircuitIdentifier
            ACCESS  read-only
            DESCRIPTION
                    "dsx3ConfigTable is implemented as read-only."

        VARIATION   dsx3LoopbackConfig
            ACCESS  read-only
            DESCRIPTION
                    "dsx3ConfigTable is implemented as read-only."

        VARIATION   dsx3TransmitClockSource
            ACCESS  read-only
            DESCRIPTION
                    "dsx3ConfigTable is implemented as read-only."

        VARIATION   dsx3LineLength
            ACCESS  read-only
            DESCRIPTION
                    "dsx3ConfigTable is implemented as read-only."

        VARIATION   dsx3LineStatusChangeTrapEnable
            ACCESS  read-only
            DESCRIPTION
                    "dsx3ConfigTable is implemented as read-only."

        VARIATION   dsx3Channelization
            ACCESS  read-only
            DESCRIPTION
                    "dsx3ConfigTable is implemented as read-only."

        VARIATION   dsx3Ds1ForRemoteLoop
            ACCESS  read-only
            DESCRIPTION
                    "dsx3ConfigTable is implemented as read-only."

        VARIATION   dsx3FarEndEquipCode
            ACCESS  read-only
            DESCRIPTION
                    "dsx3FarEndConfigTable is implemented as read-only."

        VARIATION   dsx3FarEndLocationIDCode
            ACCESS  read-only
            DESCRIPTION
                    "dsx3FarEndConfigTable is implemented as read-only."

        VARIATION   dsx3FarEndFrameIDCode
            ACCESS  read-only
            DESCRIPTION
                    "dsx3FarEndConfigTable is implemented as read-only."

        VARIATION   dsx3FarEndUnitCode
            ACCESS  read-only
            DESCRIPTION
                    "dsx3FarEndConfigTable is implemented as read-only."

        VARIATION   dsx3FarEndFacilityIDCode
            ACCESS  read-only
            DESCRIPTION
                    "dsx3FarEndConfigTable is implemented as read-only."

        VARIATION   dsx3IfIndex
            ACCESS  not-implemented
            DESCRIPTION
                    "Deprecated object"

        VARIATION   dsx3LineStatusChange
            ACCESS  not-implemented
            DESCRIPTION
                    "dsx3LineStatusChange notification is not implemented."

    ::= { tmnxSROSV10v0 11 }  -- DS3

--
--  ETHERLIKE CAPABILITIES
--
tmnxSROSEtherLikeCapsV10v0    AGENT-CAPABILITIES
    PRODUCT-RELEASE "Alcatel-Lucent SROS"
    STATUS          current
    DESCRIPTION     "Implementation of Ethernet-like network interfaces
                     capabilities for Alcatel-Lucent SROS release R10.0"

    SUPPORTS        EtherLike-MIB
        INCLUDES    {
            etherStatsBaseGroup,
            etherDuplexGroup,
            etherStatsLowSpeedGroup,
            etherStatsHighSpeedGroup,
            etherControlPauseGroup,
            etherHCControlPauseGroup,
            etherControlGroup
-- EXCLUDE  etherCollisionTableGroup
-- EXCLUDE  etherRateControlGroup
-- EXCLUDE  etherHCStatsGroup
        }

        VARIATION   dot3ControlInUnknownOpcodes
            ACCESS  not-implemented
            DESCRIPTION
                    "dot3ControlInUnknownOpcodes is not implemented."

        VARIATION   dot3HCControlInUnknownOpcodes
            ACCESS  not-implemented
            DESCRIPTION
                    "dot3HCControlInUnknownOpcodes is not implemented."

        VARIATION   dot3PauseAdminMode
            ACCESS  not-implemented
            DESCRIPTION
                    "dot3PauseAdminMode is not implemented."

        VARIATION   dot3PauseOperMode
            ACCESS  not-implemented
            DESCRIPTION
                    "dot3PauseOperMode is not implemented."

    ::= { tmnxSROSV10v0 12 }  -- EtherLike MIB

--
--  ETHER-WIS CAPABILITIES
--
tmnxSROSEtherWisCapsV10v0    AGENT-CAPABILITIES
    PRODUCT-RELEASE "Alcatel-Lucent SROS"
    STATUS current
    DESCRIPTION     "Implementation of Ethernet WIS capabilities for
                     Alcatel-Lucent SROS release R10.0"

    SUPPORTS ETHER-WIS
        INCLUDES    {
            etherWisDeviceGroupBasic,
            etherWisSectionGroup,
            etherWisPathGroup,
            etherWisFarEndPathGroup
        }

        VARIATION   etherWisDeviceTxTestPatternMode
            ACCESS  read-only
            DESCRIPTION
                    "etherWisDeviceTxTestPatternMode is read-only."

        VARIATION   etherWisDeviceRxTestPatternMode
            ACCESS  read-only
            DESCRIPTION
                    "etherWisDeviceRxTestPatternMode is read-only."

        VARIATION   etherWisDeviceRxTestPatternErrors
            ACCESS  read-only
            DESCRIPTION
                    "etherWisDeviceRxTestPatternErrors is read-only."

        VARIATION   etherWisSectionCurrentJ0Transmitted
            ACCESS  read-only
            DESCRIPTION
                    "etherWisSectionCurrentJ0Transmitted is read-only."

        VARIATION   etherWisPathCurrentJ1Transmitted
            ACCESS  read-only
            DESCRIPTION
                    "etherWisPathCurrentJ1Transmitted is read-only."

    ::= { tmnxSROSV10v0 13 }  -- ETHER-WIS

--
--  FILTER CAPABILITIES
--
tmnxSROSFilterCapsV10v0    AGENT-CAPABILITIES
    PRODUCT-RELEASE "Alcatel-Lucent SROS"
    STATUS          current
    DESCRIPTION     "Implementation of Qos filters capabilities for
                     Alcatel-Lucent SROS release R10.0"

    SUPPORTS        TIMETRA-FILTER-MIB
        INCLUDES    {
            tFilterScalarGroup,
            tIPFilterV9v0Group,
            tMacFilterV8v0Group,
            tFilterLogGroup,
            tFilterLogV5v0Group,
            tFilterRedirectPolicyGroup,
            tFilterNotificationsV9v0Group,
            tFilterNotificationObjV9v0Group,
            tIPv6FilterV10v0Group,
            tTodPolicies77x0V5v0Group,
            tToDPoliciesV5v0NotifyGroup,
            tMacFilterVidFilteringV9v0Group,
            tDhcpFilterV10v0Group,
            tFilterNameV10v0Group,
            tLiFilterV10v0Group,
            tFilterPrefixListV10v0Group
        }

        VARIATION   tAutoIPFilterEntryTable
            ACCESS  not-implemented
            DESCRIPTION
                    "The tAutoIPFilterEntryTable was made obsolete in
                    release 3.0."

        VARIATION   tIPv6FilterParamsForwardRedPlcy
        DESCRIPTION
             "The object tIPv6FilterParamsForwardRedPlcy is added for
              future use. The corresponding functionality is not offered
              in this release.
              The only actions allowed on this object will therefore be
              GET and SET to its default value."

        VARIATION   tIPv6FilterParamsCflowdSample
        DESCRIPTION
             "The object tIPv6FilterParamsCflowdSample is added for
              future use. The corresponding functionality is not offered
              in this release.
              The only actions allowed on this object will therefore be
              GET and SET to its default value."

        VARIATION   tIPv6FilterParamsCflowdIfSample
        DESCRIPTION
                "The object tIPv6FilterParamsCflowdIfSample is added for
                 future use. The corresponding functionality is not offered
                 in this release.
                 The only actions allowed on this object will therefore be
                 GET and SET to its default value."

        VARIATION   tIPFilterParamsFwdRtrId
        DESCRIPTION
                "The object tIPFilterParamsFwdRtrId can only be set
                 in a (system generated) BGP flowspec filter entry in
                 this release.
                 The only actions allowed on this object will therefore be
                 GET and SET to its current value."

       VARIATION   tFilterLogDestination
       DESCRIPTION
               "The valie file(3) is not supported."

       VARIATION   tMacFilterType
       DESCRIPTION
               "The value 'vid' is not supported on SR-1 or ESS-1 systems."
    ::= { tmnxSROSV10v0 14 }  -- FILTER

tmnx7710FilterCapsV10v0    AGENT-CAPABILITIES
    PRODUCT-RELEASE "Alcatel-Lucent SROS"
    STATUS          current
    DESCRIPTION     "Implementation of Qos filters capabilities for
                     Alcatel-Lucent SROS release R10.0"
    SUPPORTS        TIMETRA-FILTER-MIB
        INCLUDES    {
            tMacFilterVidFilteringV9v0Group
        }
        VARIATION   tMacFilterType
        DESCRIPTION
                "The value 'vid' is not supported on 7710 systems."
        ::= { tmnxSROSFilterCapsV10v0 1 }

--
--  FRAME RELAY DTE CAPABILITIES
--
tmnxSROSFrameRelayDTECapsV10v0    AGENT-CAPABILITIES
    PRODUCT-RELEASE "Alcatel-Lucent SROS"
    STATUS          current
    DESCRIPTION     "Implementation of Frame Relay DTE capabilities for
                     Alcatel-Lucent SROS release R10.0"

    SUPPORTS        FRAME-RELAY-DTE-MIB
        INCLUDES    {
            frPortGroup,
            frCircuitGroup
-- EXCLUDE  frErrGroup,
-- EXCLUDE  frTrapGroup,
-- EXCLUDE  frNotificationGroup
        }

        VARIATION   frDlcmiAddress
            ACCESS  read-only
            DESCRIPTION
                    "frDlcmiAddress is read-only."

        VARIATION   frDlcmiAddressLen
            ACCESS  read-only
            DESCRIPTION
                    "frDlcmiAddressLen is read-only."

        VARIATION   frDlcmiMaxSupportedVCs
            ACCESS  read-only
            DESCRIPTION
                    "frDlcmiMaxSupportedVCs is read-only."

        VARIATION   frDlcmiMulticast
            ACCESS  read-only
            DESCRIPTION
                    "frDlcmiMulticast is read-only."

        VARIATION   frDlcmiRowStatus
            ACCESS  read-only
            DESCRIPTION
                    "frDlcmiRowStatus is read-only.  New entries in this
                    table cannot be created via SNMP SET requests."

        VARIATION   frCircuitState
            ACCESS  read-only
            DESCRIPTION
                    "frCircuitTable is read-only."

        VARIATION   frCircuitCommittedBurst
            ACCESS  read-only
            DESCRIPTION
                    "frCircuitTable is read-only."

        VARIATION   frCircuitExcessBurst
            ACCESS  read-only
            DESCRIPTION
                    "frCircuitTable is read-only."

        VARIATION   frCircuitThroughput
            ACCESS  read-only
            DESCRIPTION
                    "frCircuitTable is read-only."

        VARIATION   frCircuitMulticast
            ACCESS  read-only
            DESCRIPTION
                    "frCircuitTable is read-only."

        VARIATION   frCircuitLogicalIfIndex
            ACCESS  read-only
            DESCRIPTION
                    "frCircuitTable is read-only."

-- How are rows created in this table?  TIMETRA-VRTR-MIB? TIMETRA-CHASSIS-MIB?
        VARIATION   frCircuitRowStatus
            ACCESS  read-only
            DESCRIPTION
                    "frCircuitTable is read-only.  Row entries cannot be
                     created by SNMP SET requests."

        VARIATION   frDLCIStatusChange
            ACCESS  not-implemented
            DESCRIPTION
                    "frDLCIStatusChange notification is not implemented."

    ::= { tmnxSROSV10v0 15 }  -- FRAME RELAY

--
--  IEEE 8021 PAE CAPABILITIES
--
tmnxSROSIEEE8021PaeCapsV10v0    AGENT-CAPABILITIES
    PRODUCT-RELEASE "Alcatel-Lucent SROS"
    STATUS current
    DESCRIPTION     "Implementation of IEEE 8021 PAE protocol capabilities for
                     Alcatel-Lucent SROS release R10.0."

    SUPPORTS IEEE8021-PAE-MIB
        INCLUDES    {
            dot1xPaeSystemGroup,
            dot1xPaeAuthConfigGroup,
            dot1xPaeAuthStatsGroup,
            dot1xPaeAuthDiagGroup,
            dot1xPaeAuthSessionStatsGroup
-- EXCLUDE  dot1xPaeSuppConfigGroup,
-- EXCLUDE  dot1xPaeSuppStatsGroup
         }

        VARIATION   dot1xAuthAdminControlledDirections
            ACCESS  read-only
            DESCRIPTION
                    "dot1xAuthAdminControlledDirections is read-only."

        VARIATION   dot1xAuthKeyTxEnabled
            SYNTAX  TruthValue
            ACCESS  read-only
            DESCRIPTION
                    "dot1xAuthKeyTxEnabled is read-only.  The value returned
                    is always false."

    SUPPORTS  ALCATEL-IEEE8021-PAE-MIB
        INCLUDES    {
            alxDot1xAuthConfigGroup,
            alxDot1xRadiusPlcyGroup
         }

    ::= { tmnxSROSV10v0 16 }  -- IEEE-8021-PAE

--
--  INTERFACE CAPABILITIES
--
tmnxSROSIfCapsV10v0    AGENT-CAPABILITIES
    PRODUCT-RELEASE "Alcatel-Lucent SROS"
    STATUS          current
    DESCRIPTION     "Implementation of Interface capabilities for
                     Alcatel-Lucent SROS release R10.0"

    SUPPORTS        IF-MIB
        INCLUDES    {
            ifGeneralInformationGroup,
            linkUpDownNotificationsGroup,
            ifPacketGroup,
            ifHCPacketGroup,
            ifVHCPacketGroup,
            ifCounterDiscontinuityGroup,
            ifStackGroup2
-- EXCLUDE  ifFixedLengthGroup
-- EXCLUDE  ifHCFixedLengthGroup
-- EXCLUDE  ifRcvAddressGroup
        }

        VARIATION   ifAdminStatus
            SYNTAX  INTEGER {
                        up      (1),       -- ready to pass packets
                        down    (2)
                    }
            DESCRIPTION
                    "Write access using value 'testing (3)' is not supported."

        VARIATION   linkDown
            DESCRIPTION
                    "The linkDown notification has ifDescr appended to the
                     variable list."

        VARIATION   linkUp
            DESCRIPTION
                    "The linkUp trap has ifDescr appended to the variable list."

        VARIATION   ifLinkUpDownTrapEnable
            ACCESS  read-only
            DESCRIPTION
                    "ifLinkUpDownTrapEnable is supported as read-only."

        VARIATION   ifPromiscuousMode
            ACCESS  read-only
            DESCRIPTION
                    "ifPromiscuousMode is supported as read-only."

        VARIATION   ifAlias
            SYNTAX  DisplayString (SIZE(0..160))
            ACCESS  read-only
            DESCRIPTION
                    "ifAlias is supported as read-only.  The maximum size
                     string returned has been increased from 64 to
                     160 characters.  The string returned for ifAlias
                     is the user configured port or interface description."

        VARIATION   ifStackStatus
            ACCESS  read-only
            DESCRIPTION
                    "ifStackStatus is supported as read-only."

    SUPPORTS        IF-INVERTED-STACK-MIB
        INCLUDES    {
            ifInvStackGroup
        }

    ::= { tmnxSROSV10v0 17 }  -- INTERFACE


--
--  IGMP CAPABILITIES
--
tmnxSROSIgmpCapsV10v0    AGENT-CAPABILITIES
    PRODUCT-RELEASE "Alcatel-Lucent SROS"
    STATUS          current
    DESCRIPTION     "Implementation of IGMP protocol capabilities for
                     Alcatel-Lucent SROS release R10.0"

    SUPPORTS        IGMP-STD-MIB
        INCLUDES    {
            igmpBaseMIBGroup,
            igmpRouterMIBGroup,
            igmpV2HostMIBGroup,
            igmpHostOptMIBGroup,
            igmpV2RouterMIBGroup,
            igmpV2ProxyMIBGroup
        }

        VARIATION   igmpInterfaceQueryInterval
            ACCESS  not-implemented
            DESCRIPTION
                    "igmpInterfaceQueryInterval is not implemented."

        VARIATION   igmpInterfaceStatus
            ACCESS  not-implemented
            DESCRIPTION
                    "igmpInterfaceStatus is not implemented."

        VARIATION   igmpInterfaceVersion
            ACCESS  not-implemented
            DESCRIPTION
                    "igmpInterfaceVersion is not implemented."

        VARIATION   igmpInterfaceQuerier
            ACCESS  not-implemented
            DESCRIPTION
                    "igmpInterfaceQuerier is not implemented."

        VARIATION   igmpInterfaceQueryMaxResponseTime
            ACCESS  not-implemented
            DESCRIPTION
                    "igmpInterfaceQueryMaxResponseTime is not implemented."

        VARIATION   igmpInterfaceQuerierUpTime
            ACCESS  not-implemented
            DESCRIPTION
                    "igmpInterfaceQuerierUpTime is not implemented."

        VARIATION   igmpInterfaceQuerierExpiryTime
            ACCESS  not-implemented
            DESCRIPTION
                    "igmpInterfaceQuerierExpiryTime is not implemented."

        VARIATION   igmpInterfaceVersion1QuerierTimer
            ACCESS  not-implemented
            DESCRIPTION
                    "igmpInterfaceVersion1QuerierTimer is not implemented."

        VARIATION   igmpInterfaceWrongVersionQueries
            ACCESS  not-implemented
            DESCRIPTION
                    "igmpInterfaceWrongVersionQueries is not implemented."

        VARIATION   igmpInterfaceJoins
            ACCESS  not-implemented
            DESCRIPTION
                    "igmpInterfaceJoins is not implemented."

        VARIATION   igmpInterfaceProxyIfIndex
            ACCESS  not-implemented
            DESCRIPTION
                    "igmpInterfaceProxyIfIndex is not implemented."

        VARIATION   igmpInterfaceGroups
            ACCESS  not-implemented
            DESCRIPTION
                    "igmpInterfaceGroups is not implemented."

        VARIATION   igmpInterfaceRobustness
            ACCESS  not-implemented
            DESCRIPTION
                    "igmpInterfaceRobustness is not implemented."

        VARIATION   igmpInterfaceLastMembQueryIntvl
            ACCESS  not-implemented
            DESCRIPTION
                    "igmpInterfaceLastMembQueryIntvl is not implemented."

        VARIATION   igmpCacheSelf
            ACCESS  read-only
            DESCRIPTION
                    "igmpCacheSelf is implemented as read-only."

        VARIATION   igmpCacheStatus
            ACCESS  read-only
            DESCRIPTION
                    "igmpCacheStatus is implemented as read-only."

    SUPPORTS        TIMETRA-IGMP-MIB
        INCLUDES    {
            tmnxIgmpGlobalGroup,
            tmnxIgmpIfV5v0Group,
            tmnxIgmpNotificationV10v0Group,
            tmnxIgmpIfV6v1Group,
            tmnxIgmpIfV7v0Group,
            tmnxIgmpIfV8v0Group,
            tmnxIgmpIfV9v0Group,
            tmnxIgmpIfV10v0Group
        }

        VARIATION   vRtrIgmpIfSSMTransRowStatus
            SYNTAX  RowStatus
            DESCRIPTION
                    "vRtrIgmpIfSSMTransRowStatus only supports 'ipv4' indices."

        VARIATION   vRtrIgmpRsvpIfSenderAddrType
            SYNTAX  INTEGER {
                        -- unknown  (0),
                        ipv4        (1)
                        -- ipv6      (2)
                        -- ipv4z    (3),
                        -- ipv6z    (4),
                        -- dns      (16)
                    }
            DESCRIPTION
                    "vRtrIgmpRsvpIfSenderAddrType supports only InetAddressType
                     'ipv4'."

        VARIATION   vRtrIgmpRsvpIfSenderAddr
            SYNTAX  InetAddress (SIZE (4))
            DESCRIPTION
                    "vRtrIgmpRsvpIfSenderAddr supports only InetAddressType
                    'ipv4'."

    ::= { tmnxSROSV10v0 18 }  -- IGMP

--
--  IGMP SNOOPING
--
tmnxSROSIgmpSnoopingCapsV10v0    AGENT-CAPABILITIES
    PRODUCT-RELEASE "Alcatel-Lucent SROS"
    STATUS current
    DESCRIPTION     "Implementation of IGMP Snooping capabilities for
                     Alcatel-Lucent SROS release R10.0"

    SUPPORTS ALCATEL-IGMP-SNOOPING-MIB
        INCLUDES    {
            alxTlsIgmpSnpgConfigV6v0Group,
            alxTlsIgmpSnpgQuerierV3v0Group,
            alxTlsIgmpSnpgProxyV3v0Group,
            alxTlsIgmpSnpgMRouterV3v0Group,
            alxTlsMvrConfigV3v0Group,
            alxTlsIgmpSnpgTimeStampGroup,
            alxSapIgmpSnpgConfigV5v0Group,
            alxSapIgmpSnpgGroupV3v0,
            alxSapIgmpSnpgStaticV3v0Group,
            alxSapIgmpSnpgStatsV6v0Group,
            alxSapMvrV3v0Group,
            alxSapIgmpSnpgNotV5v0Group,
            alxSapIgmpSnpgTimeStampGroup,
            alxSdpBindIgmpSnpgConfV5v0Group,
            alxSdpBindIgmpSnpgV3v0Group,
            alxSdpBindIgmpSnpgStatV3v0Group,
            alxSdpBindIgmpSnpgStatsV6v0Grp,
            alxSdpBindIgmpSnpgNotV5v0Group,
            alxSdpBindIgmpSnpgTimeStampGroup,
            alxSapIgmpSnpgConfigV8v0Group,
            alxSapIgmpSnpgMaxSrcsV6v1Group,
            alxSapIgmpSnpgMaxSrcsNotV6v1Grp,
            alxSdpBindIgmpSnpgMaxSrcsV6v1Grp,
            alxSdpBindIgmpSnpgNotV6v1Group
        }
    ::= { tmnxSROSV10v0 19 }  -- IGMP-SNOOPING

--
--  IP CAPABILITIES
--
tmnxSROSIPCapsV10v0    AGENT-CAPABILITIES
    PRODUCT-RELEASE "Alcatel-Lucent SROS"
    STATUS          current
    DESCRIPTION     "Implementation of Internet Protocol, IP, capabilities for
                     Alcatel-Lucent SROS release R10.0"

    SUPPORTS        IP-MIB
        INCLUDES    {
            ipGroup,
            ipAddressPrefixGroup,
            ipAddressGroup,
            ipNetToPhysicalGroup,
            ipv6RouterAdvertGroup,
            icmpGroup,
            ipv6GeneralGroup2,
            ipLastChangeGroup,
            ipv4IfGroup,
            ipv6IfGroup,
            ipSystemStatsGroup,
            ipv6ScopeGroup,
            ipDefaultRouterGroup,
            icmpStatsGroup
        }

        VARIATION   ipNetToMediaType
            SYNTAX  INTEGER {
                        other   (1),      -- none of the following
                        invalid (2),      -- an invalidated mapping
                        dynamic (3),
                        static  (4),
                        managed (5)       -- added for SROS
                    }
            DESCRIPTION
                    "The value 'managed (5)' is used to indicate that the
                    ARP entry has been added by:
                        - a static host
                        - a DHCP lease state if
                          TIMETRA-VRTR-MIB::vRtrIfArpPopulate
                          is set to enabled.

                    An attempt to set ipNetToMediaType to the value 'managed'
                    results in an 'inconsistentValue' error."

        VARIATION   ipForwarding
            ACCESS  read-only
            DESCRIPTION
                    "ipForwarding is implemented as read-only.
                    It always returns the value 'forwarding (1)'."

        VARIATION   ipDefaultTTL
            ACCESS  read-only
            DESCRIPTION
                    "ipDefaultTTL is implemented as read-only.
                    It always returns the value '64'."

        VARIATION   ipAddressSpinLock
            ACCESS  read-only
            DESCRIPTION
                    "ipAddressSpinLock is implemented as read-only."

        VARIATION   ipv6RouterAdvertSpinLock
            ACCESS  read-only
            DESCRIPTION
                    "ipv6RouterAdvertSpinLock is implemented as read-only."

        VARIATION   ipAddressIfIndex
            ACCESS  read-only
            DESCRIPTION
                    "ipAddressTable is implemented as read-only."

        VARIATION   ipAddressType
            ACCESS  read-only
            DESCRIPTION
                    "ipAddressTable is implemented as read-only."

        VARIATION   ipAddressPrefix
            ACCESS  read-only
            DESCRIPTION
                    "ipAddressTable is implemented as read-only."

        VARIATION   ipAddressOrigin
            ACCESS  read-only
            DESCRIPTION
                    "ipAddressTable is implemented as read-only."

        VARIATION   ipAddressStatus
            ACCESS  read-only
            DESCRIPTION
                    "ipAddressTable is implemented as read-only."

        VARIATION   ipAddressCreated
            ACCESS  read-only
            DESCRIPTION
                    "ipAddressTable is implemented as read-only."

        VARIATION   ipAddressRowStatus
            ACCESS  read-only
            DESCRIPTION
                    "ipAddressTable is implemented as read-only."

        VARIATION   ipAddressStorageType
            ACCESS  read-only
            DESCRIPTION
                    "ipAddressTable is implemented as read-only."

        VARIATION   ipv6IpForwarding
            ACCESS  read-only
            DESCRIPTION
                    "ipv6IpForwarding is implemented as read-only."

        VARIATION   ipv6IpDefaultHopLimit
            ACCESS  read-only
            DESCRIPTION
                    "ipv6IpDefaultHopLimit is implemented as read-only."

        VARIATION   ipv4InterfaceEnableStatus
            ACCESS  read-only
            DESCRIPTION
                    "ipv4InterfaceTable is implemented as read-only."

        VARIATION   ipv6InterfaceEnableStatus
            ACCESS  read-only
            DESCRIPTION
                    "ipv6InterfaceTable is implemented as read-only."

        VARIATION   ipv6InterfaceForwarding
            ACCESS  read-only
            DESCRIPTION
                    "ipv6InterfaceTable is implemented as read-only."

        VARIATION   ipDefaultRouterLifetime
            ACCESS  not-implemented
            DESCRIPTION
                    "ipDefaultRouterTable is not implemented because it is
                     meant for hosts."

        VARIATION   ipDefaultRouterPreference
            ACCESS  not-implemented
            DESCRIPTION
                    "ipDefaultRouterTable is not implemented because it is
                     meant for hosts."

        VARIATION   ipv6ScopeZoneIndexLinkLocal
            ACCESS  not-implemented
            DESCRIPTION
                    "ipv6ScopeZoneIndexTable is not implemented."

        VARIATION   ipv6ScopeZoneIndex3
            ACCESS  not-implemented
            DESCRIPTION
                    "ipv6ScopeZoneIndexTable is not implemented."

        VARIATION   ipv6ScopeZoneIndexAdminLocal
            ACCESS  not-implemented
            DESCRIPTION
                    "ipv6ScopeZoneIndexTable is not implemented."

        VARIATION   ipv6ScopeZoneIndexSiteLocal
            ACCESS  not-implemented
            DESCRIPTION
                    "ipv6ScopeZoneIndexTable is not implemented."

        VARIATION   ipv6ScopeZoneIndex6
            ACCESS  not-implemented
            DESCRIPTION
                    "ipv6ScopeZoneIndexTable is not implemented."

        VARIATION   ipv6ScopeZoneIndex7
            ACCESS  not-implemented
            DESCRIPTION
                    "ipv6ScopeZoneIndexTable is not implemented."

        VARIATION   ipv6ScopeZoneIndexOrganizationLocal
            ACCESS  not-implemented
            DESCRIPTION
                    "ipv6ScopeZoneIndexTable is not implemented."

        VARIATION   ipv6ScopeZoneIndex9
            ACCESS  not-implemented
            DESCRIPTION
                    "ipv6ScopeZoneIndexTable is not implemented."

        VARIATION   ipv6ScopeZoneIndexA
            ACCESS  not-implemented
            DESCRIPTION
                    "ipv6ScopeZoneIndexTable is not implemented."

        VARIATION   ipv6ScopeZoneIndexB
            ACCESS  not-implemented
            DESCRIPTION
                    "ipv6ScopeZoneIndexTable is not implemented."

        VARIATION   ipv6ScopeZoneIndexC
            ACCESS  not-implemented
            DESCRIPTION
                    "ipv6ScopeZoneIndexTable is not implemented."

        VARIATION   ipv6ScopeZoneIndexD
            ACCESS  not-implemented
            DESCRIPTION
                    "ipv6ScopeZoneIndexTable is not implemented."

        VARIATION   ipNetToPhysicalType
            SYNTAX  INTEGER {
                        other   (1),       -- none of the following
                        invalid (2),       -- an invalidated mapping
                        dynamic (3),
                        static  (4),
                        local   (5),       -- local interface
                        managed (100)      -- added for SROS
                    }
            DESCRIPTION
                    "The value 'managed (100)' is used to indicate that the
                    ARP entry has been added by:

                    - a static host; or
                    - by a DHCP lease state if
                      TIMETRA-VRTR-MIB::vRtrIfArpPopulate is set to enabled.

                    An attempt to explicitly set the value of
                    ipNetToPhysicalType to 'managed' results in an
                    'inconsistentValue' error."

    SUPPORTS        IP-FORWARD-MIB
        INCLUDES    {
            ipForwardCidrRouteGroup,
            inetForwardCidrRouteGroup
        }

        VARIATION   ipCidrRouteIfIndex
            ACCESS  read-only
            DESCRIPTION
                    "ipCidrRouteTable is implemented as read-only."

        VARIATION   ipCidrRouteType
            ACCESS  read-only
            DESCRIPTION
                    "ipCidrRouteTable is implemented as read-only."

        VARIATION   ipCidrRouteProto
            DESCRIPTION
                    "ipCidrRouteProto supports the value 'bgpVpn (254)'
                    in addition to the list of enumerations to support
                    rfc2547 VPRNs on Alcatel-Lucent SROS systems."

        VARIATION   ipCidrRouteInfo
            ACCESS  read-only
            DESCRIPTION
                    "ipCidrRouteTable is implemented as read-only."

        VARIATION   ipCidrRouteNextHopAS
            ACCESS  read-only
            DESCRIPTION
                    "ipCidrRouteTable is implemented as read-only."

        VARIATION   ipCidrRouteMetric1
            ACCESS  read-only
            DESCRIPTION
                    "ipCidrRouteTable is implemented as read-only."

        VARIATION   ipCidrRouteMetric2
            ACCESS  read-only
            DESCRIPTION
                    "ipCidrRouteTable is implemented as read-only."

        VARIATION   ipCidrRouteMetric3
            ACCESS  read-only
            DESCRIPTION
                    "ipCidrRouteTable is implemented as read-only."

        VARIATION   ipCidrRouteMetric4
            ACCESS  read-only
            DESCRIPTION
                    "ipCidrRouteTable is implemented as read-only."

        VARIATION   ipCidrRouteMetric5
            ACCESS  read-only
            DESCRIPTION
                    "ipCidrRouteTable is implemented as read-only."

        VARIATION   ipCidrRouteStatus
            ACCESS  read-only
            DESCRIPTION
                    "ipCidrRouteTable is implemented as read-only."

        VARIATION   inetCidrRouteIfIndex
            ACCESS  read-only
            DESCRIPTION
                    "inetCidrRouteTable is implemented as read-only."

        VARIATION   inetCidrRouteType
            ACCESS  read-only
            DESCRIPTION
                    "inetCidrRouteTable is implemented as read-only."

        VARIATION   inetCidrRouteProto
            DESCRIPTION
                    "inetCidrRouteProto supports the values 'periodic (247)',
                     'vpnLeak (249)', 'ldp (250)', 'managed (251)',
                     'host (252)', 'ospf3 (253)', 'bgpVpn (254)',
                     'subMgmt (255)', 'tms (256)', 'nat (257)' and 'ipsec (258)'
                     in addition to the enumerations in the 
                     IANAipRouteProtocol TC."

        VARIATION   inetCidrRouteNextHopAS
            ACCESS  read-only
            DESCRIPTION
                    "inetCidrRouteTable is implemented as read-only."

        VARIATION   inetCidrRouteMetric1
            ACCESS  read-only
            DESCRIPTION
                    "inetCidrRouteTable is implemented as read-only."

        VARIATION   inetCidrRouteMetric2
            ACCESS  read-only
            DESCRIPTION
                    "inetCidrRouteTable is implemented as read-only."

        VARIATION   inetCidrRouteMetric3
            ACCESS  read-only
            DESCRIPTION
                    "inetCidrRouteTable is implemented as read-only."

        VARIATION   inetCidrRouteMetric4
            ACCESS  read-only
            DESCRIPTION
                    "inetCidrRouteTable is implemented as read-only."

        VARIATION   inetCidrRouteMetric5
            ACCESS  read-only
            DESCRIPTION
                    "inetCidrRouteTable is implemented as read-only."

        VARIATION   inetCidrRouteStatus
            SYNTAX  INTEGER {
                        active (1)
                    }
            ACCESS  read-only
            DESCRIPTION
                    "inetCidrRouteTable is implemented as read-only.

                    The indexes inetCidrRouteDestType and
                    inetCidrRouteNextHopType support the values of
                    'ipv4Mcast (128)' and 'ipv6Mcast (129)' in addition to those
                    defined by the InetAddressType textual convention.
                    'ipv4Mcast (128)' and 'ipv6Mcast (129)' are implemented
                    for 'ipv4'/'ipv6' addresses for multicast extensions."

    SUPPORTS        TCP-MIB
        INCLUDES    {
            tcpGroup,
            tcpConnectionGroup,
            tcpListenerGroup
-- EXCLUDE  tcpHCGroup (not supported)
        }

        VARIATION   tcpConnectionState
            ACCESS  read-only
            DESCRIPTION
                    "tcpConnectionState is implemented as read-only."

    SUPPORTS        UDP-MIB
        INCLUDES    {
            udpGroup,
            udpEndpointGroup
-- EXCLUDE  udpHCGroup (not supported)
        }

    ::= { tmnxSROSV10v0 20 }  -- IP

--
--  ISIS CAPABILITIES
--
tmnxSROSIsisCapsV10v0    AGENT-CAPABILITIES
    PRODUCT-RELEASE "Alcatel-Lucent SROS"
    STATUS          current
    DESCRIPTION     "Implementation of ISIS protocol capabilities for
                     Alcatel-Lucent SROS release R10.0"

    SUPPORTS        ISIS-MIB
        INCLUDES    {
            isisSystemGroup,
            isisCircuitGroup,
            isisISAdjGroup
-- EXCLUDE  isisISPDUCounterGroup,
-- EXCLUDE  isisRATableGroup
-- EXCLUDE  isisISIPRADestGroup
        }

        --
        --  isisSystemGroup
        --

        VARIATION   isisSysID
            ACCESS  read-only
            DESCRIPTION
                    "isisSysID is implemented as read-only."

        VARIATION   isisSysOrigL1LSPBuffSize
            ACCESS  not-implemented
            DESCRIPTION
                    "isisSysOrigL1LSPBuffSize is not implemented.
                     This object is no longer supported in the 6.0
                     release.

                     It has been replaced by
                     TIMETRA-ISIS-MIB::vRtrIsisSysOrigL1LSPBuffSize."

        VARIATION   isisSysMaxAreaAddresses
            ACCESS  read-only
            DESCRIPTION
                    "isisSysMaxAreaAddresses is implemented as read-only."

        VARIATION   isisSysMinL1LSPGenInt
            ACCESS  read-only
            DESCRIPTION
                    "isisSysMinL1LSPGenInt is implemented as read-only."

        VARIATION   isisSysMinL2LSPGenInt
            ACCESS  read-only
            DESCRIPTION
                    "isisSysMinL2LSPGenInt is implemented as read-only."

        VARIATION   isisSysPollESHelloRate
            ACCESS  read-only
            DESCRIPTION
                    "isisSysPollESHelloRate is implemented as read-only."

        VARIATION   isisSysOrigL2LSPBuffSize
            ACCESS  not-implemented
            DESCRIPTION
                    "isisSysOrigL2LSPBuffSize is not implemented.
                     This object is no longer supported in the 6.0
                     release.

                     It has been replaced by
                     TIMETRA-ISIS-MIB::vRtrIsisSysOrigL2LSPBuffSize."

        VARIATION   isisSysLSPIgnoreErrors
            ACCESS  read-only
            DESCRIPTION
                    "isisSysLSPIgnoreErrors is implemented as read-only."

        VARIATION   isisSysLogAdjacencyChanges
            ACCESS  read-only
            DESCRIPTION
                    "isisSysLogAdjacencyChanges is implemented as read-only."

        VARIATION   isisSysL2toL1Leaking
            ACCESS  read-only
            DESCRIPTION
                    "isisSysL2toL1Leaking is implemented as read-only."

-- ??? How are rows created in isisSysProtSuppTable??
        VARIATION   isisSysProtSuppExistState
            ACCESS  read-only
            DESCRIPTION
                    "isisSysProtSuppTable is implemented as read-only."

        VARIATION   isisSummAddressType
            ACCESS  not-implemented
            DESCRIPTION
                    "isisSummAddressType is not implemented. This object is no
                     longer supported in the 6.0 release.

                     It has been replaced by
                     TIMETRA-ISIS-MIB::vRtrIsisSummPrefix."

        VARIATION   isisSummAddress
            ACCESS  not-implemented
            DESCRIPTION
                    "isisSummAddress is not implemented. This object is no
                     longer supported in the 6.0 release.

                     It has been replaced by
                     TIMETRA-ISIS-MIB::vRtrIsisSummPrefix."

        VARIATION   isisSummAddrPrefixLen
            ACCESS  not-implemented
            DESCRIPTION
                    "isisSummAddrPrefixLen is not implemented. This object is no
                     longer supported in the 6.0 release.

                     It has been replaced by
                     TIMETRA-ISIS-MIB::vRtrIsisSummMask."

        VARIATION   isisSummAddrExistState
            ACCESS  not-implemented
            DESCRIPTION
                    "isisSummAddrExistState is not implemented. This object is
                     no longer supported in the 6.0 release."

        VARIATION   isisSummAddrAdminState
            ACCESS  not-implemented
            DESCRIPTION
                    "isisSummAddrAdminState is not implemented. This object is
                     no longer supported in the 6.0 release."

        VARIATION   isisSummAddrDefaultMetric
            ACCESS  not-implemented
            DESCRIPTION
                    "isisSummAddrDefaultMetric is not implemented. This object
                     is no longer supported in the 6.0 release."

        --
        --  isisCircuitGroup
        --
        --  isisCircTable
        --
        VARIATION   isisCircEntry
            CREATION-REQUIRES   { vRtrIsisIfRowStatus }
            DESCRIPTION
                    "Row entries in the isisCircTable are created by setting
                    TIMETRA-ISIS-MIB::vRtrIsisIfRowStatus."

        VARIATION   isisCircExistState
            SYNTAX  INTEGER {
                        active (1)
                    }
            ACCESS  read-only
            DESCRIPTION
                    "isisCircExistState, the RowStatus object, is implemented
                    as read-only."

        VARIATION   isisCircIfIndex
            ACCESS  read-only
            DESCRIPTION
                    "isisCircIfIndex is implemented as read-only."

        VARIATION   isisCircIfSubIndex
            ACCESS  read-only
            DESCRIPTION
                    "isisCircIfSubIndex is implemented as read-only."

        --
        --  isisCircLevelTable
        --
        VARIATION   isisCircLevelDefaultMetric
            SYNTAX  DefaultMetric (0..63)
            ACCESS  read-only
            DESCRIPTION
                    "isisCircLevelDefaultMetric is implemented as read-only.
                    isisCircLevelDefaultMetric can have a value of 0 for
                    loopback and system interfaces."

        VARIATION   isisCircLevelISPriority
            ACCESS  read-only
            DESCRIPTION
                    "isisCircLevelISPriority is implemented as read-only."

        VARIATION   isisCircLevelHelloTimer
            ACCESS  read-only
            DESCRIPTION
                    "isisCircLevelHelloTimer is implemented as read-only."

        VARIATION   isisCircLevelDRHelloTimer
            ACCESS  read-only
            DESCRIPTION
                    "isisCircLevelDRHelloTimer is implemented as read-only."

        VARIATION   isisCircLevelLSPThrottle
            ACCESS  read-only
            DESCRIPTION
                    "isisCircLevelLSPThrottle is implemented as read-only."

        VARIATION   isisCircLevelMinLSPRetransInt
            ACCESS  read-only
            DESCRIPTION
                    "isisCircLevelMinLSPRetransInt is implemented as read-only."

        VARIATION   isisCircLevelCSNPInterval
            ACCESS  read-only
            DESCRIPTION
                    "isisCircLevelCSNPInterval is implemented as read-only."

        VARIATION   isisCircLevelPartSNPInterval
            ACCESS  read-only
            DESCRIPTION
                    "isisCircLevelPartSNPInterval is implemented as read-only."

        VARIATION   isisCircLevelHelloMultiplier
            DEFVAL  { 3 }
            DESCRIPTION
                    "The default hello multiplier value is 3 instead of 10
                    since the value of 10 results in a long holding time."

        VARIATION   isisSysMaxPathSplits
            ACCESS  read-only
            DESCRIPTION
                    "isisSysMaxPathSplits is implemented as read-only."

    SUPPORTS        TIMETRA-ISIS-MIB
        INCLUDES    {
            vRtrIsisAdjV5v0Group,
            vRtrIsisHostGroup,
            vRtrIsisIfV5v0Group,
            vRtrIsisIfV6v0Group,
            vRtrIsisIfV6v1Group,
            vRtrIsisLSPGroup,
            vRtrIsisLspMtuV6v0Group,
            vRtrIsisNotificationV3v0Group,
            vRtrIsisNotificationV6v0Group,
            vRtrIsisNotificationV7v0Group,
            vRtrIsisPathV5v0Group,
            vRtrIsisRouteV5v0Group,
            vRtrIsisRouteV6v1Group,
            vRtrIsisSpfGroup,
            vRtrIsisSummaryV4v0Group,
            vRtrIsisSummaryV6v1Group,
            vRtrIsisV5v0Group,
            vRtrIsisV6v0Group,
            vRtrIsisV6v1Group,
            vRtrIsisV7v0Group,
            vRtrIsisV8v0Group,
            vRtrIsisV9v0Group,
            vRtrIsisIfV9v0Group,
            vRtrSpbEctFidGroup,
            vRtrIsisV9v0R4Group,
            vRtrIsisNotifyV10v0Group,
            vRtrIsisNotifyObjsV10v0Group,
            vRtrIsisV10v0Group
        }

        VARIATION   vRtrIsisLevelAuthType
            SYNTAX  INTEGER {
                        none (1),
                        password (2),
                        md5 (3)
                    }
            DESCRIPTION
                    "The values supported for this object are
                     'none', 'password' and 'md5'."

        VARIATION   vRtrIsisIfLevelTeMetric
            ACCESS  read-only
            DESCRIPTION
                    "vRtrIsisIfLevelTeMetric is implemented as read-only."

        VARIATION   vRtrIsisShortCuts
            ACCESS  read-only
            DESCRIPTION
                    "vRtrIsisShortCuts is implemented as read-only."

        VARIATION   vRtrIsisGRRestartDuration
            ACCESS  not-implemented
            DESCRIPTION
                    "vRtrIsisGRRestartDuration is not implemented."

        VARIATION   vRtrIsisIfLevelOperMetric
            SYNTAX  Unsigned32 (0..16777215)
            DESCRIPTION
                    "vRtrIsisIfLevelOperMetric can have a value of 0 for
                    loopback and system interfaces."

        VARIATION   vRtrIsisOverloadOnBoot
            SYNTAX  INTEGER {
                    disabled (1),
                    enabled (2)
                    -- enabledWaitForBgp (3)
                }
            DESCRIPTION
                    "vRtrIsisOverloadOnBoot only supports disabled (1)' and
                    'enabled (2)'. 'enabledWaitForBgp (3) is not implemented."

        VARIATION   vRtrIsisSpfHoldTime
            ACCESS  read-only
            DESCRIPTION
                    "vRtrIsisSpfHoldTime is implemented as read-only."

    ::= { tmnxSROSV10v0 21 }  -- ISIS

--
--  LINK AGGREGATION, LAG, CAPABILITIES
--
tmnxSROSLAGCapsV10v0    AGENT-CAPABILITIES
    PRODUCT-RELEASE "Alcatel-Lucent SROS"
    STATUS          current
    DESCRIPTION     "Implementation of Link Aggregation, LAG, capabilities
                     for Alcatel-Lucent SROS release R10.0"

    SUPPORTS        IEEE8023-LAG-MIB
        INCLUDES    {
            dot3adAggGroup,
            dot3adAggPortGroup,
            dot3adTablesLastChangedGroup
-- EXCLUDE  dot3adAggPortListGroup,
-- EXCLUDE  dot3adAggPortStatsGroup,
-- EXCLUDE  dot3adAggPortDebugGroup
        }

        --
        -- dot3adTablesLastChangedGroup
        --
        VARIATION   dot3adTablesLastChanged
            ACCESS  not-implemented
            DESCRIPTION
                    "dot3adTablesLastChanged is not implemented."

        --
        -- dot3adAggGroup
        --
        VARIATION   dot3adAggActorAdminKey
            ACCESS  read-write
            DESCRIPTION
                    "The value of dot3adAggActorAdminKey cannot be changed
                    after the row entry has been created.  A set to the
                    same value succeeds."

        VARIATION   dot3adAggActorSystemPriority
            ACCESS  read-only
            DESCRIPTION
                    "dot3adAggActorSystemPriority is supported as read-only."

-- ??? Is there a meaningful value returned to a read of this object???
-- ??? Or should this object be excluded by IEEE8023-LAG-MIB.ctl???
        VARIATION   dot3adAggCollectorMaxDelay
            ACCESS  read-only
            DESCRIPTION
                   "dot3adAggCollectorMaxDelay is supported as read-only."

        VARIATION   dot3adAggEntry
            CREATION-REQUIRES   { tLagRowStatus }
            DESCRIPTION
                    "An entry in the dot3adAggTable is created when an entry
                    is created in the tLagConfigTable in TIMETRA-LAG-MIB."

        --
        -- dot3adAggPortGroup
        --
        VARIATION   dot3adAggPortActorSystemPriority
            ACCESS  read-only
            DESCRIPTION
                    "dot3adAggPortActorSystemPriority is supported as
                    read-only."

        VARIATION   dot3adAggPortActorAdminKey
            ACCESS  read-only
            DESCRIPTION
                    "dot3adAggPortActorAdminKey is supported as read-only."

        VARIATION   dot3adAggPortActorOperKey
            ACCESS  read-only
            DESCRIPTION
                    "dot3adAggPortActorOperKey is supported as read-only."

        VARIATION   dot3adAggPortPartnerAdminSystemPriority
            ACCESS  read-only
            DESCRIPTION
                    "dot3adAggPortPartnerAdminSystemPriority is supported as
                     read-only."

        VARIATION   dot3adAggPortPartnerAdminSystemID
            ACCESS  read-only
            DESCRIPTION
                    "dot3adAggPortPartnerAdminSystemID is supported as
                    read-only."

        VARIATION   dot3adAggPortPartnerAdminKey
            ACCESS  read-only
            DESCRIPTION
                    "dot3adAggPortPartnerAdminKey is supported as read-only."

--        VARIATION   dot3adAggPortActorPortPriority
--            DESCRIPTION
--                    "dot3adAggPortActorPortPriority is the only writable
--                    object implemented in the dot3adAggPortTable."

        VARIATION   dot3adAggPortPartnerAdminPort
            ACCESS  read-only
            DESCRIPTION
                    "dot3adAggPortPartnerAdminPort is supported as read-only."

        VARIATION   dot3adAggPortPartnerAdminPortPriority
            ACCESS  read-only
            DESCRIPTION
                    "dot3adAggPortPartnerAdminPortPriority is supported as
                    read-only."

        VARIATION   dot3adAggPortActorAdminState
            ACCESS  read-only
            DESCRIPTION
                    "dot3adAggPortActorAdminState is supported as read-only."

        VARIATION   dot3adAggPortPartnerAdminState
            ACCESS  read-only
            DESCRIPTION
                    "dot3adAggPortPartnerAdminState is supported as read-only."

    SUPPORTS        TIMETRA-LAG-MIB
        INCLUDES    {
            tmnxLagInstanceV7v0Group,
            tmnxLagInstanceV9v0Group,
            tmnxLagV6v0NotifGroup,
            tmnxLagV10v0NotifGroup,                        
            tmnxLagHsmdaV6v0Group,
            tmnxLagV8v0Group
        }

        VARIATION  tLagAccessAdaptQos
            DESCRIPTION
                    "The default value for tLagAccessAdaptQos varies based on
                     the MDA type. For an HS-MDA, the default value is
                     'link (1)'."

    ::= { tmnxSROSV10v0 22 }  -- LAG

tmnxSprLAGCapsV10v0    AGENT-CAPABILITIES
    PRODUCT-RELEASE "Alcatel-Lucent SROS"
    STATUS          current
    DESCRIPTION     "Implementation of specific Link Aggregation, LAG,
                     capabilities for Alcatel-Lucent SROS SPR release R10.0"

    SUPPORTS        TIMETRA-LAG-MIB
        INCLUDES    {
            tmnxLagInstanceV7v0Group,
            tmnxLagV6v0NotifGroup,
            tmnxLagV10v0NotifGroup,
-- EXCLUDE  tmnxLagHsmdaV6v0Group,         no Q-MDA on SPR
            tmnxLagV8v0Group
        }

        VARIATION   tLagPortType
            SYNTAX  INTEGER {
                        standard   (1),
                        -- hsmda   (2),
                        hsmdaV2    (3)
                    }
            DESCRIPTION
                    "tLagPortType value of 'hsmda (2)' is not
                    supported."

    ::= { tmnxSROSLAGCapsV10v0 3 }  -- SPR LAG

--
--  LDP CAPABILITIES
--
tmnxSROSLdpCapsV10v0    AGENT-CAPABILITIES
    PRODUCT-RELEASE "Alcatel-Lucent SROS"
    STATUS          current
    DESCRIPTION     "Implementation of LDP capabilities
                     for Alcatel-Lucent SROS release R10.0"

    SUPPORTS        MPLS-LDP-MIB
        INCLUDES    {
            mplsLdpGeneralGroup,
            mplsLdpNotificationsGroup
-- EXCLUDE  mplsLdpGenericGroup
-- EXCLUDE  mplsLdpMappingGroup
-- EXCLUDE  mplsLdpAtmGroup
-- EXCLUDE  mplsLdpFrameRelayGroup
        }

        VARIATION   mplsLdpEntityIndexNext
            ACCESS  not-implemented
            DESCRIPTION
                    "The mplsLdpEntityTable is implemented as read-only.
                    Row entries cannot be created by SNMP SET requests.
                    LDP Entities are created in TIMETRA-LDP-MIB."

        VARIATION   mplsLdpEntityEntry
            CREATION-REQUIRES   { vRtrLdpStatus }
            DESCRIPTION
                    "Row entries cannot be created by SNMP SET requests.

                    Row entries in the mplsLdpEntityTable are created by
                    setting TIMETRA-VRTR-MIB::vRtrLdpStatus to 'create'."

        VARIATION   mplsLdpEntityProtocolVersion
            ACCESS  read-only
            DESCRIPTION
                    "The mplsLdpEntityTable is implemented as read-only."

        VARIATION   mplsLdpEntityAdminStatus
            ACCESS  read-only
            DESCRIPTION
                    "The mplsLdpEntityTable is implemented as read-only."

        VARIATION   mplsLdpEntityWellKnownTcpDiscoveryPort
            ACCESS  read-only
            DESCRIPTION
                    "The mplsLdpEntityTable is implemented as read-only."

        VARIATION   mplsLdpEntityWellKnownUdpDiscoveryPort
            ACCESS  read-only
            DESCRIPTION
                    "The mplsLdpEntityTable is implemented as read-only."

        VARIATION   mplsLdpEntityMaxPduLength
            ACCESS  read-only
            DESCRIPTION
                    "The mplsLdpEntityTable is implemented as read-only."

        VARIATION   mplsLdpEntityKeepAliveHoldTimer
            ACCESS  read-only
            DESCRIPTION
                    "The mplsLdpEntityTable is implemented as read-only."

        VARIATION   mplsLdpEntityHelloHoldTimer
            ACCESS  read-only
            DESCRIPTION
                    "The mplsLdpEntityTable is implemented as read-only."

        VARIATION   mplsLdpEntityFailedInitSessionTrapEnable
            ACCESS  read-only
            DESCRIPTION
                    "The mplsLdpEntityTable is implemented as read-only."

        VARIATION   mplsLdpEntityFailedInitSessionThreshold
            ACCESS  read-only
            DESCRIPTION
                    "The mplsLdpEntityTable is implemented as read-only."

        VARIATION   mplsLdpEntityLabelDistributionMethod
            ACCESS  read-only
            DESCRIPTION
                    "The mplsLdpEntityTable is implemented as read-only."

        VARIATION   mplsLdpEntityLabelRetentionMode
            ACCESS  read-only
            DESCRIPTION
                    "The mplsLdpEntityTable is implemented as read-only."

        VARIATION   mplsLdpEntityPVLimitMismatchTrapEnable
            ACCESS  read-only
            DESCRIPTION
                    "The mplsLdpEntityTable is implemented as read-only."

        VARIATION   mplsLdpEntityPathVectorLimit
            ACCESS  read-only
            DESCRIPTION
                    "The mplsLdpEntityTable is implemented as read-only."

        VARIATION   mplsLdpEntityHopCountLimit
            ACCESS  read-only
            DESCRIPTION
                    "The mplsLdpEntityTable is implemented as read-only."

        VARIATION   mplsLdpEntityTargetedPeer
            ACCESS  read-only
            DESCRIPTION
                    "The mplsLdpEntityTable is implemented as read-only."

        VARIATION   mplsLdpEntityTargetedPeerAddrType
            ACCESS  read-only
            DESCRIPTION
                    "The mplsLdpEntityTable is implemented as read-only."

        VARIATION   mplsLdpEntityTargetedPeerAddr
            ACCESS  read-only
            DESCRIPTION
                    "The mplsLdpEntityTable is implemented as read-only."

        VARIATION   mplsLdpEntityOptionalParameters
            ACCESS  read-only
            DESCRIPTION
                    "The mplsLdpEntityTable is implemented as read-only."

        VARIATION   mplsLdpEntityStorageType
            ACCESS  read-only
            DESCRIPTION
                    "The mplsLdpEntityTable is implemented as read-only."

        VARIATION   mplsLdpEntityRowStatus
            ACCESS  read-only
            DESCRIPTION
                    "The mplsLdpEntityTable is implemented as read-only.
                    Row entries cannot be created by SNMP SET requests.
                    LDP Entities are created in TIMETRA-LDP-MIB and
                    this table when TIMETRA-VRTR-MIB::vRtrLdpStatus
                    is set to 'create'."

        VARIATION   mplsLdpAttemptedSessions
            ACCESS  not-implemented
            DESCRIPTION
                    "The mplsLdpAttemptedSessions is not supported. It is
                      implemented through vRtrLdpStatsAttemptedSessions in
                      TIMETRA-LDP-MIB."

        VARIATION   mplsLdpSessionRejectedNoHelloErrors
            ACCESS  not-implemented
            DESCRIPTION
                    "The mplsLdpSessionRejectedNoHelloErrors is not supported.
                      It is implemented through vRtrLdpStatsSessRejNoHelloErrors
                      in TIMETRA-LDP-MIB."

        VARIATION   mplsLdpSessionRejectedAdvertisementErrors
            ACCESS  not-implemented
            DESCRIPTION
                    "The mplsLdpSessionRejectedAdvertisementErrors is not
                     supported. It is implemented through
                     vRtrLdpStatsSessRejAdvErrors in TIMETRA-LDP-MIB."

        VARIATION   mplsLdpSessionRejectedMaxPduErrors
            ACCESS  not-implemented
            DESCRIPTION
                    "The mplsLdpSessionRejectedMaxPduErrors is not supported.
                     It is implemented through vRtrLdpStatsSessRejMaxPduErrors
                     in TIMETRA-LDP-MIB."

        VARIATION   mplsLdpSessionRejectedLabelRangeErrors
            ACCESS  not-implemented
            DESCRIPTION
                    "The mplsLdpSessionRejectedLabelRangeErrors is not
                     supported. It is implemented through
                     vRtrLdpStatsSessRejLabelRangeErrors in TIMETRA-LDP-MIB."

        VARIATION   mplsLdpBadLdpIdentifierErrors
            ACCESS  not-implemented
            DESCRIPTION
                    "The mplsLdpBadLdpIdentifierErrors is not supported.
                     It is implemented through
                     vRtrLdpStatsBadLdpIdentifierErrors in TIMETRA-LDP-MIB."

        VARIATION   mplsLdpBadPduLengthErrors
            ACCESS  not-implemented
            DESCRIPTION
                    "The mplsLdpBadPduLengthErrors is not supported.
                     It is implemented through vRtrLdpStatsBadPduLengthErrors
                     in TIMETRA-LDP-MIB."

        VARIATION   mplsLdpBadMessageLengthErrors
            ACCESS  not-implemented
            DESCRIPTION
                    "The mplsLdpBadMessageLengthErrors is not supported.
                     It is implemented through
                     vRtrLdpStatsBadMessageLengthErrors in TIMETRA-LDP-MIB."

        VARIATION   mplsLdpBadTlvLengthErrors
            ACCESS  not-implemented
            DESCRIPTION
                    "The mplsLdpBadTlvLengthErrors is not supported.
                     It is implemented through vRtrLdpStatsBadTlvLengthErrors
                     in TIMETRA-LDP-MIB."

        VARIATION   mplsLdpMalformedTlvValueErrors
            ACCESS  not-implemented
            DESCRIPTION
                    "The mplsLdpMalformedTlvValueErrors is not supported.
                     It is implemented through
                     vRtrLdpStatsMalformedTlvValueErrors in TIMETRA-LDP-MIB."

        VARIATION   mplsLdpKeepAliveTimerExpiredErrors
            ACCESS  not-implemented
            DESCRIPTION
                    "The mplsLdpKeepAliveTimerExpiredErrors is not supported.
                     It is implemented through
                     vRtrLdpStatsKeepAliveExpiredErrors in TIMETRA-LDP-MIB."

        VARIATION   mplsLdpShutdownNotifReceived
            ACCESS  not-implemented
            DESCRIPTION
                    "The mplsLdpShutdownNotifReceived is not supported.
                     It is implemented through vRtrLdpStatsShutdownNotifRecv
                     in TIMETRA-LDP-MIB."

        VARIATION   mplsLdpShutdownNotifSent
            ACCESS  not-implemented
            DESCRIPTION
                    "The mplsLdpShutdownNotifSent is not supported.
                     It is implemented through vRtrLdpStatsShutdownNotifSent
                     in TIMETRA-LDP-MIB."

        VARIATION   mplsLdpSessionStatsTable
            ACCESS  not-implemented
            DESCRIPTION
                    "The mplsLdpSessionStatsTable is not supported."

        VARIATION   mplsFecIndexNext
            ACCESS  not-implemented
            DESCRIPTION
                    "The mplsFecTable is not supported."

        VARIATION   mplsFecTable
            ACCESS  not-implemented
            DESCRIPTION
                    "The mplsFecTable is not supported."

        VARIATION   mplsLdpSessionPeerAddressTable
            ACCESS  not-implemented
            DESCRIPTION
                    "The mplsLdpSessionPeerAddressTable is not supported."

        VARIATION   mplsLdpSessionUpDownTrapEnable
            ACCESS  not-implemented
            DESCRIPTION
                    "The generation of MPLS LDP traps is controled by the
                    tmnxEventTable in TIMETRA-LOG-MIB."

        VARIATION   mplsLdpFailedInitSessionThresholdExceeded
            ACCESS  not-implemented
            DESCRIPTION
                    "mplsLdpFailedInitSessionThresholdExceeded notification
                    is not implemented."

        VARIATION   mplsLdpPathVectorLimitMismatch
            ACCESS  not-implemented
            DESCRIPTION
                    "mplsLdpPathVectorLimitMismatch notification
                    is not implemented."

        VARIATION   mplsLdpSessionUp
            ACCESS  not-implemented
            DESCRIPTION
                    "mplsLdpSessionUp notification is not implemented."

        VARIATION   mplsLdpSessionDown
            ACCESS  not-implemented
            DESCRIPTION
                    "mplsLdpSessionDown notification is not implemented."

    SUPPORTS        TIMETRA-LDP-MIB
        INCLUDES    {
            tmnxLdpGlobalV5v0Group,
            tmnxLdpGenExtGlobalV5v0Group,
            tmnxLdpIfV5v0Group,
            tmnxLdpAdjR2r1Group,
            tmnxLdpAggrPreMatchV7v0Group,
            tmnxLdpSessionV5v0Group,
            tmnxLdpServFecV6v0Group,
            tmnxLdpNotificationGroup,
            tmnxLdpStaticFecV3v0Group,
-- EXCLUDE  tmnxLdpAdjBackoffGroup
            tmnxLdpCepTdmFecV6v0Group,
            tmnxLdpServFec129V6v0Group,
            tmnxLdpStatsV7v0Group,
            tmnxLdpGlobalV8v0Group,
            tmnxLdpSessionV8v0Group,
            tmnxLdpStatsV8v0Group,
            tmnxLdpPeerV7v0Group,
            tmnxLdpGlobalV8v0R4Group,
            tmnxLdpServFecV8v0Group,
            tmnxLdpServFec129V8v0Group,
            tmnxLdpGlobalV9v0Group,
            tmnxLdpGlobalV9v0R4Group,
            tmnxLdpP2MPFecV10v0Group,
            tmnxLdpAddressFecV10v0Group,
            tmnxLdpAddrActiveFecV10v0Group
        }

        VARIATION   vRtrLdpGenDeaggregateFec
            ACCESS  read-only
            DESCRIPTION
                    "vRtrLdpGenDeaggregateFec is implemented as read-only."

        VARIATION   vRtrLdpGenRoutePreference
            ACCESS  read-only
            DESCRIPTION
                    "vRtrLdpGenRoutePreference is implemented as read-only."

        VARIATION   vRtrLdpGenPropagatePolicy
            ACCESS  read-only
            DESCRIPTION
                    "vRtrLdpGenPropagatePolicy is implemented as read-only."

        VARIATION   vRtrLdpGenLoopDetectCapable
            ACCESS  read-only
            DESCRIPTION
                    "vRtrLdpGenLoopDetectCapable is implemented as read-only."

        VARIATION   vRtrLdpGenHopLimit
            ACCESS  read-only
            DESCRIPTION
                    "vRtrLdpGenHopLimit is implemented as read-only."

        VARIATION   vRtrLdpGenPathVectorLimit
            ACCESS  read-only
            DESCRIPTION
                    "vRtrLdpGenPathVectorLimit is implemented as read-only."

        VARIATION   vRtrLdpGenBackoffTime
            ACCESS  read-only
            DESCRIPTION
                    "vRtrLdpGenBackoffTime is implemented as read-only."

        VARIATION   vRtrLdpGenMaxBackoffTime
            ACCESS  read-only
            DESCRIPTION
                    "vRtrLdpGenMaxBackoffTime is implemented as read-only."

        VARIATION   vRtrLdpGenTargPassiveMode
            ACCESS  read-only
            DESCRIPTION
                    "vRtrLdpGenTargPassiveMode is implemented as read-only."

        VARIATION   vRtrLdpIfTableSpinlock
            ACCESS  not-implemented
            DESCRIPTION
                    "vRtrLdpIfTableSpinlock is not implemented."

        VARIATION   vRtrLdpIfBackoffTime
            ACCESS  read-only
            DESCRIPTION
                    "vRtrLdpIfBackoffTime is implemented as read-only."

        VARIATION   vRtrLdpIfMaxBackoffTime
            ACCESS  read-only
            DESCRIPTION
                    "vRtrLdpIfMaxBackoffTime is implemented as read-only."

        VARIATION   vRtrLdpIfPassiveMode
            ACCESS  read-only
            DESCRIPTION
                    "vRtrLdpIfPassiveMode is implemented as read-only."

        VARIATION   vRtrLdpPeerTTLLogId
            ACCESS  not-implemented
            DESCRIPTION
                    "vRtrLdpPeerTTLLogId is not implemented."

        VARIATION   vRtrLdpGenTrustList
            ACCESS  not-implemented
            DESCRIPTION
                    "vRtrLdpGenTrustList is not implemented. This object
                     was made obsolete in the 5.0-R3 release."

        VARIATION   vRtrLdpEgrStatFecPfxRowStatus
            DESCRIPTION
                    "vRtrLdpEgrStatFecPfxRowStatus supports only 'ipv4'
                    indices.  If an attempt is made to create a row entry with
                    the vRtrLdpEgrStatFecPfxAddrType index set to a value other
                    than 'ipv4', a 'noCreation' error will be returned."

    ::= { tmnxSROSV10v0 23 }  -- LDP

--
--  EVENT LOGGING CAPABILITIES
--
tmnxSROSLogCapsV10v0    AGENT-CAPABILITIES
    PRODUCT-RELEASE "Alcatel-Lucent SROS"
    STATUS          current
    DESCRIPTION     "Implementation of event logging capabilities
                     for Alcatel-Lucent SROS release R10.0"

    SUPPORTS        NOTIFICATION-LOG-MIB
        INCLUDES    {
            notificationLogConfigGroup,
            notificationLogStatsGroup,
            notificationLogLogGroup,
            notificationLogDateGroup
        }

        VARIATION   nlmConfigGlobalEntryLimit
            ACCESS  read-only
            DESCRIPTION
                    "nlmConfigGlobalEntryLimit is implemented as read-only."

        VARIATION   nlmConfigGlobalAgeOut
            ACCESS  read-only
            DESCRIPTION
                    "nlmConfigGlobalAgeOut is implemented as read-only."

        VARIATION   nlmConfigLogStorageType
            ACCESS  read-only
            DESCRIPTION
                    "nlmConfigLogStorageType is implemented as read-only."

        VARIATION   nlmConfigLogEntryStatus
            SYNTAX  INTEGER {
                        active (1)
                    }
            ACCESS  read-only
            DESCRIPTION
                    "nlmConfigLogEntryStatus is implemented as read-only.
                    Row entries cannot be created by SNMP SET requests.
                    Notification logs are created using the TIMETRA-LOG-MIB."

    SUPPORTS        TIMETRA-LOG-MIB
        INCLUDES    {
            tmnxLogGlobalGroup,
            tmnxLogV5v0Group,
            tmnxLogAccountingPolicyGroup,
            tmnxLogAccountingPolicyV6v1Group,
            tmnxLogAccountingPolicyCRV7v0Group,
            tmnxLogFileIdGroup,
            tmnxLogSyslogV5v0Group,
            tmnxSnmpTrapV5v0Group,
            tmnxSnmpTrapDestV6v0Group,
            tmnxSnmpSetErrsGroup,
            tmnxLogEventsV5v0Group,
            tmnxLogNotificationV6v0Group,
            tmnxLogNotificationV9v0Group,
            tmnxLogRoutePreferenceV7v0Group,
            tmnxLogEventDampedV8v0Group,
            tmnxLogApV9v0Group,
            tmnxLogExRbkOpGroup,
            tmnxLogApExtGroup,
            tmnxLogAppRouteNotifV10v0Group
        }

        VARIATION   tmnxLogApRowStatus
            SYNTAX  INTEGER {
                    active (1),
                    -- notInService (2),
                    -- notReady (3),
                    createAndGo (4),
                    -- createAndWait (5),
                    destroy (6)
                }
            DESCRIPTION
                    "tmnxLogApRowStatus supports only 'active (1)',
                    'createAndGo (4)' and 'destroy (6)'."

        VARIATION   tmnxLogApCrQueueRowStatus
            SYNTAX  INTEGER {
                    active (1),
                    -- notInService (2),
                    -- notReady (3),
                    createAndGo (4),
                    -- createAndWait (5),
                    destroy (6)
                }
            DESCRIPTION
                    "tmnxLogApCrQueueRowStatus supports only 'active (1)',
                    'createAndGo (4)' and 'destroy (6)'."

        VARIATION   tmnxLogApCrOverrideCntrRowStatus
            SYNTAX  INTEGER {
                    active (1),
                    -- notInService (2),
                    -- notReady (3),
                    createAndGo (4),
                    -- createAndWait (5),
                    destroy (6)
                }
            DESCRIPTION
                    "tmnxLogApCrOverrideCntrRowStatus supports only
                    'active (1)', 'createAndGo (4)' and 'destroy (6)'."

        VARIATION   tmnxLogApAdminStatus
            SYNTAX  INTEGER {
                    -- noop (1),
                    inService (2),
                    outOfService (3)
                }
            DESCRIPTION
                    "tmnxLogApAdminStatus supports only 'inService (2)' and
                    'outOfService (3)'."

        VARIATION   tmnxLogIdAdminStatus
            SYNTAX  INTEGER {
                    -- noop (1),
                    inService (2),
                    outOfService (3)
                }
            DESCRIPTION
                    "tmnxLogIdAdminStatus supports only 'inService (2)' and
                    'outOfService (3)'."

        VARIATION   tmnxLogFilterParamsApplOperator
            SYNTAX  INTEGER {
                    off (1),
                    equal (2),
                    notEqual (3)
                    -- lessThan (4),
                    -- lessThanOrEqual (5),
                    -- greaterThan (6),
                    -- greaterThanOrEqual (7)
                    }
            DESCRIPTION
                    "tmnxLogFilterParamsApplOperator supports only 'off (1)',
                    'equal (2)', and 'notEqual (3)'."

        VARIATION   tmnxLogFilterParamsSubjectOperator
            SYNTAX  INTEGER {
                    off (1),
                    equal (2),
                    notEqual (3)
                    -- lessThan (4),
                    -- lessThanOrEqual (5),
                    -- greaterThan (6),
                    -- greaterThanOrEqual (7)
                    }
            DESCRIPTION
                    "tmnxLogFilterParamsSubjectOperator supports only 'off (1)',
                    'equal (2)', and 'notEqual (3)'."

        VARIATION   tmnxLogFilterParamsRouterOperator
            SYNTAX  INTEGER {
                    off (1),
                    equal (2),
                    notEqual (3)
                    -- lessThan (4),
                    -- lessThanOrEqual (5),
                    -- greaterThan (6),
                    -- greaterThanOrEqual (7)
                    }
            DESCRIPTION
                    "tmnxLogFilterParamsRouterOperator supports only 'off (1)',
                    'equal (2)', and 'notEqual (3)'."

        VARIATION   tmnxEventSeverity
            DESCRIPTION
                    "An attempt to set tmnxEventSeverity to value 'none(0)'
                     will result in a 'wrongValue' error."
        
        VARIATION   tmnxLogApCrAACounters
            SYNTAX INTEGER {                    
                    -- any (0),
                    sfa (1),
                    nfa (2),
                    sfd (3),
                    nfd (4),
                    saf (5),
                    naf (6),
                    spa (7),
                    npa (8),
                    sba (9),
                    nba (10),
                    spd (11),
                    npd (12),
                    sbd (13),
                    nbd (14),
                    sdf (15),
                    mdf (16),
                    ldf (17),
                    tfd (18),
                    tfc (19),
                    sbm (20),
                    spm (21),
                    smt (22),
                    nbm (23),
                    npm (24),
                    nmt (25)
                    }
        DESCRIPTION
                "An attempt to set tmnxLogApCrAACounters to value 'any (0)' will
                 result in a 'wrongValue' error."

        VARIATION tmnxLogApCrSignChangeAACounters
            SYNTAX INTEGER {
                    any (0)
                    -- sfa (1),
                    -- nfa (2),
                    -- sfd (3),
                    -- nfd (4),
                    -- saf (5),
                    -- naf (6),
                    -- spa (7),
                    -- npa (8),
                    -- sba (9),
                    -- nba (10),
                    -- spd (11),
                    -- npd (12),
                    -- sbd (13),
                    -- nbd (14),
                    -- sdf (15),
                    -- mdf (16),
                    -- ldf (17),
                    -- tfd (18),
                    -- tfc (19),
                    -- sbm (20),
                    -- spm (21),
                    -- smt (22),
                    -- nbm (23),
                    -- npm (24),
                    -- nmt (25),
                    }
            DESCRIPTION
                    "An attempt to set tmnxLogApCrSignChangeAACounters to a 
                     value other than 'any (0)' will result in a 'wrongValue'
                     error."

    ::= { tmnxSROSV10v0 24 }  -- LOG

tmnx7710LogCapsV10v0    AGENT-CAPABILITIES
    PRODUCT-RELEASE "Alcatel-Lucent SROS"
    STATUS          current
    DESCRIPTION     "Implementation of specific event logging capabilities
                     for Alcatel-Lucent SROS 7710 release R10.0"

    SUPPORTS        TIMETRA-LOG-MIB
        INCLUDES    {
            tmnxLogAccountingPolicyGroup
        }

        VARIATION   tmnxLogApRecord
            SYNTAX  INTEGER {
                    none (0),
                    svcIngressOctet (1),
                    svcEgressOctet (2),
                    svcIngressPkt (3),
                    svcEgressPkt (4),
                    netIngressOctet (5),
                    netEgressOctet (6),
                    netIngressPkt (7),
                    netEgressPkt (8),
                    compactSvcInOctet (9),
                    combinedSvcIngress (10),
                    combinedNetInEgOctet (11),
                    combinedSvcInEgOctet (12),
                    completeSvcInEg (13),
                    combinedSvcSdpInEg (14),
                    completeSvcSdpInEg (15),
                    completeSubscrIngrEgr (16),
                    -- bsxProtocol              (17)
                    -- bsxApplication           (18)
                    -- bsxAppGroup              (19)
                    -- bsxSubscriberProtocol    (20)
                    -- bsxSubscriberApplication (21)
                    -- bsxSubscriberAppGroup    (22)
                    customRecordSubscriber (23),
                    customRecordService (24),
                    customRecordAa (25),
                    queueGroupOctets (26),
                    queueGroupPackets (27),
                    combinedQueueGroup (28),
                    combinedMplsLspIngress (29),
                    combinedMplsLspEgress (30),
                    combinedLdpLspEgress (31),
                    saa (32)
                }
            DESCRIPTION
                    "The BSX (Application Assurance) record
                     types are not supported on SROS 7710 systems."

        VARIATION   tmnxLogApPortType
            SYNTAX  INTEGER {
                    none       (0),
                    access     (1),
                    network    (2),
                    sdp        (3),
                    subscriber (4)
                    -- appAssure  (5)
                }
            DESCRIPTION
                    "The BSX (Application Assurance) port
                     type is not supported on SROS 7710 systems."

    ::= { tmnxSROSLogCapsV10v0 3 }  -- 7710 LOG

tmnx7950LogCapsV10v0    AGENT-CAPABILITIES
    PRODUCT-RELEASE "Alcatel-Lucent SROS"
    STATUS          current
    DESCRIPTION     "Implementation of specific event logging capabilities
                     for Alcatel-Lucent SROS 7950 release R10.0"

    SUPPORTS        TIMETRA-LOG-MIB
        INCLUDES    {
            tmnxLogAccountingPolicyGroup
                }

        VARIATION   tmnxLogApRecord
            SYNTAX  INTEGER {
                       none                      (0),
                       svcIngressOctet           (1),
                       svcEgressOctet            (2),
                       svcIngressPkt             (3),
                       svcEgressPkt              (4),
                       netIngressOctet           (5),
                       netEgressOctet            (6),
                       netIngressPkt             (7),
                       netEgressPkt              (8),
                       compactSvcInOctet         (9),
                       combinedSvcIngress       (10),
                       combinedNetInEgOctet     (11),
                       combinedSvcInEgOctet     (12),
                       completeSvcInEg          (13),
                       combinedSvcSdpInEg       (14),
                       completeSvcSdpInEg       (15),
                       completeSubscrIngrEgr    (16),
                    -- bsxProtocol              (17)
                    -- bsxApplication           (18)
                    -- bsxAppGroup              (19)
                    -- bsxSubscriberProtocol    (20)
                    -- bsxSubscriberApplication (21)
                    -- bsxSubscriberAppGroup    (22)
                       customRecordSubscriber   (23),
                       customRecordService      (24),
                       customRecordAa           (25),
                       queueGroupOctets         (26),
                       queueGroupPackets        (27),
                       combinedQueueGroup       (28),
                       combinedMplsLspIngress   (29),
                       combinedMplsLspEgress    (30),
                       combinedLdpLspEgress     (31),
                       saa                      (32)
                }
            DESCRIPTION
                    "The BSX (Application Assurance) record
                     types are not supported on SROS 7950 systems."

        VARIATION   tmnxLogApPortType
            SYNTAX  INTEGER {
                       none       (0),
                       access     (1),
                       network    (2),
                       sdp        (3),
                       subscriber (4)
                    -- appAssure  (5)
                }
            DESCRIPTION
                    "The BSX (Application Assurance) port
                     type is not supported on SROS 7950 systems."

    ::= { tmnxSROSLogCapsV10v0 4 }  -- 7950 LOG
--
--  MIRROR CAPABILITIES
--
tmnxSROSMirrorCapsV10v0    AGENT-CAPABILITIES
    PRODUCT-RELEASE "Alcatel-Lucent SROS"
    STATUS          current
    DESCRIPTION     "Implementation of port mirroring capabilities
                     for Alcatel-Lucent SROS release R10.0"

    SUPPORTS        TIMETRA-MIRROR-MIB
        INCLUDES    {
            tMirrorDestinationV8v0Group,
            tMirrorDestV8v0Group,
            tMirrorDestinationR2r1RemoteSourceGroup,
            tMirrorSourceV10v0Group,
            tMirrorNotificationsGroup,
            tMirrorSourceNotificationsV6v0Group,
-- EXCLUDE  tMirrorBsxV6v0Group
            tMirrorRadiusLiV8v0Group,
            tMirrorSourceNotifGroup,
            tMirrorLiGroup,
            tMirrorEncapV10v0Group,
            tMirrorNotifV10v0Group,
            tMirrorLiSourceV10v0Group
        }

        VARIATION   tMirrorDestinationEncapsulation
            SYNTAX  INTEGER {
                        ether           (1),
                        frameRelay      (2),
                        ppp             (3),
                        atmSdu          (4),
                        satopE1         (5),
                        satopT1         (6),
                        -- satopE3      (7),
                        -- satopT3      (8),
                        cesopsn         (9),
                        cesopsnCas      (10)
                    }
            DESCRIPTION
                    "The values
                        - 'satopE3 (7)',
                        - 'satopT3 (8)',
                        are invalid on a SROS system, as they are not
                        implemented."

        VARIATION   tMirrorSourceRemovedBySystem
            ACCESS  not-implemented
            DESCRIPTION
                    "tMirrorSourceRemovedBySystem notification is not
                    implemented."

        VARIATION   tMirrorSourceSubIpAddrType
            SYNTAX  INTEGER {
                        unknown     (0),
                        ipv4        (1)
                        -- ipv6     (2),
                        -- ipv4z    (3),
                        -- ipv6z    (4),
                        -- dns      (16)
                    }
            DESCRIPTION
                    "tMirrorSourceSubIpAddrType supports only InetAddressType
                    values 'unknown (0)' and 'ipv4 (1)'."

        VARIATION   tMirrorSourceSubIpAddr
            SYNTAX  InetAddress (SIZE (0|4))
            DESCRIPTION
                    "The tMirrorSourceSubIpAddr supports only InetAddressType
                    values 'unknown (0)' and 'ipv4 (1)'."

    ::= { tmnxSROSV10v0 25 }  -- MIRROR

tmnx7750MirrorCapsV10v0    AGENT-CAPABILITIES
    PRODUCT-RELEASE "Alcatel-Lucent SROS"
    STATUS          current
    DESCRIPTION     "Implementation of port mirroring capabilities
                     for Alcatel-Lucent 7750 release R10.0"

    SUPPORTS        TIMETRA-MIRROR-MIB
        INCLUDES    {
            tMirrorBsxV6v0Group,
            tMirrorDestinationV8v0Group
        }

        VARIATION   tMirrorDestinationEncapsulation
            SYNTAX  INTEGER {
                        ether       (1),
                        frameRelay  (2),
                        ppp         (3),
                        atmSdu      (4),
                        satopE1     (5),
                        satopT1     (6),
                    -- satopE3      (7)
                    -- satopT3      (8)
                        cesopsn     (9),
                        cesopsnCas (10)
                    }
            DESCRIPTION
                    "The values
                        - 'satopE3 (7)',
                        - 'satopT3 (8)',
                        are invalid on a 7750 system, as they are not
                        implemented."

    ::= { tmnxSROSMirrorCapsV10v0 1 }  -- 7750 MIRROR

tmnx7450MirrorCapsV10v0    AGENT-CAPABILITIES
    PRODUCT-RELEASE "Alcatel-Lucent SROS"
    STATUS          current
    DESCRIPTION     "Implementation of specific port mirroring capabilities for
                     Alcatel-Lucent SROS 7450 release R10.0"

    SUPPORTS        TIMETRA-MIRROR-MIB
        INCLUDES    {
            tMirrorBsxV6v0Group,
            tMirrorDestinationV8v0Group
        }

        VARIATION   tMirrorDestinationEncapsulation
            SYNTAX  INTEGER {
                        ether           (1),
                        frameRelay      (2),
                        ppp             (3),
                        atmSdu          (4)
                    -- satopE1      (5)
                    -- satopT1      (6)
                    -- satopE3      (7)
                    -- satopT3      (8)
                    -- cesopsn      (9)
                        -- cesopsnCas   (10)
                    }
            DESCRIPTION
                    "The values
                        - 'satopE1     (5)',
                        - 'satopT1     (6)',
                        - 'cesopsn     (9)',
                        - 'cesopsnCas (10)'
                        are invalid on a SROS 7450 system, as
                        Circuit Emulation (CEM) is not supported."

    ::= { tmnxSROSMirrorCapsV10v0 2 }  -- 7450 MIRROR

tmnxSprMirrorCapsV10v0    AGENT-CAPABILITIES
    PRODUCT-RELEASE "Alcatel-Lucent SROS"
    STATUS          current
    DESCRIPTION     "Implementation of specific port mirroring capabilities
                     for Alcatel-Lucent SROS SPR release R10.0"

    SUPPORTS        TIMETRA-MIRROR-MIB
        INCLUDES    {
            tMirrorDestinationV8v0Group,
            tMirrorDestV8v0Group,
            tMirrorDestinationR2r1RemoteSourceGroup,
            tMirrorSourceV10v0Group,
            tMirrorNotificationsGroup,
            tMirrorSourceNotificationsV6v0Group,
            tMirrorRadiusLiV8v0Group
        }

        VARIATION   tMirrorDestinationEncapsulation
            SYNTAX  INTEGER {
                       ether        (1),
                       frameRelay   (2),
                       ppp          (3),
                       atmSdu       (4),
                       satopE1      (5),
                       satopT1      (6),
                    -- satopE3      (7)
                    -- satopT3      (8)
                       cesopsn      (9),
                       cesopsnCas  (10)
                    }
            DESCRIPTION
                    "The values
                        - 'satopE3 (7)',
                        - 'satopT3 (8)',
                        are invalid on a SPR system, as they are not
                        implemented."

    ::= { tmnxSROSMirrorCapsV10v0 3 }  -- SPR MIRROR

--
--  MPLS CAPABILITIES
--
tmnxSROSMplsCapsV10v0    AGENT-CAPABILITIES
    PRODUCT-RELEASE "Alcatel-Lucent SROS"
    STATUS          current
    DESCRIPTION     "Implementation of MPLS protocol capabilities
                     for Alcatel-Lucent SROS release R10.0"

    SUPPORTS        MPLS-LSR-MIB
        INCLUDES    {
            mplsInSegmentGroup,
            mplsOutSegmentGroup,
            mplsXCGroup,
            mplsInterfaceGroup,
-- EXCLUDE  mplsPerfGroup,
-- EXCLUDE  mplsSegmentDiscontinuityGroup,
-- EXCLUDE  mplsHCInSegmentPerfGroup,
-- EXCLUDE  mplsHCOutSegmentPerfGroup,
            mplsTrafficParamGroup,
-- EXCLUDE  mplsLabelStackGroup
            mplsXCIsPersistentGroup,
            mplsXCIsNotPersistentGroup,
            mplsLsrNotificationGroup
        }

        VARIATION   mplsOutSegmentTrafficParamPtr
            ACCESS  read-only
            DESCRIPTION
                    "The mplsOutSegmentTrafficParamPtr is implemented as
                     read-only."

        VARIATION   mplsInSegmentTrafficParamPtr
            ACCESS  read-only
            DESCRIPTION
                    "The mplsInSegmentTrafficParamPtr is implemented as
                     read-only."

        VARIATION   mplsXCAdminStatus
            SYNTAX  INTEGER {
                        up      (1),       -- ready to pass packets
                        down    (2)
                    }
            DESCRIPTION
                    "Write access using value 'testing (3)' is not supported."

        VARIATION   mplsTrafficParamMaxRate
            ACCESS  read-only
            DESCRIPTION
                    "The mplsTrafficParamTable is implemented as read-only."

        VARIATION   mplsTrafficParamMeanRate
            ACCESS  read-only
            DESCRIPTION
                    "The mplsTrafficParamTable is implemented as read-only."

        VARIATION   mplsTrafficParamMaxBurstSize
            ACCESS  read-only
            DESCRIPTION
                    "The mplsTrafficParamTable is implemented as read-only."

-- How are row entries created in this table?
        VARIATION   mplsTrafficParamRowStatus
            ACCESS  read-only
            DESCRIPTION
                    "The mplsTrafficParamTable is implemented as read-only.
                    Row entries cannot be created by SNMP SET requests."

        VARIATION   mplsTrafficParamStorageType
            ACCESS  read-only
            DESCRIPTION
                    "The mplsTrafficParamTable is implemented as read-only."

        VARIATION   mplsOutSegmentNextHopIpv6Addr
            ACCESS  not-implemented
            DESCRIPTION
                    "IPv6 MPLS is not implemented on Alcatel-Lucent SROS
                    systems."

        VARIATION   mplsInSegmentPerfTable
            ACCESS  not-implemented
            DESCRIPTION
                    "mplsInSegmentPerfTable is not implemented on Alcatel-Lucent
                     SROS systems."

        VARIATION   mplsOutSegmentPerfTable
            ACCESS  not-implemented
            DESCRIPTION
                    "mplsOutSegmentPerfTable is not implemented on
                     Alcatel-Lucent SROS systems."

        VARIATION   mplsXCLspId
            ACCESS  read-only
            DESCRIPTION
                    "mplsXCLspId is implemented as read-only."

        VARIATION   mplsXCLabelStackIndex
            ACCESS  read-only
            DESCRIPTION
                    "mplsXCLabelStackIndex is implemented as read-only."

        VARIATION   mplsXCIsPersistent
            ACCESS  read-only
            DESCRIPTION
                    "mplsXCIsPersistent is implemented as read-only."

        VARIATION   mplsXCTrapEnable
            ACCESS  not-implemented
            DESCRIPTION
                    "Generation of MPLS traps is controled by the
                    TIMETRA-LOG-MIB tmnxEventTable."

        VARIATION   mplsInterfaceConfStorageType
            ACCESS  read-only
            DESCRIPTION
                    "mplsInterfaceConfStorageType is implemented as read-only."

    SUPPORTS        MPLS-TE-MIB
        INCLUDES    {
            mplsTunnelGroup,
            mplsTunnelManualGroup,
            mplsTunnelSignaledGroup,
            mplsTunnelIsNotIntfcGroup,
            mplsTunnelIsIntfcGroup,
            mplsTunnelOptionalGroup
-- EXCLUDE  mplsTeNotificationGroup
        }

        VARIATION   mplsTunnelAdminStatus
            SYNTAX  INTEGER {
                        up      (1),       -- ready to pass packets
                        down    (2)
                    }
            DESCRIPTION
                    "Write access using value 'testing (3)' is not supported."

        VARIATION   mplsTunnelResourcePointer
            ACCESS  read-only
            DESCRIPTION
                    "mplsTunnelResourceTable is not implemented and
                    mplsTunnelResourcePointer always returns the null
                    identifier value { ccitt 0 }."

        VARIATION   mplsTunnelResourceIndexNext
            ACCESS  not-implemented
            DESCRIPTION
                    "mplsTunnelResourceTable is not implemented."

        VARIATION   mplsTunnelResourceTable
            ACCESS  not-implemented
            DESCRIPTION
                    "mplsTunnelResourceTable is not implemented."

        VARIATION   mplsTunnelEntry
            CREATION-REQUIRES   {   mplsTunnelRowStatus,
                                    mplsTunnelName
                                }
            DESCRIPTION
                    "mplsTunnelName must be set for row creation to succeed.
                    The value of these objects cannot be changed after the
                    row entry has been created:
                        mplsTunnelDescr, mplsTunnelIsIf,
                        mplsTunnelSignallingProto,
                        mplsTunnelSetupPrio, mplsTunnelHoldingPrio,
                        mplsTunnelOwner, mplsTunnelLocalProtectInUse,
                        mplsTunnelResourcePointer, mplsTunnelSessionAttributes,
                        mplsTunnelInstancePriority."

        VARIATION   mplsTunnelRowStatus
            SYNTAX  INTEGER {
                        active      (1),
                        createAndGo (4),
                        destroy     (6)
                     }
            DESCRIPTION
                    "mplsTunnelRowStatus supports only the values
                    'active (1)', 'createAndGo (4)' and 'destroy (6)'."

        VARIATION   mplsTunnelHopIpv6Addr
            ACCESS  not-implemented
            DESCRIPTION
                    "IPv6 MPLS is not implemented."

        VARIATION   mplsTunnelHopIpv6PrefixLen
            ACCESS  not-implemented
            DESCRIPTION
                    "IPv6 MPLS is not implemented."

        VARIATION   mplsTunnelHopAsNumber
            ACCESS  not-implemented
            DESCRIPTION
                    "mplsTunnelHopAsNumber is not implemented on Alcatel-Lucent
                     SROS systems."

        VARIATION   mplsTunnelHopLspId
            ACCESS  not-implemented
            DESCRIPTION
                    "mplsTunnelHopLspId is not implemented on Alcatel-Lucent
                     SROS systems."

        VARIATION   mplsTunnelARHopIpv6Addr
            ACCESS  not-implemented
            DESCRIPTION
                    "IPv6 MPLS is not implemented."

        VARIATION   mplsTunnelARHopIpv6PrefixLen
            ACCESS  not-implemented
            DESCRIPTION
                    "IPv6 MPLS is not implemented."

-- NOTE: mplsTunnelTrapEnable should be implemented and tied to the logger
--       event controls.
        VARIATION   mplsTunnelTrapEnable
            ACCESS  not-implemented
            DESCRIPTION
                    "Control of MPLS traps is managed using the tmnxEventTable
                    in the TIMETRA-LOG-MIB."

        VARIATION   mplsTunnelHopTableIndex
            ACCESS  read-only
            DESCRIPTION
                    "mplsTunnelHopTableIndex is implemented as read-only.
                     The value of mplsTunnelHopTableIndex is the same as
                     mplsTunnelIndex."

        VARIATION   mplsTunnelIsIf
            ACCESS  read-only
            DESCRIPTION
                    "mplsTunnelIsIf is implemented as read-only."

        VARIATION   mplsTunnelXCPointer
            ACCESS  read-only
            DESCRIPTION
                    "mplsTunnelXCPointer is implemented as read-only."

        VARIATION   mplsTunnelSignallingProto
            ACCESS  read-only
            DESCRIPTION
                    "mplsTunnelSignallingProto is implemented as read-only."

        VARIATION   mplsTunnelSetupPrio
            ACCESS  read-only
            DESCRIPTION
                    "mplsTunnelSetupPrio is implemented as read-only."

        VARIATION   mplsTunnelHoldingPrio
            ACCESS  read-only
            DESCRIPTION
                    "mplsTunnelHoldingPrio is implemented as read-only."

        VARIATION   mplsTunnelSessionAttributes
            ACCESS  read-only
            DESCRIPTION
                    "mplsTunnelSessionAttributes is implemented as read-only."

        VARIATION   mplsTunnelOwner
            ACCESS  read-only
            DESCRIPTION
                    "mplsTunnelOwner is implemented as read-only."

        VARIATION   mplsTunnelLocalProtectInUse
                    ACCESS  read-only
                    DESCRIPTION
                    "mplsTunnelLocalProtectInUse is implemented as read-only."

        VARIATION   mplsTunnelInstancePriority
            ACCESS  read-only
            DESCRIPTION
                    "mplsTunnelInstancePriority is implemented as read-only."

        VARIATION   mplsTunnelName
            SYNTAX  DisplayString (SIZE(0..32))
            DESCRIPTION
                    "The maximum length supported for the mplsTunnelName is 32
                     characters."

    SUPPORTS        TIMETRA-MPLS-MIB
        INCLUDES    {
            tmnxMplsGlobalV6v0Group,
            tmnxMplsLspV5v0Group,
            tmnxMplsLspPathV6v0Group,
            tmnxMplsLspPathV6v1Group,
            tmnxMplsLspPathV7v0Group,
            tmnxMplsLspPathV8v0Group,
            tmnxMplsXCGroup,
            tmnxMplsIfGroup,
            tmnxMplsTunnelARHopGroup,
            tmnxMplsTunnelCHopGroup,
            tmnxMplsAdminGroupGroup,
            tmnxMplsNotificationR2r1Group,
            tmnxMplsLabelRangeGroup,
            tmnxMplsSrlgV6v0Group,
            tmnxMplsIfV6v0Group,
            tmnxMplsLspV6v0Group,
            tmnxMplsLspV7v0Group,
            tmnxMplsGlobalV7v0Group,
            tmnxMplsP2mpInstanceGroup,
            tmnxMplsP2mpS2lGroup,
            tmnxMplsNotificationV7v0Group,
            tmnxMplsSrlgV7v0Group,
            tmnxMplsNotifyObjsV8v0Group,
            tmnxMplsNotificationV8v0Group,
            tmnxMplsGlobalV8v0Group,
            tmnxMplsLspV8v0Group,
            tmnxMplsLspStatsV7v0Group,
            tmnxMplsLspAutoBWV8v0Group,
            tmnxMplsLspTemplateV8v0Group,
            tmnxMplsGlobalV9v0Group,
            tmnxMplsLspV9v0Group,
            tmnxMplsLspV9v0R4Group,
            tmnxMplsNotifV9v0R4Group,
            tmnxMplsLspPathV9v0R4Group,
            tmnxMplsGlobalV10v0Group,
            tmnxMplsNotifyV10v0Group
        }

        VARIATION   vRtrMplsLspInheritance
            ACCESS  read-only
            DESCRIPTION
                    "vRtrMplsLspInheritance is implemented as read-only."

--- This object should be removed from TIMETRA-MPLS-MIB
        VARIATION   vRtrMplsLspPathTableSpinlock
            ACCESS  not-implemented
            DESCRIPTION
                    "The vRtrMplsLspPathTableSpinlock was intended to be used
                    for control of changes to inherited attributes.  There
                    are no inherited attributes in the base version of
                    MPLS on Alcatel-Lucent SROS systems."

        VARIATION   vRtrMplsLspDecrementTtl
            ACCESS  read-only
            DESCRIPTION
                    "vRtrMplsLspDecrementTtl is implemented as read-only."

        VARIATION   vRtrMplsLspClassOfService
            ACCESS  read-only
            DESCRIPTION
                    "vRtrMplsLspClassOfService is implemented as read-only."

        VARIATION   vRtrMplsLspSetupPriority
            ACCESS  read-only
            DESCRIPTION
                    "vRtrMplsLspSetupPriority is implemented as read-only."

        VARIATION   vRtrMplsLspHoldPriority
            ACCESS  read-only
            DESCRIPTION
                    "vRtrMplsLspHoldPriority is implemented as read-only."

        VARIATION   vRtrMplsLspRecord
            ACCESS  read-only
            DESCRIPTION
                    "vRtrMplsLspRecord is implemented as read-only."

        VARIATION   vRtrMplsLspBandwidth
            ACCESS  read-only
            DESCRIPTION
                    "vRtrMplsLspBandwidth is implemented as read-only."

        VARIATION   vRtrMplsLspOptimizeTimer
            ACCESS  read-only
            DESCRIPTION
                    "vRtrMplsLspOptimizeTimer is implemented as read-only."

        VARIATION   vRtrMplsLspFRObject
            ACCESS  read-only
            DESCRIPTION
                    "vRtrMplsLspFRObject is implemented as read-only."

        VARIATION   vRtrMplsLspPathCos
            ACCESS  read-only
            DESCRIPTION
                    "vRtrMplsLspPathCos is implemented as read-only."

        VARIATION   vRtrMplsLspPathCosSource
            ACCESS  read-only
            DESCRIPTION
                    "vRtrMplsLspPathCosSource is implemented as read-only."

        VARIATION   vRtrMplsLspPathClassOfService
            ACCESS  read-only
            DESCRIPTION
                    "vRtrMplsLspPathClassOfService is implemented as
                     read-only."

        VARIATION   vRtrMplsLspPathOptimizeTimer
            ACCESS  read-only
            DESCRIPTION
                    "vRtrMplsLspPathOptimizeTimer is implemented as read-only."

        VARIATION   vRtrMplsGeneralPropagateTtl
            ACCESS  read-only
            DESCRIPTION
                    "vRtrMplsGeneralPropagateTtl is implemented as read-only."

        VARIATION   vRtrMplsGeneralTE
            ACCESS  read-only
            DESCRIPTION
                    "vRtrMplsGeneralTE is implemented as read-only."

        VARIATION   vRtrMplsGeneralOptimizeTimer
            ACCESS  read-only
            DESCRIPTION
                    "vRtrMplsGeneralOptimizeTimer is implemented as read-only."

        VARIATION   vRtrMplsLspBwProtect
            ACCESS  read-only
            DESCRIPTION
                    "vRtrMplsLspBwProtect is implemented as read-only."

        VARIATION   vRtrMplsLspPathBwProtect
            ACCESS  read-only
            DESCRIPTION
                    "vRtrMplsLspPathBwProtect is implemented as read-only."

        VARIATION   vRtrMplsLspPreference
            ACCESS  read-only
            DESCRIPTION
                    "vRtrMplsLspPreference is implemented as read-only."

        VARIATION   vRtrMplsLspPathSharing
            ACCESS  read-only
            DESCRIPTION
                    "vRtrMplsLspPathSharing is implemented as read-only."

        VARIATION   vRtrMplsLspOctets
            ACCESS  not-implemented
            DESCRIPTION
                    "vRtrMplsLspOctets is not implemented."

        VARIATION   vRtrMplsLspPackets
            ACCESS  not-implemented
            DESCRIPTION
                    "vRtrMplsLspPackets is not implemented."

        VARIATION   vRtrMplsSrlgDBIfRowStatus
            SYNTAX  INTEGER {
                        active           (1),
                        -- notInService  (2),
                        -- notReady      (3),
                        createAndGo      (4),
                        --createAndWait  (5),
                        destroy          (6)
                    }
            DESCRIPTION
                    "vRtrMplsSrlgDBIfRowStatus supports only 'active (1)',
                     'createAndGo (4)', and 'destroy (6)'. "

        VARIATION   vRtrMplsSrlgDBRtrIdRowStatus
            SYNTAX  INTEGER {
                        active           (1),
                        -- notInService  (2),
                        -- notReady      (3),
                        createAndGo      (4),
                        --createAndWait  (5),
                        destroy          (6)
                    }
            DESCRIPTION
                    "vRtrMplsSrlgDBRtrIdRowStatus supports only 'active (1)',
                     'createAndGo (4)', and 'destroy (6)'. "

        VARIATION   vRtrMplsLspTemplateFRMethod
            SYNTAX  INTEGER {
                        -- oneToOneBackup(1),
                        facilityBackup(2)
                    }
            DESCRIPTION
                    "For LSP templates of type P2MP, oneToOneBackup is not
                     supported."

    ::= { tmnxSROSV10v0 26 }  -- MPLS

--
--  OAM TEST CAPABILITIES
--
tmnxSROSOamTestCapsV10v0    AGENT-CAPABILITIES
    PRODUCT-RELEASE "Alcatel-Lucent SROS"
    STATUS          current
    DESCRIPTION     "Implementation of OAM test capabilities
                     for Alcatel-Lucent SROS release R10.0"

    SUPPORTS        TIMETRA-OAM-TEST-MIB
        INCLUDES    {
            tmnxOamAncpTestV5v0Group,
-- EXCLUDE  tmnxOamAtmPingR2r1Group
            tmnxOamCpePingV4v0Group,
            tmnxOamEthCfmPingV8v0Group,
            tmnxOamEthCfmTrV8v0Group,
            tmnxOamGeneralV8v0Group,
            tmnxOamIcmpPingGroup,
            tmnxOamLTtraceV9v0Group,
            tmnxOamLspPingV6v0Group,
            tmnxOamLspTrV6v0Group,
            tmnxOamMRInfoV4v0Group,
            tmnxOamMacPingV4v0Group,
            tmnxOamMacTrV3v0Group,
            tmnxOamMcastTrV4v0Group,
            tmnxOamMfibPingV6v0Group,
            tmnxOamP2mpLspPingGroup,
            tmnxOamP2mpLspPingV8v0Group,
            tmnxOamP2mpLspTraceGroup,
            tmnxOamPingGeneralV10v0Group,
            tmnxOamPingNotificationV7v0Group,
            tmnxOamSaaGeneralV7v0Group,
            tmnxOamSaaGeneralV8v0Group,
            tmnxOamSaaNotificationV3v0Group,
            tmnxOamSaaThresholdV3v0Group,
            tmnxOamTrGeneralV7v0Group,
            tmnxOamTrGeneralV8v0Group,
            tmnxOamTrHopsV4v0Group,
            tmnxOamTrNotificationV5v0Group,
            tmnxOamTrNotificationV8v0Group,
            tmnxOamVccvPingV5v0Group,
            tmnxOamVccvPingV9v0Group,
            tmnxOamVccvTrV6v0Group,
            tmnxOamVccvTrV9v0Group,
            tmnxOamVprnPingV4v0Group,
            tmnxOamVprnTrV6v0Group,
            tmnxOamPingCtlV10v0Group,
            tmnxOamSaaGeneralV10v0Group,
            tmnxOamMobilePingGroup,
            tmnxOamGeneralV10v0Group,
            tmnxOamP2mpLspPingV10v0Group
        }

        VARIATION   tmnxOamCpePingCtlSrcAddrType
            SYNTAX  INTEGER {
                        -- unknown  (0),
                        ipv4        (1)
                        -- ipv6     (2),
                        -- ipv4z    (3),
                        -- ipv6z    (4),
                        -- dns      (16)
                    }
            DESCRIPTION
                    "The only value supported during a set operation is
                     'ipv4(1)'."

        VARIATION   tmnxOamLspPingCtlReturnLsp
            ACCESS  read-only
            DESCRIPTION
                    "The LSP return option is not supported for configuration
                    of OAM lspPing tests."

        VARIATION   tmnxOamLTtraceAutoRowStatus
            SYNTAX  INTEGER {
                    active (1),
                    -- notInService (2),
                    -- notReady (3),
                    createAndGo (4),
                    -- createAndWait (5),
                    destroy (6)
                }
            DESCRIPTION
                    "tmnxOamLTtraceAutoRowStatus supports only 'active (1)',
                     'createAndGo (4)' and 'destroy (6)'."

        VARIATION   tmnxOamMcastTrCtlSrcAddrType
            SYNTAX  INTEGER {
                        unknown     (0),
                        ipv4        (1)
                        -- ipv6     (2),
                        -- ipv4z    (3),
                        -- ipv6z    (4),
                        -- dns      (16)
                    }
            DESCRIPTION
                    "tmnxOamMcastTrCtlSrcAddrType supports only 'unknown (0)'
                     and 'ipv4 (1)'."

        VARIATION   tmnxOamMcastTrCtlDestAddrType
            SYNTAX  INTEGER {
                        unknown     (0),
                        ipv4        (1)
                        -- ipv6     (2),
                        -- ipv4z    (3),
                        -- ipv6z    (4),
                        -- dns      (16)
                    }
            DESCRIPTION
                    "tmnxOamMcastTrCtlDestAddrType supports only 'unknown (0)'
                     and 'ipv4 (1)'."

        VARIATION   tmnxOamMcastTrCtlGrpAddrType
            SYNTAX  INTEGER {
                        unknown     (0),
                        ipv4        (1)
                        -- ipv6     (2),
                        -- ipv4z    (3),
                        -- ipv6z    (4),
                        -- dns      (16)
                    }
            DESCRIPTION
                    "tmnxOamMcastTrCtlGrpAddrType supports only 'unknown (0)'
                     and 'ipv4 (1)'."

        VARIATION   tmnxOamP2mpLspPingCtlIpRowStatus
            SYNTAX  INTEGER {
                    active (1),
                    -- notInService (2),
                    -- notReady (3),
                    createAndGo (4),
                    -- createAndWait (5),
                    destroy (6)
                }
            DESCRIPTION
                    "tmnxOamP2mpLspPingCtlIpRowStatus supports only
                     'active (1)', 'createAndGo (4)' and 'destroy (6)'."

        VARIATION   tmnxOamPingCtlRowStatus
            SYNTAX  INTEGER {
                    active (1),
                    -- notInService (2),
                    -- notReady (3),
                    createAndGo (4),
                    -- createAndWait (5),
                    destroy (6)
                }
            DESCRIPTION
                    "tmnxOamPingCtlRowStatus supports only 'active (1)',
                     'createAndGo (4)' and 'destroy (6)'."

        VARIATION   tmnxOamPingCtlSAA
            ACCESS  read-only
            DESCRIPTION
                    "tmnxOamPingCtlSAA is implemented as read-only."

        VARIATION   tmnxOamSaaCtlRowStatus
            SYNTAX  INTEGER {
                    active (1),
                    -- notInService (2),
                    -- notReady (3),
                    createAndGo (4),
                    -- createAndWait (5),
                    destroy (6)
                }
            DESCRIPTION
                    "tmnxOamSaaCtlRowStatus supports only 'active (1)',
                     'createAndGo (4)' and 'destroy (6)'."

        VARIATION   tmnxOamSaaTRowStatus
            SYNTAX  INTEGER {
                    active (1),
                    -- notInService (2),
                    -- notReady (3),
                    createAndGo (4),
                    -- createAndWait (5),
                    destroy (6)
                }
            DESCRIPTION
                    "tmnxOamSaaTRowStatus supports only 'active (1)',
                     'createAndGo (4)' and 'destroy (6)'."

        VARIATION   tmnxOamSaaTThreshold
            DESCRIPTION
                    "The value of tmnxOamSaaTThreshold must be a multiple of
                     1000 when specifying a tmnxOamSaaTType with units of
                     microseconds."

        VARIATION   tmnxOamTrCtlRowStatus
            SYNTAX  INTEGER {
                    active (1),
                    -- notInService (2),
                    -- notReady (3),
                    createAndGo (4),
                    -- createAndWait (5),
                    destroy (6)
                }
            DESCRIPTION
                    "tmnxOamTrCtlRowStatus supports only 'active (1)',
                     'createAndGo (4)' and 'destroy (6)'."

        VARIATION   tmnxOamTrCtlSAA
            ACCESS  read-only
            DESCRIPTION
                    "tmnxOamTrCtlSAA is implemented as read-only."

        VARIATION tmnxOamTrCtlTrapGeneration
            SYNTAX  BITS {
                        -- pathChange(0),  not supported
                        testFailure(1),
                        testCompletion(2)
            }
            DESCRIPTION
                    "The pathChange bit is not supported."

        VARIATION   tmnxOamTrPathChange
            ACCESS  not-implemented
            DESCRIPTION
                    "tmnxOamTrPathChange notification is not supported."

        VARIATION   tmnxOamPingCtlTestMode
            SYNTAX      INTEGER {
                            sdpPing (1),
                            mtuPing (2),
                            svcPing (3),
                            -- macQuery (4),  obsolete
                            macPing (5),
                            macPopulate (6),
                            macPurge (7),
                            lspPing (8),
                            vprnPing (9),
                            -- atmPing (10),
                            mfibPing (11),
                            cpePing (12),
                            mrInfo (13),
                            vccvPing (14),
                            icmpPing (15),
                            dnsPing (16),
                            ancpLoopback (17),
                            p2mpLspPing (18),
                            ethCfmLoopback (19),
                            ethCfmTwoWayDelay (20)
                            -- mobGtpPing (21) not supported
                        }
            DESCRIPTION
                    "The values 'atmPing (10) and 'mobGtpPing (21)' are not
                     supported on the Alcatel-Lucent SROS systems."

        VARIATION   tmnxOamPingCtlTgtAddrType
            SYNTAX  INTEGER {
                        unknown     (0),
                        ipv4        (1),
                        ipv6        (2),
                        -- ipv4z    (3),
                        ipv6z       (4),
                        dns         (16)
                    }
            DESCRIPTION
                    "tmnxOamPingCtlTgtAddrType does not support the
                     InetAddressType 'ipv4z(3)'."

        VARIATION   tmnxOamP2mpLspPingCtlSrcAddrType
            SYNTAX  INTEGER {
                        unknown     (0),
                        ipv4        (1)
                        -- ipv6     (2),
                        -- ipv4z    (3),
                        -- ipv6z    (4),
                        -- dns      (16)
                    }
            DESCRIPTION
                    "tmnxOamP2mpLspPingCtlSrcAddrType supports only
                     'unknown (0)' and 'ipv4 (1)'."

        VARIATION   tmnxOamP2mpLspPingCtlGrpAddrType
            SYNTAX  INTEGER {
                        unknown     (0),
                        ipv4        (1)
                        -- ipv6     (2),
                        -- ipv4z    (3),
                        -- ipv6z    (4),
                        -- dns      (16)
                    }
            DESCRIPTION
                    "tmnxOamP2mpLspPingCtlGrpAddrType supports only
                     'unknown (0)' and 'ipv4 (1)'."

    ::= { tmnxSROSV10v0 27 }  -- OAM TEST

tmnx7750OamTestCapsV10v0    AGENT-CAPABILITIES
    PRODUCT-RELEASE "Alcatel-Lucent SROS"
    STATUS          current
    DESCRIPTION     "Implementation of OAM test capabilities
                     for Alcatel-Lucent 7750 release R10.0"

    SUPPORTS        TIMETRA-OAM-TEST-MIB
        INCLUDES    {
            tmnxOamAtmPingR2r1Group,
            tmnxOamPingGeneralV10v0Group
        }

        VARIATION   tmnxOamPingCtlTestMode
            SYNTAX      INTEGER {
                            sdpPing (1),
                            mtuPing (2),
                            svcPing (3),
                            -- macQuery (4),  obsolete
                            macPing (5),
                            macPopulate (6),
                            macPurge (7),
                            lspPing (8),
                            vprnPing (9),
                            atmPing (10),
                            mfibPing (11),
                            cpePing (12),
                            mrInfo (13),
                            vccvPing (14),
                            icmpPing (15),
                            dnsPing (16),
                            ancpLoopback (17),
                            p2mpLspPing (18),
                            ethCfmLoopback (19),
                            ethCfmTwoWayDelay (20)
                            -- mobGtpPing (21) not supported
                        }
            DESCRIPTION
                    "The value 'mobGtpPing (21)' is not supported on the
                     Alcatel-Lucent 7750 systems."

    ::= { tmnxSROSOamTestCapsV10v0 1 }

tmnx7450OamTestCapsV10v0    AGENT-CAPABILITIES
    PRODUCT-RELEASE "Alcatel-Lucent SROS"
    STATUS          current
    DESCRIPTION     "Implementation of OAM test capabilities
                     for Alcatel-Lucent 7450 release R10.0"

    SUPPORTS        TIMETRA-OAM-TEST-MIB
        INCLUDES    {
            tmnxOamAtmPingR2r1Group,
            tmnxOamPingGeneralV10v0Group
        }

        VARIATION   tmnxOamPingCtlTestMode
            SYNTAX      INTEGER {
                            sdpPing (1),
                            mtuPing (2),
                            svcPing (3),
                            -- macQuery (4),  obsolete
                            macPing (5),
                            macPopulate (6),
                            macPurge (7),
                            lspPing (8),
                            vprnPing (9),
                            atmPing (10),
                            mfibPing (11),
                            cpePing (12),
                            mrInfo (13),
                            vccvPing (14),
                            icmpPing (15),
                            dnsPing (16),
                            ancpLoopback (17),
                            p2mpLspPing (18),
                            ethCfmLoopback (19),
                            ethCfmTwoWayDelay (20)
                            -- mobGtpPing (21) not supported
                        }
            DESCRIPTION
                    "The value 'mobGtpPing (21)' is not supported on the
                     Alcatel-Lucent 7450 systems."

    ::= { tmnxSROSOamTestCapsV10v0 2 }

tmnxSPROamTestCapsV10v0     AGENT-CAPABILITIES
    PRODUCT-RELEASE "Alcatel-Lucent SROS"
    STATUS          current
    DESCRIPTION     "Implementation of OAM test capabilities
                     for Alcatel-Lucent SPR release R10.0"

    SUPPORTS        TIMETRA-OAM-TEST-MIB
        INCLUDES    {
            tmnxOamAtmPingR2r1Group,
            tmnxOamPingGeneralV10v0Group
        }

        VARIATION   tmnxOamPingCtlTestMode
            SYNTAX      INTEGER {
                            sdpPing (1),
                            mtuPing (2),
                            svcPing (3),
                            -- macQuery (4),  obsolete
                            macPing (5),
                            macPopulate (6),
                            macPurge (7),
                            lspPing (8),
                            vprnPing (9),
                            atmPing (10),
                            mfibPing (11),
                            cpePing (12),
                            mrInfo (13),
                            vccvPing (14),
                            icmpPing (15),
                            dnsPing (16),
                            ancpLoopback (17),
                            p2mpLspPing (18),
                            ethCfmLoopback (19),
                            ethCfmTwoWayDelay (20)
                            -- mobGtpPing (21) not supported
                        }
            DESCRIPTION
                    "The value 'mobGtpPing (21)' is not supported on the
                     Alcatel-Lucent SPR systems."

    ::= { tmnxSROSOamTestCapsV10v0 3 }

--
--  OSPF CAPABILITIES
--
tmnxSROSOspfCapsV10v0    AGENT-CAPABILITIES
    PRODUCT-RELEASE "Alcatel-Lucent SROS"
    STATUS          current
    DESCRIPTION     "Implementation of OSPF protocol capabilities
                     for Alcatel-Lucent SROS release R10.0"

    SUPPORTS        OSPF-MIB
        INCLUDES    {
            ospfBasicGroup2,
            ospfAreaGroup2,
            ospfStubAreaGroup,
            ospfIfGroup2,
            ospfIfMetricGroup,
            ospfVirtIfGroup2,
            ospfNbrGroup2,
            ospfVirtNbrGroup2,
            ospfAreaAggregateGroup2,
            ospfHostGroup2,
            ospfLsdbGroup,
            ospfLocalLsdbGroup,
            ospfVirtLocalLsdbGroup,
            ospfAsLsdbGroup
-- EXCLUDE  ospfAreaLsaCountGroup
-- EXCLUDE  ospfExtLsdbGroup
        }

        VARIATION   ospfRouterId
            ACCESS  read-only
            DESCRIPTION
                    "ospfRouterId is implemented as read-only."

        VARIATION   ospfAdminStat
            ACCESS  read-only
            DESCRIPTION
                    "ospfAdminStat is implemented as read-only."

        VARIATION   ospfVersionNumber
            ACCESS  read-only
            DESCRIPTION
                    "ospfVersionNumber is implemented as read-only."

        VARIATION   ospfAreaBdrRtrStatus
            ACCESS  read-only
            DESCRIPTION
                    "ospfAreaBdrRtrStatus is implemented as read-only."

        VARIATION   ospfASBdrRtrStatus
            ACCESS  read-only
            DESCRIPTION
                    "ospfASBdrRtrStatus is implemented as read-only."

        VARIATION   ospfExternLsaCount
            ACCESS  read-only
            DESCRIPTION
                    "ospfExternLsaCount is implemented as read-only."

        VARIATION   ospfExternLsaCksumSum
            ACCESS  read-only
            DESCRIPTION
                    "ospfExternLsaCksumSum is implemented as read-only."

        VARIATION   ospfTOSSupport
            ACCESS  read-only
            DESCRIPTION
                    "ospfTOSSupport is implemented as read-only."

        VARIATION   ospfOriginateNewLsas
            ACCESS  read-only
            DESCRIPTION
                    "ospfOriginateNewLsas is implemented as read-only."

        VARIATION   ospfRxNewLsas
            ACCESS  read-only
            DESCRIPTION
                    "ospfRxNewLsas is implemented as read-only."

        VARIATION   ospfExtLsdbLimit
            ACCESS  read-only
            DESCRIPTION
                    "ospfExtLsdbLimit is implemented as read-only."

        VARIATION   ospfMulticastExtensions
            ACCESS  read-only
            DESCRIPTION
                    "ospfMulticastExtensions is implemented as read-only."

        VARIATION   ospfExitOverflowInterval
            ACCESS  read-only
            DESCRIPTION
                    "ospfExitOverflowInterval is implemented as read-only."

        VARIATION   ospfDemandExtensions
            ACCESS  read-only
            DESCRIPTION
                    "ospfDemandExtensions is implemented as read-only."

        VARIATION   ospfRFC1583Compatibility
            ACCESS  read-only
            DESCRIPTION
                    "ospfRFC1583Compatibility is implemented as read-only."

        VARIATION   ospfOpaqueLsaSupport
            ACCESS  read-only
            DESCRIPTION
                    "ospfOpaqueLsaSupport is implemented as read-only."

        VARIATION   ospfReferenceBandwidth
            ACCESS  read-only
            DESCRIPTION
                    "ospfReferenceBandwidth is implemented as read-only."

        VARIATION   ospfRestartSupport
            ACCESS  read-only
            DESCRIPTION
                    "ospfRestartSupport is implemented as read-only."

        VARIATION   ospfRestartInterval
            ACCESS  read-only
            DESCRIPTION
                    "ospfRestartInterval is implemented as read-only."

        VARIATION   ospfRestartStrictLsaChecking
            ACCESS  read-only
            DESCRIPTION
                    "ospfRestartStrictLsaChecking is implemented as read-only."

        VARIATION   ospfRestartStatus
            ACCESS  read-only
            DESCRIPTION
                    "ospfRestartStatus is implemented as read-only."

        VARIATION   ospfRestartAge
            ACCESS  read-only
            DESCRIPTION
                    "ospfRestartAge is implemented as read-only."

        VARIATION   ospfRestartExitReason
            ACCESS  read-only
            DESCRIPTION
                    "ospfRestartExitReason is implemented as read-only."

        VARIATION   ospfAsLsaCount
            ACCESS  read-only
            DESCRIPTION
                    "ospfAsLsaCount is implemented as read-only."

        VARIATION   ospfAsLsaCksumSum
            ACCESS  read-only
            DESCRIPTION
                    "ospfAsLsaCksumSum is implemented as read-only."

        VARIATION   ospfStubRouterSupport
            ACCESS  read-only
            DESCRIPTION
                    "ospfStubRouterSupport is implemented as read-only."

        VARIATION   ospfStubRouterAdvertisement
            ACCESS  read-only
            DESCRIPTION
                    "ospfStubRouterAdvertisement is implemented as read-only."

        VARIATION   ospfDiscontinuityTime
            ACCESS  read-only
            DESCRIPTION
                    "ospfDiscontinuityTime is implemented as read-only."

        VARIATION   ospfAreaId
            ACCESS  read-only
            DESCRIPTION
                    "ospfAreaId is implemented as read-only."

        VARIATION   ospfImportAsExtern
            ACCESS  read-only
            DESCRIPTION
                    "ospfImportAsExtern is implemented as read-only."

        VARIATION   ospfSpfRuns
            ACCESS  read-only
            DESCRIPTION
                    "ospfSpfRuns is implemented as read-only."

        VARIATION   ospfAreaBdrRtrCount
            ACCESS  read-only
            DESCRIPTION
                    "ospfAreaBdrRtrCount is implemented as read-only."

        VARIATION   ospfAsBdrRtrCount
            ACCESS  read-only
            DESCRIPTION
                    "ospfAsBdrRtrCount is implemented as read-only."

        VARIATION   ospfAreaLsaCount
            ACCESS  read-only
            DESCRIPTION
                    "ospfAreaLsaCount is implemented as read-only."

        VARIATION   ospfAreaLsaCksumSum
            ACCESS  read-only
            DESCRIPTION
                    "ospfAreaLsaCksumSum is implemented as read-only."

        VARIATION   ospfAreaSummary
            ACCESS  read-only
            DESCRIPTION
                    "ospfAreaSummary is implemented as read-only."

        VARIATION   ospfAreaStatus
            ACCESS  read-only
            DESCRIPTION
                    "ospfAreaStatus is implemented as read-only."

        VARIATION   ospfAreaNssaTranslatorRole
            ACCESS  read-only
            DESCRIPTION
                    "ospfAreaNssaTranslatorRole is implemented as read-only."

        VARIATION   ospfAreaNssaTranslatorState
            ACCESS  read-only
            DESCRIPTION
                    "ospfAreaNssaTranslatorState is implemented as read-only."

        VARIATION   ospfAreaNssaTranslatorStabilityInterval
            ACCESS  read-only
            DESCRIPTION
                    "ospfAreaNssaTranslatorStabilityInterval is implemented as
                     read-only."

        VARIATION   ospfAreaNssaTranslatorEvents
            ACCESS  read-only
            DESCRIPTION
                    "ospfAreaNssaTranslatorEvents is implemented as read-only."

        VARIATION   ospfStubAreaId
            ACCESS  read-only
            DESCRIPTION
                    "ospfStubAreaId is implemented as read-only."

        VARIATION   ospfStubTOS
            ACCESS  read-only
            DESCRIPTION
                    "ospfStubTOS is implemented as read-only."

        VARIATION   ospfStubMetric
            ACCESS  read-only
            DESCRIPTION
                    "ospfStubMetric is implemented as read-only."

        VARIATION   ospfStubStatus
            ACCESS  read-only
            DESCRIPTION
                    "ospfStubStatus is implemented as read-only."

        VARIATION   ospfStubMetricType
            ACCESS  read-only
            DESCRIPTION
                    "ospfStubMetricType is implemented as read-only."

        VARIATION   ospfLsdbAreaId
            ACCESS  read-only
            DESCRIPTION
                    "ospfLsdbAreaId is implemented as read-only."

        VARIATION   ospfLsdbType
            ACCESS  read-only
            DESCRIPTION
                    "ospfLsdbType is implemented as read-only."

        VARIATION   ospfLsdbLsid
            ACCESS  read-only
            DESCRIPTION
                    "ospfLsdbLsid is implemented as read-only."

        VARIATION   ospfLsdbRouterId
            ACCESS  read-only
            DESCRIPTION
                    "ospfLsdbRouterId is implemented as read-only."

        VARIATION   ospfLsdbSequence
            ACCESS  read-only
            DESCRIPTION
                    "ospfLsdbSequence is implemented as read-only."

        VARIATION   ospfLsdbAge
            ACCESS  read-only
            DESCRIPTION
                    "ospfLsdbAge is implemented as read-only."

        VARIATION   ospfLsdbChecksum
            ACCESS  read-only
            DESCRIPTION
                    "ospfLsdbChecksum is implemented as read-only."

        VARIATION   ospfLsdbAdvertisement
            ACCESS  read-only
            DESCRIPTION
                    "ospfLsdbAdvertisement is implemented as read-only."

        VARIATION   ospfAreaRangeAreaId
            ACCESS  read-only
            DESCRIPTION
                    "ospfAreaRangeAreaId is implemented as read-only."

        VARIATION   ospfAreaRangeNet
            ACCESS  read-only
            DESCRIPTION
                    "ospfAreaRangeNet is implemented as read-only."

        VARIATION   ospfAreaRangeMask
            ACCESS  read-only
            DESCRIPTION
                    "ospfAreaRangeMask is implemented as read-only."

        VARIATION   ospfAreaRangeStatus
            ACCESS  read-only
            DESCRIPTION
                    "ospfAreaRangeStatus is implemented as read-only."

        VARIATION   ospfAreaRangeEffect
            ACCESS  read-only
            DESCRIPTION
                    "ospfAreaRangeEffect is implemented as read-only."

        VARIATION   ospfHostIpAddress
            ACCESS  read-only
            DESCRIPTION
                    "ospfHostIpAddress is implemented as read-only."

        VARIATION   ospfHostTOS
            ACCESS  read-only
            DESCRIPTION
                    "ospfHostTOS is implemented as read-only."

        VARIATION   ospfHostMetric
            ACCESS  read-only
            DESCRIPTION
                    "ospfHostMetric is implemented as read-only."

        VARIATION   ospfHostStatus
            ACCESS  read-only
            DESCRIPTION
                    "ospfHostStatus is implemented as read-only."

        VARIATION   ospfHostAreaID
            ACCESS  read-only
            DESCRIPTION
                    "ospfHostAreaID is implemented as read-only."

        VARIATION   ospfHostCfgAreaID
            ACCESS  read-only
            DESCRIPTION
                    "ospfHostCfgAreaID is implemented as read-only."

        VARIATION   ospfIfIpAddress
            ACCESS  read-only
            DESCRIPTION
                    "ospfIfIpAddress is implemented as read-only."

        VARIATION   ospfAddressLessIf
            ACCESS  read-only
            DESCRIPTION
                    "ospfAddressLessIf is implemented as read-only."

        VARIATION   ospfIfAreaId
            ACCESS  read-only
            DESCRIPTION
                    "ospfIfAreaId is implemented as read-only."

        VARIATION   ospfIfType
            ACCESS  read-only
            DESCRIPTION
                    "ospfIfType is implemented as read-only."

        VARIATION   ospfIfAdminStat
            ACCESS  read-only
            DESCRIPTION
                    "ospfIfAdminStat is implemented as read-only."

        VARIATION   ospfIfRtrPriority
            ACCESS  read-only
            DESCRIPTION
                    "ospfIfRtrPriority is implemented as read-only."

        VARIATION   ospfIfTransitDelay
            ACCESS  read-only
            DESCRIPTION
                    "ospfIfTransitDelay is implemented as read-only."

        VARIATION   ospfIfRetransInterval
            ACCESS  read-only
            DESCRIPTION
                    "ospfIfRetransInterval is implemented as read-only."

        VARIATION   ospfIfHelloInterval
            ACCESS  read-only
            DESCRIPTION
                    "ospfIfHelloInterval is implemented as read-only."

        VARIATION   ospfIfRtrDeadInterval
            ACCESS  read-only
            DESCRIPTION
                    "ospfIfRtrDeadInterval is implemented as read-only."

        VARIATION   ospfIfPollInterval
            ACCESS  read-only
            DESCRIPTION
                    "ospfIfPollInterval is implemented as read-only."

        VARIATION   ospfIfState
            ACCESS  read-only
            DESCRIPTION
                    "ospfIfState is implemented as read-only."

        VARIATION   ospfIfDesignatedRouter
            ACCESS  read-only
            DESCRIPTION
                    "ospfIfDesignatedRouter is implemented as read-only."

        VARIATION   ospfIfBackupDesignatedRouter
            ACCESS  read-only
            DESCRIPTION
                    "ospfIfBackupDesignatedRouter is implemented as read-only."

        VARIATION   ospfIfEvents
            ACCESS  read-only
            DESCRIPTION
                    "ospfIfEvents is implemented as read-only."

        VARIATION   ospfIfAuthType
            ACCESS  read-only
            DESCRIPTION
                    "ospfIfAuthType is implemented as read-only."

        VARIATION   ospfIfAuthKey
            ACCESS  read-only
            DESCRIPTION
                    "ospfIfAuthKey is implemented as read-only."

        VARIATION   ospfIfStatus
            ACCESS  read-only
            DESCRIPTION
                    "ospfIfStatus is implemented as read-only."

        VARIATION   ospfIfMulticastForwarding
            ACCESS  read-only
            DESCRIPTION
                    "ospfIfMulticastForwarding is implemented as read-only."

        VARIATION   ospfIfDemand
            ACCESS  read-only
            DESCRIPTION
                    "ospfIfDemand is implemented as read-only."

        VARIATION   ospfIfLsaCount
            ACCESS  read-only
            DESCRIPTION
                    "ospfIfLsaCount is implemented as read-only."

        VARIATION   ospfIfLsaCksumSum
            ACCESS  read-only
            DESCRIPTION
                    "ospfIfLsaCksumSum is implemented as read-only."

        VARIATION   ospfIfMetricIpAddress
            ACCESS  read-only
            DESCRIPTION
                    "ospfIfMetricIpAddress is implemented as read-only."

        VARIATION   ospfIfMetricAddressLessIf
            ACCESS  read-only
            DESCRIPTION
                    "ospfIfMetricAddressLessIf is implemented as read-only."

        VARIATION   ospfIfMetricTOS
            ACCESS  read-only
            DESCRIPTION
                    "ospfIfMetricTOS is implemented as read-only."

        VARIATION   ospfIfMetricValue
            ACCESS  read-only
            DESCRIPTION
                    "ospfIfMetricValue is implemented as read-only."

        VARIATION   ospfIfMetricStatus
            ACCESS  read-only
            DESCRIPTION
                    "ospfIfMetricStatus is implemented as read-only."

        VARIATION   ospfVirtIfAreaId
            ACCESS  read-only
            DESCRIPTION
                    "ospfVirtIfAreaId is implemented as read-only."

        VARIATION   ospfVirtIfNeighbor
            ACCESS  read-only
            DESCRIPTION
                    "ospfVirtIfNeighbor is implemented as read-only."

        VARIATION   ospfVirtIfTransitDelay
            ACCESS  read-only
            DESCRIPTION
                    "ospfVirtIfTransitDelay is implemented as read-only."

        VARIATION   ospfVirtIfRetransInterval
            ACCESS  read-only
            DESCRIPTION
                    "ospfVirtIfRetransInterval is implemented as read-only."

        VARIATION   ospfVirtIfHelloInterval
            ACCESS  read-only
            DESCRIPTION
                    "ospfVirtIfHelloInterval is implemented as read-only."

        VARIATION   ospfVirtIfRtrDeadInterval
            ACCESS  read-only
            DESCRIPTION
                    "ospfVirtIfRtrDeadInterval is implemented as read-only."

        VARIATION   ospfVirtIfState
            ACCESS  read-only
            DESCRIPTION
                    "ospfVirtIfState is implemented as read-only."

        VARIATION   ospfVirtIfEvents
            ACCESS  read-only
            DESCRIPTION
                    "ospfVirtIfEvents is implemented as read-only."

        VARIATION   ospfVirtIfAuthType
            ACCESS  read-only
            DESCRIPTION
                    "ospfVirtIfAuthType is implemented as read-only."

        VARIATION   ospfVirtIfAuthKey
            ACCESS  read-only
            DESCRIPTION
                    "ospfVirtIfAuthKey is implemented as read-only."

        VARIATION   ospfVirtIfStatus
            ACCESS  read-only
            DESCRIPTION
                    "ospfVirtIfStatus is implemented as read-only."

        VARIATION   ospfVirtIfLsaCount
            ACCESS  read-only
            DESCRIPTION
                    "ospfVirtIfLsaCount is implemented as read-only."

        VARIATION   ospfVirtIfLsaCksumSum
            ACCESS  read-only
            DESCRIPTION
                    "ospfVirtIfLsaCksumSum is implemented as read-only."

        VARIATION   ospfIfDesignatedRouterId
            ACCESS  read-only
            DESCRIPTION
                    "ospfIfDesignatedRouterId is implemented as read-only."

        VARIATION   ospfIfBackupDesignatedRouterId
            ACCESS  read-only
            DESCRIPTION
                    "ospfIfBackupDesignatedRouterId is implemented as
                    read-only."

        VARIATION   ospfNbrIpAddr
            ACCESS  read-only
            DESCRIPTION
                    "ospfNbrIpAddr is implemented as read-only."

        VARIATION   ospfNbrAddressLessIndex
            ACCESS  read-only
            DESCRIPTION
                    "ospfNbrAddressLessIndex is implemented as read-only."

        VARIATION   ospfNbrRtrId
            ACCESS  read-only
            DESCRIPTION
                    "ospfNbrRtrId is implemented as read-only."

        VARIATION   ospfNbrOptions
            ACCESS  read-only
            DESCRIPTION
                    "ospfNbrOptions is implemented as read-only."

        VARIATION   ospfNbrPriority
            ACCESS  read-only
            DESCRIPTION
                    "ospfNbrPriority is implemented as read-only."

        VARIATION   ospfNbrState
            ACCESS  read-only
            DESCRIPTION
                    "ospfNbrState is implemented as read-only."

        VARIATION   ospfNbrEvents
            ACCESS  read-only
            DESCRIPTION
                    "ospfNbrEvents is implemented as read-only."

        VARIATION   ospfNbrLsRetransQLen
            ACCESS  read-only
            DESCRIPTION
                    "ospfNbrLsRetransQLen is implemented as read-only."

        VARIATION   ospfNbmaNbrStatus
            ACCESS  read-only
            DESCRIPTION
                    "ospfNbmaNbrStatus is implemented as read-only."

        VARIATION   ospfNbmaNbrPermanence
            ACCESS  read-only
            DESCRIPTION
                    "ospfNbmaNbrPermanence is implemented as read-only."

        VARIATION   ospfNbrHelloSuppressed
            ACCESS  read-only
            DESCRIPTION
                    "ospfNbrHelloSuppressed is implemented as read-only."

        VARIATION   ospfNbrRestartHelperStatus
            ACCESS  read-only
            DESCRIPTION
                    "ospfNbrRestartHelperStatus is implemented as read-only."

        VARIATION   ospfNbrRestartHelperAge
            ACCESS  read-only
            DESCRIPTION
                    "ospfNbrRestartHelperAge is implemented as read-only."

        VARIATION   ospfNbrRestartHelperExitReason
            ACCESS  read-only
            DESCRIPTION
                    "ospfNbrRestartHelperExitReason is implemented as
                    read-only."

        VARIATION   ospfVirtNbrArea
            ACCESS  read-only
            DESCRIPTION
                    "ospfVirtNbrArea is implemented as read-only."

        VARIATION   ospfVirtNbrRtrId
            ACCESS  read-only
            DESCRIPTION
                    "ospfVirtNbrRtrId is implemented as read-only."

        VARIATION   ospfVirtNbrIpAddr
            ACCESS  read-only
            DESCRIPTION
                    "ospfVirtNbrIpAddr is implemented as read-only."

        VARIATION   ospfVirtNbrOptions
            ACCESS  read-only
            DESCRIPTION
                    "ospfVirtNbrOptions is implemented as read-only."

        VARIATION   ospfVirtNbrState
            ACCESS  read-only
            DESCRIPTION
                    "ospfVirtNbrState is implemented as read-only."

        VARIATION   ospfVirtNbrEvents
            ACCESS  read-only
            DESCRIPTION
                    "ospfVirtNbrEvents is implemented as read-only."

        VARIATION   ospfVirtNbrLsRetransQLen
            ACCESS  read-only
            DESCRIPTION
                    "ospfVirtNbrLsRetransQLen is implemented as read-only."

        VARIATION   ospfVirtNbrHelloSuppressed
            ACCESS  read-only
            DESCRIPTION
                    "ospfVirtNbrHelloSuppressed is implemented as read-only."

        VARIATION   ospfVirtNbrRestartHelperStatus
            ACCESS  read-only
            DESCRIPTION
                    "ospfVirtNbrRestartHelperStatus is implemented as
                    read-only."

        VARIATION   ospfVirtNbrRestartHelperAge
            ACCESS  read-only
            DESCRIPTION
                    "ospfVirtNbrRestartHelperAge is implemented as read-only."

        VARIATION   ospfVirtNbrRestartHelperExitReason
            ACCESS  read-only
            DESCRIPTION
                    "ospfVirtNbrRestartHelperExitReason is implemented as
                    read-only."

        VARIATION   ospfExtLsdbType
            ACCESS  read-only
            DESCRIPTION
                    "ospfExtLsdbType is implemented as read-only."

        VARIATION   ospfExtLsdbLsid
            ACCESS  read-only
            DESCRIPTION
                    "ospfExtLsdbLsid is implemented as read-only."

        VARIATION   ospfExtLsdbRouterId
            ACCESS  read-only
            DESCRIPTION
                    "ospfExtLsdbRouterId is implemented as read-only."

        VARIATION   ospfExtLsdbSequence
            ACCESS  read-only
            DESCRIPTION
                    "ospfExtLsdbSequence is implemented as read-only."

        VARIATION   ospfExtLsdbAge
            ACCESS  read-only
            DESCRIPTION
                    "ospfExtLsdbAge is implemented as read-only."

        VARIATION   ospfExtLsdbChecksum
            ACCESS  read-only
            DESCRIPTION
                    "ospfExtLsdbChecksum is implemented as read-only."

        VARIATION   ospfExtLsdbAdvertisement
            ACCESS  read-only
            DESCRIPTION
                    "ospfExtLsdbAdvertisement is implemented as read-only."

        VARIATION   ospfAreaAggregateAreaID
            ACCESS  read-only
            DESCRIPTION
                    "ospfAreaAggregateAreaID is implemented as read-only."

        VARIATION   ospfAreaAggregateLsdbType
            ACCESS  read-only
            DESCRIPTION
                    "ospfAreaAggregateLsdbType is implemented as read-only."

        VARIATION   ospfAreaAggregateNet
            ACCESS  read-only
            DESCRIPTION
                    "ospfAreaAggregateNet is implemented as read-only."

        VARIATION   ospfAreaAggregateMask
            ACCESS  read-only
            DESCRIPTION
                    "ospfAreaAggregateMask is implemented as read-only."

        VARIATION   ospfAreaAggregateStatus
            ACCESS  read-only
            DESCRIPTION
                    "ospfAreaAggregateStatus is implemented as read-only."

        VARIATION   ospfAreaAggregateEffect
            ACCESS  read-only
            DESCRIPTION
                    "ospfAreaAggregateEffect is implemented as read-only."

        VARIATION   ospfAreaAggregateExtRouteTag
            ACCESS  read-only
            DESCRIPTION
                    "ospfAreaAggregateExtRouteTag is implemented as read-only."

        VARIATION   ospfLocalLsdbSequence
            ACCESS  read-only
            DESCRIPTION
                    "ospfLocalLsdbSequence is implemented as read-only."

        VARIATION   ospfLocalLsdbAge
            ACCESS  read-only
            DESCRIPTION
                    "ospfLocalLsdbAge is implemented as read-only."

        VARIATION   ospfLocalLsdbChecksum
            ACCESS  read-only
            DESCRIPTION
                    "ospfLocalLsdbChecksum is implemented as read-only."

        VARIATION   ospfLocalLsdbAdvertisement
            ACCESS  read-only
            DESCRIPTION
                    "ospfLocalLsdbAdvertisement is implemented as read-only."

        VARIATION   ospfVirtLocalLsdbSequence
            ACCESS  read-only
            DESCRIPTION
                    "ospfVirtLocalLsdbSequence is implemented as read-only."

        VARIATION   ospfVirtLocalLsdbAge
            ACCESS  read-only
            DESCRIPTION
                    "ospfVirtLocalLsdbAge is implemented as read-only."

        VARIATION   ospfVirtLocalLsdbChecksum
            ACCESS  read-only
            DESCRIPTION
                    "ospfVirtLocalLsdbChecksum is implemented as read-only."

        VARIATION   ospfVirtLocalLsdbAdvertisement
            ACCESS  read-only
            DESCRIPTION
                    "ospfVirtLocalLsdbAdvertisement is implemented as
                    read-only."

        VARIATION   ospfAsLsdbSequence
            ACCESS  read-only
            DESCRIPTION
                    "ospfAsLsdbSequence is implemented as read-only."

        VARIATION   ospfAsLsdbAge
            ACCESS  read-only
            DESCRIPTION
                    "ospfAsLsdbAge is implemented as read-only."

        VARIATION   ospfAsLsdbChecksum
            ACCESS  read-only
            DESCRIPTION
                    "ospfAsLsdbChecksum is implemented as read-only."

        VARIATION   ospfAsLsdbAdvertisement
            ACCESS  read-only
            DESCRIPTION
                    "ospfAsLsdbAdvertisement is implemented as read-only."

        VARIATION   ospfAreaLsaCountNumber
            ACCESS  read-only
            DESCRIPTION
                    "ospfAreaLsaCountNumber is implemented as read-only."

    SUPPORTS        OSPF-TRAP-MIB
        INCLUDES    {
            ospfTrapControlGroup,
            ospfTrapEventGroup
        }

        VARIATION   ospfSetTrap
            ACCESS  read-only
            DESCRIPTION
                    "ospfSetTrap is implemented as read-only.  The generation
                    of OSPF notifications is controled by tmnxEventTable
                    in the TIMETRA-LOG-MIB."

    SUPPORTS        TIMETRA-OSPF-NG-MIB
        INCLUDES    {
            tmnxOspfGeneralV5v0Group,
            tmnxOspfGeneralV7v0Group,
            -- tmnxOspfAreaGroup
            -- tmnxOspfAreaV8v0Group,
            tmnxOspfAreaV9v0Group,
            tmnxOspfNgLinkLsdbV9v0Group,
            tmnxOspfHostGroup,
            -- tmnxOspfIfV5v0Group,
            tmnxOspfNgIfV9v0Group,
            tmnxOspfNgIfOperV9v0Group,
            tmnxOspfNgIfStatsV9v0Group,
            tmnxOspfVirtIfGroup,
            -- tmnxOspfNbrGroup,
            tmnxOspfNgNbrV9v0Group,
            tmnxOspfVirtNbrGroup,
            tmnxOspfAreaAggrGroup,
            -- tmnxOspfMD5KeyGroup,
            tmnxOspfMD5KeyV9v0Group,
            tmnxOspfNotifyObjsGroup,
            -- tmnxOspfNotifyObjsV8v0Group,
            -- tmnxOspfNotificationGroup,
            -- tmnxOspfIfV6v0Group,
            tmnxOspfGeneralV6v0Group,
            tmnxOspfGeneralV6v1Group,
            -- tmnxOspfNotificationV6v0Group,
            tmnxOspfNotificationV7v0Group,
            tmnxOspfNotificationV9v0Group,
            tmnxOspfGenNotificationV7v0Grp,
            tmnxOspfVirtIfV8v0Group,
            tmnxOspfIfV8v0Group,
            tmnxOspfGeneralV8v0Group,
            tmnxOspfShamLinksV7v0Group,
            tmnxOspfGeneralV10v0Group,
            tmnxOspfFRRV10v0Group
        }

        VARIATION tmnxOspfMulticastExtensions
            ACCESS  read-only
            DESCRIPTION
                 "tmnxOspfMulticastExtensions is implemented as read-only."

        VARIATION tmnxOspfDemandExtensions
            ACCESS  read-only
            DESCRIPTION
                 "tmnxOspfDemandExtensions is implemented as read-only."

        VARIATION tmnxOspfStrictLsaChecking
            ACCESS  read-only
            DESCRIPTION
                 "tmnxOspfStrictLsaChecking is implemented as read-only."

        VARIATION tmnxOspfRestartSupport
            ACCESS  read-only
            DESCRIPTION
                 "tmnxOspfRestartSupport is implemented as read-only."

        VARIATION tmnxOspfRestartInterval
            ACCESS  read-only
            DESCRIPTION
                 "tmnxOspfRestartInterval is implemented as read-only."

        VARIATION tmnxOspfAreaStubMetricType
            ACCESS  read-only
            DESCRIPTION
                 "tmnxOspfAreaStubMetricType is implemented as read-only."

        VARIATION tmnxOspfAreaNssaTranslatorRole
            ACCESS  read-only
            DESCRIPTION
                 "tmnxOspfAreaNssaTranslatorRole is implemented as read-only."

        VARIATION tmnxOspfAreaNssaTranslatorStabInt
            ACCESS  read-only
            DESCRIPTION
                 "tmnxOspfAreaNssaTranslatorStabInt is implemented as
                 read-only."

        VARIATION tmnxOspfIfMulticastForwarding
            ACCESS  read-only
            DESCRIPTION
                 "tmnxOspfIfMulticastForwarding is implemented as read-only."

        VARIATION tmnxOspfIfDemand
            ACCESS  read-only
            DESCRIPTION
                 "tmnxOspfIfDemand is implemented as read-only."

        VARIATION tmnxOspfAreaAggrRouteTag
            ACCESS  read-only
            DESCRIPTION
                 "tmnxOspfAreaAggrRouteTag is implemented as read-only."

        VARIATION tmnxOspfBootOverloadAdmState
            SYNTAX  INTEGER {
                    disabled (1),
                    enabled (2)
                    -- enabledWaitForBgp (3)
                }
            DESCRIPTION
                 "tmnxOspfBootOverloadAdmState only supports
                  'disabled (1)' and 'enabled (2)'.  'enabledWaitForBgp (3) is
                  not implemented."

        VARIATION   tmnxOspfShamIfMD5KeyStartTime
            ACCESS  read-only
            DESCRIPTION
                 "tmnxOspfShamIfMD5KeyStartTime is implemented as read only."

        VARIATION   tmnxOspfShamIfMD5KeyStopTime
            ACCESS  read-only
            DESCRIPTION
                 "tmnxOspfShamIfMD5KeyStopTime is implemented as read only."

        VARIATION   tmnxOspfVirtIfMD5KeyStartTime
            ACCESS  read-only
            DESCRIPTION
                 "tmnxOspfVirtIfMD5KeyStartTime is implemented as read only."

        VARIATION   tmnxOspfVirtIfMD5KeyStopTime
            ACCESS  read-only
            DESCRIPTION
                 "tmnxOspfVirtIfMD5KeyStopTime is implemented as read only."

        VARIATION   tmnxOspfNgIfMD5KeyStartTime
            ACCESS  read-only
            DESCRIPTION
                 "tmnxOspfNgIfMD5KeyStartTime is implemented as read only."

        VARIATION   tmnxOspfNgIfMD5KeyStopTime
            ACCESS  read-only
            DESCRIPTION
                 "tmnxOspfNgIfMD5KeyStopTime is implemented as read only."

    ::= { tmnxSROSV10v0 28 }  -- OSPF


--
--  PIM CAPABILITIES
--
tmnxSROSPimCapsV10v0    AGENT-CAPABILITIES
    PRODUCT-RELEASE "Alcatel-Lucent SROS"
    STATUS          current
    DESCRIPTION     "Implementation of PIM protocol capabilities
                     for Alcatel-Lucent SROS release R10.0"

    SUPPORTS        TIMETRA-PIM-NG-MIB
        INCLUDES    {
            tmnxPimNgGlobalGrpSrcV9v0Group,
            tmnxPimNgIfGroup,
            tmnxPimIfSecNbrV6v0Group,
            tmnxPimNgIfStatsV7v0Group,
            tmnxPimNgNotificationGroup,
            tmnxPimNgNotificationV7v0Group,
            tmnxPimNgNotifyObjsV7v0Group,
            tmnxPimNgEmbeddedRPV7v0Group,
            tmnxPimNgV7v0Group,
            tmnxPimNgEchoGroup,
            tmnxPimNgMvpnV8v0Group,
            tmnxPimNgIfV8v0Group,
            tmnxPimNgGlobalSSMV6v1Group,
            tmnxPimNgGlobalGroupV8v0,
            tmnxPimNgIfIpv6BfdV9v0Group,
            tmnxPimNgNotifyObjsV8v0Group,
            tmnxPimNgNotifyObjsV9v0Group,
            tmnxPimNgMvpnV9v0Group,
            tmnxPimNgIfStatsV9v0Group,
            tmnxPimNgIfIPMSIV9v0Group,
            tmnxPimNgMvpnV9v0R4Group,
            tmnxPimNgGlobalGroupV10v0,
            tmnxPimNgLdpEntryV10v0Group,
            tmnxPimNgIfV10v0Group,
            tmnxPimNgIfStatsV10v0Group,
            tmnxPimNgMvpnExtranetGroupV10v0,
            tmnxPimNgGlobalGrpSrcV10v0Group
        }

        VARIATION   vRtrPimNgRsvpIfSenderAddrType
            SYNTAX  INTEGER {
                        -- unknown  (0),
                        ipv4        (1)
                        -- ipv6      (2)
                        -- ipv4z    (3),
                        -- ipv6z    (4),
                        -- dns      (16)
                    }
            DESCRIPTION
                    "vRtrPimNgRsvpIfSenderAddrType supports only InetAddressType
                     'ipv4'."

        VARIATION   vRtrPimNgRsvpIfSenderAddr
            SYNTAX  InetAddress (SIZE (4))
            DESCRIPTION
                    "vRtrPimNgRsvpIfSenderAddr supports only InetAddressType
                    'ipv4'."

        VARIATION   vRtrPimNgMvpnUMHPEStandbyAdrTyp
            SYNTAX  INTEGER {
                        -- unknown  (0),
                        ipv4        (1)
                        -- ipv6      (2)
                        -- ipv4z    (3),
                        -- ipv6z    (4),
                        -- dns      (16)
                    }
            DESCRIPTION
                    "vRtrPimNgMvpnUMHPEStandbyAdrTyp supports only
                     InetAddressType 'ipv4'."

        VARIATION   vRtrPimNgMvpnUMHPEStandbyAddr
            SYNTAX  InetAddress (SIZE (4))
            DESCRIPTION
                    "vRtrPimNgMvpnUMHPEStandbyAddr supports only
                     InetAddressType 'ipv4'."

        VARIATION   vRtrPimNgAFGenMvpnUMHSelection
            SYNTAX  INTEGER {
                        highestip    (0),
                        hashbased    (1)
                        -- tunnelstatus (2)
                    }
            DESCRIPTION
                    "vRtrPimNgAFGenMvpnUMHSelection does not support the value
                     'tunnelStatus (2)' for version 9.0R1 on  Alcatel-Lucent
                     SROS series systems."

    ::= { tmnxSROSV10v0 29 }  -- PIM

--
--  PORT CAPABILITIES
--
tmnxSROSPortCapsV10v0    AGENT-CAPABILITIES
    PRODUCT-RELEASE "Alcatel-Lucent SROS"
    STATUS          current
    DESCRIPTION     "Implementation of hardware port capabilities
                     for Alcatel-Lucent SROS release R10.0"

    SUPPORTS        TIMETRA-PORT-MIB
        INCLUDES    {
-- EXCLUDE  tmnxPortCemGroupV6v0                - Circuit Emulation
-- EXCLUDE  tmnxPortCEMGroupV8v0
            tmnxPortGroupV7v0,
            tmnxPortGroupV8v0,
            tmnxPortEthernetV7v0Group,
            tmnxPortEthernetV10v0Group,
            tmnxPortEtherPhysStatsGroup,
            tmnxPortDwdmGroup,
            tmnxWaveTrackerGroup,
            tmnxPortSonetV3v0Group,
            tmnxPortTDME1GroupV6v1,
            tmnxPortFRGroup,
            tmnxFrIntfGroup,            -- ASAP ports with FR
            tmnxFrf12IntfGroup,         -- ASAP ports with FR
            tmnxQosAppObjsGroup,
            tmnxPortQV8v0Group,
            tmnxPortQStatV7v0Group,
            tmnxPortNotificationGroupV8v0,
            tmnxPortNotificationGroupV9v4,
            tmnxPortIngrMdaQosStatR2r1Group,
            tmnxPortATMGroupV7v0,
            tmnxPortATMGroupV9v0,
            tmnxPortStatsR2r1Group,
            tmnxCiscoHDLCGroup,
            tmnxScalarPortV3v0Group,
            tmnxMlBundleGroupV6v0,
            tmnxMlImaBundleGroup,
            tmnxMcMfrBundleGroup,
            tmnxPortSchedV5v0Group,             -- QOS Port Scheduler Override
            tmnxMcMlpppBundleGroup,
-- EXCLUDE  tmnxPortTestGroup                   - not implemented
-- EXCLUDE  tmnx7710PortTDMGroupV5v0
            tmnxMlpppBundleGroup,
            tmnxMlpppBundleGroupV7v0,
            tmnxNamedPoolGroupV6v0,
            tmnxHsmdaGroupV10v0,
            tmnxDigitalDiagMonitorGroup,
            tmnxDDMLaneGroupV10v0,
            tmnxPortSchedStatsGroup,
            tmnxPortVPortV9v0Group,
            tmnxOpticalPortGroup,
            tmnxPortEgrExpShaperV9v0Group,
            tmnxOpticalPortGroupV9v0,
            tmnxPortNotifyObjsGroupV8v9,
            tmnxPortNotificationGroupV8v9,
            tmnxPortObjAppV9v0Group,
            tmnxPortEgrVPortStatsV9v0Group,
            tmnxPortEtherV9v0Group,
            tmnxPortNotificationV9v0Group,
            tmnxPortV9v0Group,
            tmnxPortNetEgrV10v0Group,
            tmnxPortPlcyGroup,
            tmnxPwPortV10v0Group,
            tmnxPortLoadBalGroupV10v0
        }

        VARIATION   tmnxPortEntry
            DESCRIPTION
                    "Vports are created by routed TLS and cannot be modified.
                    Management ports cannot be modified."

        VARIATION   tmnxPortClearAlarms
            ACCESS  read-only
            DESCRIPTION
                    "tmnxPortClearAlarms is implemented as read-only."

        VARIATION   tmnxPortMode
            DESCRIPTION
                    "tmnxPortMode is implemented as read-only for LAG ports
                    Multi-Link PPP (MLPPP) and IMA bundles, and ATM/FR ports.

                    Setting/changing tmnxPortMode on channelized interfaces is
                    H/W dependent."

        VARIATION   tmnxPortAlias
            DESCRIPTION
                    "tmnxPortAlias is implemented as read-only for LAG ports."

        VARIATION   tmnxPortDescription
            DESCRIPTION
                    "tmnxPortDescription is implemented as read-only for
                    LAG ports."

        VARIATION   tmnxPortEncapType
            SYNTAX  INTEGER {
                        unknown         (0),
                        nullEncap       (1),
                        qEncap          (2),
                        mplsEncap       (3),
                        bcpNullEncap    (4),
                        bcpDot1qEncap   (5),
                        ipcpEncap       (6),
                        frEncap         (7),
                        pppAutoEncap    (8),
                        atmEncap        (9),
                        qinqEncap       (10),
                        wanMirrorEncap  (11),
                        ciscoHDLCEncap  (12)
                    -- cemEncap        (13)  - CEM encap not supported
                    }
            DESCRIPTION
                    "tmnxPortEncapType is implemented as read-only for
                    Multi-Link PPP (MLPPP) bundles and IMA bundles.
                    Also the value 'cemEncap (13)' is not supported."

        VARIATION   tmnxPortHoldTimeUp
            DESCRIPTION
                    "tmnxPortHoldTimeUp is implemented as read-only for
                    LAG ports, Multi-Link PPP (MLPPP) bundles, and IMA
                    bundles."

        VARIATION   tmnxPortHoldTimeDown
            DESCRIPTION
                    "tmnxPortHoldTimeDown is implemented as read-only for
                    LAG ports, Multi-Link PPP (MLPPP) bundles, and IMA
                    bundles."

        VARIATION   tmnxPortNetworkEgrQueues
            DESCRIPTION
                    "tmnxPortNetworkEgrQueues is implemented as read-only for
                    LAG ports, Multi-Link PPP (MLPPP) bundles, and IMA
                    bundles.

                    tmnxPortNetworkEgrQueues can only be modified for
                    channels and ethernet ports."

        VARIATION   tmnxPortEtherMTU
            DESCRIPTION
                    "tmnxPortEtherMTU is implemented as read-only for
                    LAG ports."

        VARIATION   tmnxPortEtherDuplex
            DESCRIPTION
                    "tmnxPortEtherDuplex is implemented as read-only for
                    LAG ports that are not the primary LAG port."

        VARIATION   tmnxPortEtherSpeed
            DESCRIPTION
                    "tmnxPortEtherSpeed is implemented as read-only for
                    LAG ports that are not the primary LAG port."

        VARIATION   tmnxPortEtherAutoNegotiate
            DESCRIPTION
                    "tmnxPortEtherAutoNegotiate is implemented as read-only for
                    LAG ports that are not the primary LAG port."

        VARIATION   tmnxPortEtherAcctPolicyId
            DESCRIPTION
                    "tmnxPortEtherAcctPolicyId is implemented as read-only for
                    LAG ports that are not the primary LAG port."

        VARIATION   tmnxPortEtherCollectStats
            DESCRIPTION
                    "tmnxPortEtherCollectStats is implemented as read-only
                    for LAG ports that are not the primary LAG port."

        VARIATION   tmnxPortEtherXGigMode
            DESCRIPTION
                    "tmnxPortEtherXGigMode is implemented as read-only
                    for LAG ports that are not the primary LAG port."

        VARIATION   tmnxPortEtherEgressRate
            DESCRIPTION
                    "tmnxPortEtherEgressRate is implemented as read-only
                    for LAG ports that are not the primary LAG port."

        VARIATION   tmnxEqOobPortFailure
            ACCESS  not-implemented
            DESCRIPTION
                    "tmnxEqOobPortFailure notification is not implemented.
                    This notification was made obsolete in the 3.0 release.

                    The Out-of-band, OOB, port is what we refer to as the
                    management port or cpm port.  It has an entry in ifTable
                    and linkup, linkDown and tmnxEqPortError notifications
                    are sent for the management port just as for any other
                    port in the system."

        VARIATION   tmnxEqPortFailure
            ACCESS  not-implemented
            DESCRIPTION
                    "tmnxEqPortFailure notification is not implemented.
                    tmnxEqPortError is used instead.
                    This notification was made obsolete in the 3.0 release.

                    Standard IETF linkDown notification is sent when a
                    physical port failure is detected.  tmnxEqPortError is
                    sent with a ASCII reason message when port errors are
                    detected.

                    It was originally intended that tmnxEqPortError be used
                    to report errors that do not cause port state change to
                    'down'.

                    tmnxEqPortFailure was intended to report errors that
                    do cause the port state change to 'down'.

                    However, in the implementation tmnxEqPortError is used
                    for both fatal and non-fatal errors."

        VARIATION   tmnxEqPortWrongSFP
            ACCESS  not-implemented
            DESCRIPTION
                    "tmnxEqPortWrongSFP notification is not implemented.
                    In earlier releases it was generated when a wrong type
                    of SFP optics module was plugged into a 1 Gig MDA,
                    SONET MDA, or 100FX MDA.

                    Because of the large variety of SFPs now supported and
                    their different encoding schemes for compliance bits, the
                    check for wrong SFP has been removed.

                    A wrong SFP can be inferred from the port statistics."

        VARIATION   tmnxQosServiceDegraded
            ACCESS  not-implemented
            DESCRIPTION
                    "tmnxQosServiceDegraded notification is not implemented.
                    This notification was made obsolete in the 3.0 release."

        VARIATION   tmnxPortNotifyBerSdTca
            ACCESS  not-implemented
            DESCRIPTION
                    "tmnxPortNotifyBerSdTca notification is not implemented.
                    This notification was made obsolete in the 3.0 release."

        VARIATION   tmnxPortNotifyBerSfTca
            ACCESS  not-implemented
            DESCRIPTION
                    "tmnxPortNotifyBerSfTca notification is not implemented.
                    This notification was made obsolete in the 3.0 release."

        VARIATION   tmnxDS3ChannelClockSource
            SYNTAX  INTEGER {
                        loopTimed    (1),
                        nodeTimed    (2)
                    -- adaptive     (3)
                        -- differential (4)
                    }
            DESCRIPTION
                    "tmnxDS3ChannelClockSource values of 'adaptive (3)' and
                    'differential (4)' are not supported."

        VARIATION   tmnxDS3ChannelChannelized
            SYNTAX  INTEGER {
                        none   (1),
                        ds1    (2),
                        e1     (3)
                        -- j1  (4)
                    }
            DESCRIPTION
                    "tmnxDS3ChannelChannelized value of 'j1 (4)' is not
                    supported."

        VARIATION   tmnxBundleType
            SYNTAX  INTEGER {
                        mlppp   (1),
                    -- mlfr    (2)
                        imagrp  (3)
                    }
            DESCRIPTION
                    "tmnxBundleType value of 'mlfr (2)' is not
                    supported."

        VARIATION   tmnxPortTransceiverCode
            ACCESS  not-implemented
            DESCRIPTION
                    "tmnxPortTransceiverCode object is not implemented. This
                    object was made obsolete in the 5.0 release."

        VARIATION   tmnxDS3ChannelReportAlarm
            SYNTAX  BITS {
                    notUsed (0),
                    ais (1),
                    los (2),
                    oof (3),
                    rai (4),
                    looped (5)
                    -- berSd   (6)
                    -- berSf (7)
                }
            DESCRIPTION
                    "tmnxDS3ChannelReportAlarm does not support berSd and berSf
                    values of TmnxDSXReportAlarm"

        VARIATION   tmnxBundleImaGrpNeClockMode
            ACCESS  read-only
            DESCRIPTION
                    "The tmnxBundleImaGrpNeClockMode is implemented as
                     read-only."

        VARIATION   tmnxBundleImaGrpFeClockMode
            ACCESS  read-only
            DESCRIPTION
                    "The tmnxBundleImaGrpFeClockMode is implemented as
                     read-only."

        VARIATION  tmnxDS3ChannelRowStatus
            SYNTAX  INTEGER {
                        active      (1),
                        createAndGo (4),
                        destroy     (6)
                    }
            DESCRIPTION
                    "tmnxDS3ChannelRowStatus supports only the values
                    'active (1)', 'createAndGo (4)' and 'destroy (6)'."

        VARIATION  tmnxDS1RowStatus
            SYNTAX  INTEGER {
                        active      (1),
                        createAndGo (4),
                        destroy     (6)
                    }
            DESCRIPTION
                    "tmnxDS1RowStatus supports only the values
                    'active (1)', 'createAndGo (4)' and 'destroy (6)'."

        VARIATION  tmnxDS0ChanGroupRowStatus
            SYNTAX  INTEGER {
                        active      (1),
                        createAndGo (4),
                        destroy     (6)
                    }
            DESCRIPTION
                    "tmnxDS0ChanGroupRowStatus supports only the values
                    'active (1)', 'createAndGo (4)' and 'destroy (6)'."

        VARIATION  tmnxSonetPathRowStatus
            SYNTAX  INTEGER {
                        active      (1),
                        createAndGo (4),
                        destroy     (6)
                    }
            DESCRIPTION
                    "tmnxSonetPathRowStatus supports only the values
                    'active (1)', 'createAndGo (4)' and 'destroy (6)'."

        VARIATION  tmnxPortLastAlarmEvent
            DESCRIPTION
                    "tmnxPortLastAlarmEvent is not supported on Alcatel-Lucent
                     SROS systems. The value of tmnxPortLastAlarmEvent is
                     always '0.0'."

    ::= { tmnxSROSV10v0 30 }  -- PORT

tmnx7750PortCapsV10v0    AGENT-CAPABILITIES
    PRODUCT-RELEASE "Alcatel-Lucent SROS"
    STATUS          current
    DESCRIPTION     "Implementation of hardware port capabilities
                     for Alcatel-Lucent SROS 7750 release R10.0"

    SUPPORTS        TIMETRA-PORT-MIB
        INCLUDES    {
            tmnxPortTDMGroupV7v0,
            tmnxPortCemGroupV6v0,               -- Circuit Emulation
            tmnxPortCEMGroupV8v0
        }

        VARIATION   tmnxPortEncapType
            SYNTAX  INTEGER {
                        unknown         (0),
                        nullEncap       (1),
                        qEncap          (2),
                        mplsEncap       (3),
                        bcpNullEncap    (4),
                        bcpDot1qEncap   (5),
                        ipcpEncap       (6),
                        frEncap         (7),
                        pppAutoEncap    (8),
                        atmEncap        (9),
                        qinqEncap       (10),
                        wanMirrorEncap  (11),
                        ciscoHDLCEncap  (12),
                        cemEncap        (13)
                    }
            DESCRIPTION
                    "tmnxPortEncapType is implemented as read-only for
                    Multi-Link PPP (MLPPP) bundles and IMA bundles."

        VARIATION   tmnxDS1ClockSource
            SYNTAX  INTEGER {
                        loopTimed    (1),
                        nodeTimed    (2),
                        adaptive     (3)
                        -- differential (4)
                    }
            DESCRIPTION
                    "tmnxDS1ClockSource value of 'differential (4)' is not
                    supported."

    ::= { tmnxSROSPortCapsV10v0 1 }  -- 7750 PORT

tmnx7450PortCapsV10v0    AGENT-CAPABILITIES
    PRODUCT-RELEASE "Alcatel-Lucent SROS"
    STATUS          current
    DESCRIPTION     "Implementation of hardware port capabilities
                     for Alcatel-Lucent SROS 7450 release R10.0"

    SUPPORTS        TIMETRA-PORT-MIB
        INCLUDES    {
            tmnxPortGroupV7v0,
            tmnxPortTDMGroupV7v0
        }

        VARIATION   tmnxDS1ClockSource
            SYNTAX  INTEGER {
                        loopTimed    (1),
                        nodeTimed    (2)
                    -- adaptive     (3)
                        -- differential (4)
                    }
            DESCRIPTION
                    "tmnxDS1ClockSource values of 'adaptive (3)' and
                    'differential (4)' are not supported."
    ::= { tmnxSROSPortCapsV10v0 2 }  -- 7450 PORT

tmnxSprPortCapsV10v0    AGENT-CAPABILITIES
    PRODUCT-RELEASE "Alcatel-Lucent SROS"
    STATUS          current
    DESCRIPTION     "Implementation of specific hardware port capabilities
                     for Alcatel-Lucent SROS SPR release R10.0"

    SUPPORTS        TIMETRA-PORT-MIB
        INCLUDES    {
            tmnxPortGroupV7v0,
-- EXCLUDE  tmnxFrIntfGroup            - ASAP ports with FR
-- EXCLUDE  tmnxFrf12IntfGroup         - ASAP ports with FR
-- EXCLUDE  tmnxMlImaBundleGroup
-- EXCLUDE  tmnxMcMfrBundleGroup
            tmnxPortCemGroupV6v0,               -- Circuit Emulation
            tmnxPortCEMGroupV8v0,
            tmnx7710PortTDMGroupV5v0
-- EXCLUDE  tmnxNamedPoolGroupV6v0,
-- EXCLUDE  tmnxHsmdaGroupV10v0          no Q-MDA on SPR
        }

        VARIATION   tmnxPortEncapType
            SYNTAX  INTEGER {
                        unknown         (0),
                        nullEncap       (1),
                        qEncap          (2),
                        mplsEncap       (3),
                        bcpNullEncap    (4),
                        bcpDot1qEncap   (5),
                        ipcpEncap       (6),
                        frEncap         (7),
                        pppAutoEncap    (8),
                        atmEncap        (9),
                        qinqEncap       (10),
                        wanMirrorEncap  (11),
                        ciscoHDLCEncap  (12),
                        cemEncap        (13)
                    }
            DESCRIPTION
                    "tmnxPortEncapType is implemented as read-only for
                    Multi-Link PPP (MLPPP) bundles and IMA bundles."

    ::= { tmnxSROSPortCapsV10v0 3 }  -- SPR PORT

--
--  PPP CAPABILITIES
--
tmnxSROSPppCapsV10v0    AGENT-CAPABILITIES
    PRODUCT-RELEASE "Alcatel-Lucent SROS"
    STATUS          current
    DESCRIPTION     "Implementation of PPP protocol capabilities
                     for Alcatel-Lucent SROS release R10.0"

    SUPPORTS        TIMETRA-PPP-MIB
        INCLUDES    {
            tmnxPpp7450V4v0Group,
            tmnxPpp7750V4v0Group,
            tmnxPppNotificationGroup,
            tmnxPppCompressionGroup
        }

    ::= { tmnxSROSV10v0 31 }  -- PPP

--
--  QUALITY OF SERVICE, QOS, CAPABILITIES
--
tmnxSROSQosCapsV10v0    AGENT-CAPABILITIES
    PRODUCT-RELEASE "Alcatel-Lucent SROS"
    STATUS          current
    DESCRIPTION     "Implementation of Quality of Service, Qos, capabilities
                     for Alcatel-Lucent SROS release R10.0"

    SUPPORTS        TIMETRA-QOS-MIB
        INCLUDES    {
            tQosFCQGrpFC8v0Group,
            tQosQGrpFCGroup,
            tQosQGrpV8v0Group,
-- EXCLUDE  tmnxQosAtmTdpV5v0Group
-- EXCLUDE  tmnxQosAtmTdpV9v0Group
            tmnxQosBurstLimitGroup,
            tmnxQosDSCPGroup,
            tmnxQosEgrReClassifyV10v0Group,
            tmnxQosFCGroup,
            tmnxQosFrameBasedV6v0Group,
            tmnxQosGlobalGroup,
            tmnxQosHsmdaV9v0Group,
            tmnxQosMacCritVidFltrV9v0Group,
            tmnxQosMcFrEgrGroup,
            tmnxQosMcFrIngrGroup,
            tmnxQosMcMlpppEgrGroup,
            tmnxQosMcMlpppIngrGroup,
            tmnxQosNamedPoolPolicyV6v0Group,
            tmnxQosNetworkV7v0Group,
            tmnxQosNetworkV9v0Group,
            tmnxQosPolicerV8v0Group,
            tmnxQosPolicerV9v0Group,
            tmnxQosPortSchPlcyGrpGroup,
            tmnxQosQueueObjV8v0Group,
            tmnxQosQueueV4v0Group,
            tmnxQosSapAtmV7v0Group,
            tmnxQosSapEgrQWredGroup,
            tmnxQosSapEgressV8v0Group,
            tmnxQosSapEgressV9v0Group,
            tmnxQosSapIngressV9v0Group,
            tmnxQosSapIngressV10v0Group,
            tmnxQosSapIpv6FilterR4r0Group,
            tmnxQosSchedulerV5v0Group,
            tmnxQosSchedulerV8v0Group,
            tmnxQosSlopeGroup,
            tmnxQosPolicyV10v0Group,
            tmnxQosQueueGrpPolcrV10v0Group,
            tmnxQosNamedPoolV9v0Group,
            tmnxQosPolicerSlopeGroup,
            tmnxQosAdvConfigV10v0Group,
            tmnxQosHsmdaV10v0Group,
            tmnxQosNetworkV10v0Group
        }

        VARIATION   tSapEgressMatchCriteria
            SYNTAX  INTEGER {
                        ip(1),
                        -- mac(2),
                        none(3)
                    }
            DESCRIPTION
                    "tSapEgressMatchCriteria does not support the value
                    'mac' as defined by the TMatchCriteria
                    textual convention."

        VARIATION   tSapEgrIPCritSourceIpAddrType
            SYNTAX  INTEGER {
                        unknown     (0),
                        ipv4        (1)
                        -- ipv6     (2),
                        -- ipv4z    (3),
                        -- ipv6z    (4),
                        -- dns      (16)
                    }
            DESCRIPTION
                    "tSapEgrIPCritSourceIpAddrType only supports the values
                    'none' and 'ipv4' as defined by the InetAddressType
                    textual convention."

        VARIATION   tSapEgrIPCritDestIpAddrType
            SYNTAX  INTEGER {
                        unknown     (0),
                        ipv4        (1)
                        -- ipv6     (2),
                        -- ipv4z    (3),
                        -- ipv6z    (4),
                        -- dns      (16)
                    }
            DESCRIPTION
                    "tSapEgrIPCritDestIpAddrType only supports the values
                    'none' and 'ipv4' as defined by the InetAddressType
                    textual convention."

    ::= { tmnxSROSV10v0 32 }  -- QOS

tmnx7750QosCapsV10v0   AGENT-CAPABILITIES
    PRODUCT-RELEASE "Alcatel-Lucent SROS"
    STATUS          current
    DESCRIPTION     "Implementation of specific Quality of Service, Qos,
                     capabilities for Alcatel-Lucent SROS 7750 release R10.0"

    SUPPORTS        TIMETRA-QOS-MIB
        INCLUDES    {
            tmnxQosAtmTdpV5v0Group,
            tmnxQosAtmTdpV9v0Group
        }

    ::= { tmnxSROSQosCapsV10v0 1 }  -- 7750 QOS

tmnx7450QosCapsV10v0   AGENT-CAPABILITIES
    PRODUCT-RELEASE "Alcatel-Lucent SROS"
    STATUS          current
    DESCRIPTION     "Implementation of specific Quality of Service, Qos,
                     capabilities for Alcatel-Lucent SROS 7450 release R10.0"

    SUPPORTS        TIMETRA-QOS-MIB
        INCLUDES    {
            tmnxQosAtmTdpV5v0Group,
            tmnxQosAtmTdpV9v0Group
        }

    ::= { tmnxSROSQosCapsV10v0 2 }  -- 7450 QOS

tmnxSprQosCapsV10v0    AGENT-CAPABILITIES
    PRODUCT-RELEASE "Alcatel-Lucent SROS"
    STATUS          current
    DESCRIPTION     "Implementation of specific Quality of Service, Qos,
                     capabilities for Alcatel-Lucent SROS SPR release R10.0"

    SUPPORTS        TIMETRA-QOS-MIB
        INCLUDES    {
            tmnxQosAtmTdpV5v0Group,
            tmnxQosAtmTdpV9v0Group,
            tmnxQosSapIngressV10v0Group,
            tmnxQosSapEgressV8v0Group,
            tmnxQosQueueObjV8v0Group
-- EXCLUDE  tmnxQosNamedPoolPolicyV6v0Group   no named pools on SPR
        }

        VARIATION   tSapIngressQueuePoolName
            ACCESS  not-implemented
            DESCRIPTION
                    "tSapIngressQueuePoolName is not implemented on SPR
                     systems in 6.0 R1 release."

        VARIATION   tSapEgressQueuePoolName
            ACCESS  not-implemented
            DESCRIPTION
                    "tSapEgressQueuePoolName is not implemented on SPR
                     systems in 6.0 R1 release."

        VARIATION   tQosIngQueuePoolName
            ACCESS  not-implemented
            DESCRIPTION
                    "tQosIngQueuePoolName is not implemented on SPR
                     systems in 8.0 R1 release."

        VARIATION   tQosEgrQueuePoolName
            ACCESS  not-implemented

            DESCRIPTION
                    "tQosEgrQueuePoolName is not implemented on SPR
                     systems in 8.0 R1 release."

    ::= { tmnxSROSQosCapsV10v0 3 }  -- SPR QOS


tmnx7710QosCapsV10v0    AGENT-CAPABILITIES
    PRODUCT-RELEASE "Alcatel-Lucent SROS"
    STATUS          current
    DESCRIPTION     "Implementation of specific Quality of Service, Qos,
                     capabilities for Alcatel-Lucent SROS 7710 release R10.0"

    SUPPORTS        TIMETRA-QOS-MIB
        INCLUDES    {
-- EXCLUDE  tmnxQosPolicerV8v0Group,
            tmnxQosMacCritVidFltrV9v0Group,
            tQosQGrpV8v0Group,
            tmnxQosSapEgrQWredGroup
        }

        VARIATION   tQosEgrQGroupFCLastChanged
            ACCESS  not-implemented
            DESCRIPTION
                "tQosEgrQGroupFCLastChanged is not implemented on Alcatel-Lucent
                 7710 systems."

        VARIATION   tQosEgrQGroupFCQueue
            ACCESS  not-implemented
            DESCRIPTION
                "tQosEgrQGroupFCQueue is not implemented on Alcatel-Lucent
                 7710 systems."

        VARIATION   tQosEgrQGroupFCRowStatus
            ACCESS  not-implemented
            DESCRIPTION
                "tQosEgrQGroupFCRowStatus is not implemented on Alcatel-Lucent
                 7710 systems."

        VARIATION   tSapEgressQueueXPWredQ
            ACCESS  not-implemented
            DESCRIPTION
                "tSapEgressQueueXPWredQ is not implemented on Alcatel-Lucent
                 7710 systems."

        VARIATION   tSapEgressQueueXPWredQSlope
            ACCESS  not-implemented
            DESCRIPTION
                "tSapEgressQueueXPWredQSlope is not implemented on
                 Alcatel-Lucent 7710 systems."

        VARIATION   tSapIngressMacCritType
        DESCRIPTION
            "The value 'vid' is no supported on 7710"

    ::= { tmnxSROSQosCapsV10v0 4 }  -- 7710 QOS

--
--  RIP2 CAPABILITIES
--
tmnxSROSRip2CapsV10v0    AGENT-CAPABILITIES
    PRODUCT-RELEASE "Alcatel-Lucent SROS"
    STATUS          current
    DESCRIPTION     "Implementation of RIP-2 protocol capabilities
                     for Alcatel-Lucent SROS release R10.0"

    SUPPORTS        RIPv2-MIB
        INCLUDES    {
            rip2GlobalGroup,
            rip2IfStatGroup,
            rip2IfConfGroup,
            rip2PeerGroup
        }

        VARIATION   rip2IfConfDomain
            ACCESS  read-only
            DESCRIPTION
                    "rip2IfConfTable is implemented as read-only."

        VARIATION   rip2IfConfAuthType
            ACCESS  read-only
            DESCRIPTION
                    "rip2IfConfTable is implemented as read-only."

        VARIATION   rip2IfConfAuthKey
            ACCESS  read-only
            DESCRIPTION
                    "rip2IfConfTable is implemented as read-only."

        VARIATION   rip2IfConfSend
            ACCESS  read-only
            DESCRIPTION
                    "rip2IfConfTable is implemented as read-only."

        VARIATION   rip2IfConfReceive
            ACCESS  read-only
            DESCRIPTION
                    "rip2IfConfTable is implemented as read-only."

        VARIATION   rip2IfConfDefaultMetric
            ACCESS  read-only
            DESCRIPTION
                    "rip2IfConfTable is implemented as read-only."

        VARIATION   rip2IfConfStatus
            ACCESS  read-only
            DESCRIPTION
                    "rip2IfConfTable is implemented as read-only."

        VARIATION   rip2IfConfSrcAddress
            ACCESS  read-only
            DESCRIPTION
                    "rip2IfConfTable is implemented as read-only."

        VARIATION   rip2IfStatStatus
            ACCESS  read-only
            DESCRIPTION
                    "rip2IfStatStatus is implemented as read-only."

    SUPPORTS        TIMETRA-RIP-MIB
        INCLUDES    {
            tmnxRipGlobalGroup,
            tmnxRipV6v1Group,
            tmnxRipV7v0Group,
            tmnxRipInstanceGroup,
            tmnxRipGroupGroup,
            tmnxRipInterfaceGroup,
            tmnxRipRoutesGroup,
            tmnxRipPeerGroup,
            tmnxRipNotificationGroup,
            tmnxRipNotificationV7v0Group,
            tmnxRipRoutesV9v0R4Group
        }

    ::= { tmnxSROSV10v0 33 }  -- RIP-2

tmnx7950Rip2CapsV10v0    AGENT-CAPABILITIES
    PRODUCT-RELEASE "Alcatel-Lucent SROS"
    STATUS          current
    DESCRIPTION     "Implementation of RIP-2 protocol capabilities
                     for Alcatel-Lucent 7950 release R10.0"

--  SUPPORTS RIPv2-MIB
--    INCLUDES    {
--    }

    ::= { tmnxSROSRip2CapsV10v0    1 }  -- 7950 RIP-2
--
--  REMOTE MONITORING, RMON, CAPABILITIES
--
tmnxSROSRmonCapsV10v0    AGENT-CAPABILITIES
    PRODUCT-RELEASE "Alcatel-Lucent SROS"
    STATUS          current
    DESCRIPTION     "Implementation of Remote Monitoring, RMON, capabilities
                     for Alcatel-Lucent SROS release R10.0"

    SUPPORTS        RMON-MIB
        INCLUDES    {
            rmonEtherStatsGroup,
            rmonHistoryControlGroup,
            rmonEthernetHistoryGroup,
            rmonAlarmGroup,
            rmonEventGroup
-- EXCLUDE  rmonHostGroup
-- EXCLUDE  rmonHostTopNGroup
-- EXCLUDE  rmonMatrixGroup
-- EXCLUDE  rmonFilterGroup
-- EXCLUDE  rmonPacketCaptureGroup
        }

        VARIATION   etherStatsIndex
            SYNTAX  InterfaceIndex
            DESCRIPTION
                    "The agent creates a row entry in the etherStatsTable
                    for each ethernet port in the system that is indexed
                    by the port-id or ifIndex value and so has a larger
                    value range than that specified for etherStatsIndex
                    in the RMON-MIB."

        VARIATION   etherStatsDataSource
            ACCESS  read-only
            DESCRIPTION
                    "etherStatsTable is implemented as read-only.
                    The agent creates a row entry in the etherStatsTable
                    for each ethernet port in the system, indexed by the
                    port-id."

        VARIATION   etherStatsOwner
            ACCESS  read-only
            DESCRIPTION
                    "etherStatsTable is implemented as read-only."

        VARIATION   etherStatsStatus
            ACCESS  read-only
            DESCRIPTION
                    "etherStatsTable is implemented as read-only.  Rows cannot
                    be created by SNMP SET requests.  The agent creates a row
                    entry in the etherStatsTable for each ethernet port in
                    the system, indexed by the port-id."

         VARIATION etherStatsOversizePkts
            DESCRIPTION
                    "etherStatsOversizePkts indicates the total number of
                    packets received that were longer than the maximum frame
                    size for the particular media, usually 12287 octets
                    (excluding framing bits, but including FCS octets), and
                    were otherwise well formed.

                    TIMETRA-PORT-MIB::tmnxPortEtherPkts1519toMax,
                    TIMETRA-PORT-MIB::tmnxPortEtherHCOverPkts1519toMax and
                    TIMETRA-PORT-MIB::tmnxPortEtherHCPkts1519toMax are used
                    to indicate the total number of packets received that
                    were longer than 1518 octets but less than the maximum
                    frame size for the particular media, usually 12287 octets
                    (excluding framing bits, but including FCS octets)."

        VARIATION   alarmOwner
            SYNTAX  OwnerString (SIZE (0..80))
            DESCRIPTION
                    "The length of the alarmOwner string is limited to a
                    maximum of  80 characters."

        VARIATION   eventOwner
            SYNTAX  OwnerString (SIZE (0..80))
            DESCRIPTION
                    "The length of the eventOwner string is limited to a
                    maximum of  80 characters."

    SUPPORTS        HC-RMON-MIB
        INCLUDES    {
            mediaIndependentGroup,
            etherStatsHighCapacityGroup,
            etherHistoryHighCapacityGroup,
            hcRMONInformationGroup
        }

        VARIATION   mediaIndependentIndex
            SYNTAX  InterfaceIndex
            DESCRIPTION
                    "The agent creates a row entry in the mediaIndependentTable
                    for each physical port in the system, indexed by the
                    port-id which is also the ifIndex and has a larger value
                    range than that specified for mediaIndependentIndex in
                    the HC-RMON-MIB."

        VARIATION   mediaIndependentDataSource
            ACCESS  read-only
            DESCRIPTION
                    "mediaIndependentTable is implemented as read-only.
                    The agent creates a row entry in the mediaIndependentTable
                    for each physical port in the system, indexed by the
                    port-id."

        VARIATION   mediaIndependentOwner
            ACCESS  read-only
            DESCRIPTION
                    "mediaIndependentTable is implemented as read-only."

        VARIATION   mediaIndependentStatus
            ACCESS  read-only
            DESCRIPTION
                    "mediaIndependentTable is implemented as read-only.
                    Rows cannot be created in the table by SNMP SET requests.
                    The agent creates a row entry in the mediaIndependentTable
                    for each physical port in the system, indexed by the
                    port-id."

    ::= { tmnxSROSV10v0 34 }  -- RMON

--
--  ROUTE POLICY CAPABILITIES
--
tmnxSROSRoutePolicyCapsV10v0    AGENT-CAPABILITIES
    PRODUCT-RELEASE "Alcatel-Lucent SROS"
    STATUS          current
    DESCRIPTION     "Implementation of Route Policy capabilities
                     for Alcatel-Lucent SROS release R10.0"

    SUPPORTS        TIMETRA-ROUTE-POLICY-MIB
        INCLUDES    {
            tmnxRPASPathObjectsV5v0Group,
            tmnxRPAdminControlObjectsGroup,
            tmnxRPCommunityObjectsV5v0Group,
            tmnxRPDampingObjectsV5v0Group,
            tmnxRPInetPrefixListObjectsV5v0Group,
            tmnxRPPolicyEntryObjectsV9v0Group,
            tmnxRPPolicyObjectsV7v0Group,
            tmnxRPPolicyObjectsV8v0Group,
-- EXCLUDE  tmnxRPPolicyObjectsV9v0Group,
            tmnxRPPrefixListObjectsV5v0Group,
            tmnxRPQPPBV9v0R4Group,
            tmnxRPPolicyObjectsV10v0Group,
            tmnxRPASPathGroupV10v0Group
        }

        VARIATION   tRPOperPSFromCriteriaFamily
            SYNTAX  BITS {
                        ipv4Unicast     (0),
                        ipv4Multicast   (1),
                        ipv4UastMcast   (2),
                        ipv4MplsLabel   (3),
                        ipv4Vpn         (4),
                        ipv6Unicast     (5),
                        -- ipv6Multicast(6),
                        ipv6UcastMcast  (7),
                        ipv6MplsLabel   (8),
                        ipv6Vpn         (9),
                        l2Vpn           (10),
                        ipv4Mvpn        (11),
                        msPw            (12),
                        ipv4Flow        (13),
                        mdtSafi         (14),
                        routeTarget     (15),
                        mcastVpnIpv4    (16)
                    }
            DESCRIPTION
                    "The tRPOperPSFromCriteriaFamily does not support the value
                    'ipv6Multicast (6)' as defined by the TmnxBGPFamilyType 
                    textual convention."

        VARIATION   tRPAdminPSFromCriteriaFamily
            SYNTAX  BITS {
                        ipv4Unicast      (0),
                        ipv4Multicast    (1),
                        --ipv4UastMcast  (2),
                        --ipv4MplsLabel  (3),
                        ipv4Vpn          (4),
                        ipv6Unicast      (5),
                        ipv6Multicast    (6),
                        --ipv6UcastMcast (7),
                        --ipv6MplsLabel  (8),
                        ipv6Vpn          (9),
                        l2Vpn            (10),
                        ipv4Mvpn         (11),
                        msPw             (12),
                        ipv4Flow         (13),
                        mdtSafi          (14),
                        routeTarget      (15),
                        mcastVpnIpv4     (16)
                    }
            DESCRIPTION
                    "The tRPAdminPSFromCriteriaFamily does not support
                    the value 'ipv4UastMcast (2)', 'ipv4MplsLabel (3)',
                    'ipv6UcastMcast (7)', and 'ipv6MplsLabel (8) as
                    defined by the TmnxBGPFamilyType textual convention."

        VARIATION   tRPOperASPathTableLastChanged
            ACCESS  not-implemented
            DESCRIPTION
                    "tRPOperASPathTableLastChanged is obsoleted in release 5.0.
                    TIMETRA-SYSTEM-MIB::tmnxConfigModify notification is used
                    instead."

        VARIATION   tRPOperASPathEntryLastChanged
            ACCESS  not-implemented
            DESCRIPTION
                    "tRPOperASPathEntryLastChanged is obsoleted in release 5.0.
                     TIMETRA-SYSTEM-MIB::tmnxConfigModify notification is used
                     instead."

        VARIATION   tRPOperCommunityTableLastChanged
            DESCRIPTION
                    "tRPOperCommunityTableLastChanged is obsoleted in release
                    5.0.  TIMETRA-SYSTEM-MIB::tmnxConfigModify notification
                    is used instead."

        VARIATION   tRPOperCommunityEntryLastChanged
            DESCRIPTION
                    "tRPOperCommunityEntryLastChanged is obsoleted in release
                    5.0.  TIMETRA-SYSTEM-MIB::tmnxConfigModify notification
                    is used instead."

        VARIATION   tRPOperDampingTableLastChanged
            DESCRIPTION
                    "tRPOperDampingTableLastChanged is obsoleted in release
                    5.0.  TIMETRA-SYSTEM-MIB::tmnxConfigModify notification
                    is used instead."

        VARIATION   tRPOperDampingEntryLastChanged
            DESCRIPTION
                    "tRPOperDampingEntryLastChanged is obsoleted in release
                    5.0.  TIMETRA-SYSTEM-MIB::tmnxConfigModify notification
                    is used instead."

        VARIATION   tRPOperPrefixListTableLastChanged
            DESCRIPTION
                    "tRPOperPrefixListTableLastChanged is obsoleted in release
                    5.0.  TIMETRA-SYSTEM-MIB::tmnxConfigModify notification is
                    used instead."

        VARIATION   tRPOperPrefixListEntryLastChanged
            DESCRIPTION
                    "tRPOperPrefixListEntryLastChanged is obsoleted in release
                    5.0.  TIMETRA-SYSTEM-MIB::tmnxConfigModify notification is
                    used instead."

        VARIATION   tRPOperPolicyStatementTableLastChanged
            DESCRIPTION
                    "tRPOperPolicyStatementTableLastChanged is obsoleted in
                    release 5.0.  TIMETRA-SYSTEM-MIB::tmnxConfigModify
                    notification is used instead."

        VARIATION   tRPOperPolicyStatementEntryLastChanged
            DESCRIPTION
                    "tRPOperPolicyStatementEntryLastChanged is obsoleted in
                    release 5.0.  TIMETRA-SYSTEM-MIB::tmnxConfigModify
                    notification is used instead."

        VARIATION   tRPOperPSDefaultActionParamsTableLastChanged
            DESCRIPTION
                    "tRPOperPSDefaultActionParamsTableLastChanged is obsoleted
                    in release 5.0.  TIMETRA-SYSTEM-MIB::tmnxConfigModify
                    notification is used instead."

        VARIATION   tRPOperPSDefaultActionParamsEntryLastChanged
            DESCRIPTION
                    "tRPOperPSDefaultActionParamsEntryLastChanged is obsoleted
                    in release 5.0.   TIMETRA-SYSTEM-MIB::tmnxConfigModify
                    notification is used instead."

        VARIATION   tRPOperPSParamsTableLastChanged
            DESCRIPTION
                    "tRPOperPSParamsTableLastChanged is obsoleted in release
                    5.0.  TIMETRA-SYSTEM-MIB::tmnxConfigModify notification is
                    used instead."

        VARIATION   tRPOperPSParamsEntryLastChanged
            DESCRIPTION
                    "tRPOperPSParamsEntryLastChanged is obsoleted in release
                    5.0.  TIMETRA-SYSTEM-MIB::tmnxConfigModify notification is
                    used instead."

        VARIATION   tRPOperPSAcceptActionParamsTableLastChanged
            DESCRIPTION
                    "tRPOperPSAcceptActionParamsTableLastChanged is obsoleted
                    in release 5.0.  TIMETRA-SYSTEM-MIB::tmnxConfigModify
                    notification is used instead."

        VARIATION   tRPOperPSAcceptActionParamsEntryLastChanged
            DESCRIPTION
                    "tRPOperPSAcceptActionParamsEntryLastChanged is obsoleted
                    in release 5.0.  TIMETRA-SYSTEM-MIB::tmnxConfigModify
                    notification is used instead."

        VARIATION   tRPOperPSToCriteriaTableLastChanged
            DESCRIPTION
                    "tRPOperPSToCriteriaTableLastChanged is obsoleted in
                    release 5.0.  TIMETRA-SYSTEM-MIB::tmnxConfigModify
                    notification is used instead."

        VARIATION   tRPOperPSToCriteriaEntryLastChanged
            DESCRIPTION
                    "tRPOperPSToCriteriaEntryLastChanged is obsoleted in
                    release 5.0.  TIMETRA-SYSTEM-MIB::tmnxConfigModify
                    notification is used instead."

        VARIATION   tRPOperPSFromCriteriaTableLastChanged
            DESCRIPTION
                    "tRPOperPSFromCriteriaTableLastChanged is obsoleted in
                    release 5.0.  TIMETRA-SYSTEM-MIB::tmnxConfigModify
                    notification is used instead."

        VARIATION   tRPOperPSFromCriteriaEntryLastChanged
            DESCRIPTION
                    "tRPOperPSFromCriteriaEntryLastChanged is obsoleted in
                    release 5.0.  TIMETRA-SYSTEM-MIB::tmnxConfigModify
                    notification is used instead."

        VARIATION   tRPOperInetPrefixListTblLastChg
            DESCRIPTION
                    "tRPOperInetPrefixListTblLastChg is obsoleted in
                    release 5.0.  TIMETRA-SYSTEM-MIB::tmnxConfigModify
                    notification is used instead."

        VARIATION   tRPOperInetPrefixListLastChg
            DESCRIPTION
                    "tRPOperInetPrefixListLastChg is obsoleted in release 5.0.
                    TIMETRA-SYSTEM-MIB::tmnxConfigModify notification is used
                    instead."

        VARIATION   tRPAdminPSDefaultActionASPath
            DESCRIPTION
                    "tRPAdminPSDefaultActionASPath does not support the value
                    'remove(3)' as defined by TPolicyEntryEdit textual
                    convention."

        VARIATION   tRPAdminPSAcceptActionASPath
            DESCRIPTION
                    "tRPAdminPSAcceptActionASPath does not support the value
                    'remove(3)' as defined by TPolicyEntryEdit textual
                    convention."

        VARIATION   tRPAdminPSDefaultActionOrigin
            SYNTAX  INTEGER {
                        none            (1),
                        igp             (2),
                        egp             (3),
                        incomplete      (4)
                        -- any          (5),
                        -- aaa          (6),
                        -- dhcp         (7),
                        -- ludb         (8)
                    }
            DESCRIPTION
                    "tRPAdminPSDefaultActionOrigin does not support the values
                     'any(5)', 'aaa(6)', 'dhcp(7)' and 'ludb(8)'."

        VARIATION   tRPAdminPSAcceptActionOrigin
            SYNTAX  INTEGER {
                        none            (1),
                        igp             (2),
                        egp             (3),
                        incomplete      (4)
                        -- any          (5),
                        -- aaa          (6),
                        -- dhcp         (7),
                        -- ludb         (8)
                    }
            DESCRIPTION
                    "tRPAdminPSAcceptActionOrigin does not support the values
                     'any(5)', 'aaa(6)', 'dhcp(7)' and 'ludb(8)'."

        VARIATION   tRPAdminPSAcptActionAigpMetric
            ACCESS  not-implemented
            DESCRIPTION
                "tRPAdminPSAcptActionAigpMetric is not implemented."

        VARIATION   tRPAdminPSAcptActnAigpMetricVal
            ACCESS  not-implemented
            DESCRIPTION
                "tRPAdminPSAcptActnAigpMetricVal is not implemented."

        VARIATION   tRPOperPSAcptActionAigpMetric
            ACCESS  not-implemented
            DESCRIPTION
                "tRPOperPSAcptActionAigpMetric is not implemented."

        VARIATION   tRPOperPSAcptActnAigpMetricVal
            ACCESS  not-implemented
            DESCRIPTION
                "tRPOperPSAcptActnAigpMetricVal is not implemented."

        VARIATION   tRPAdminPSDefActionAigpMetric
            ACCESS  not-implemented
            DESCRIPTION
                "tRPAdminPSDefActionAigpMetric is not implemented."

        VARIATION   tRPAdminPSDefActnAigpMetricVal
            ACCESS  not-implemented
            DESCRIPTION
                "tRPAdminPSDefActnAigpMetricVal is not implemented."

        VARIATION   tRPOperPSDefActionAigpMetric
            ACCESS  not-implemented
            DESCRIPTION
                "tRPOperPSDefActionAigpMetric is not implemented."

        VARIATION   tRPOperPSDefActnAigpMetricVal
            ACCESS  not-implemented
            DESCRIPTION
                "tRPOperPSDefActnAigpMetricVal is not implemented."

        VARIATION  tRPAdminCommunityRowStatus
            SYNTAX  INTEGER {
                        active           (1),
                        -- notInService  (2),
                        -- notReady      (3),
                        createAndGo      (4),
                        --createAndWait  (5),
                        destroy          (6)
                    }
            DESCRIPTION
                    "tRPAdminCommunityRowStatus supports only 'active (1)',
                     'createAndGo (4)', and 'destroy (6)'."

        VARIATION  tRPAdminASPathGroupRowStatus
            SYNTAX  INTEGER {
                        active           (1),
                        -- notInService  (2),
                        -- notReady      (3),
                        createAndGo      (4),
                        --createAndWait  (5),
                        destroy          (6)
                    }
            DESCRIPTION
                    "tRPAdminASPathGroupRowStatus supports only 'active (1)',
                     'createAndGo (4)', and 'destroy (6)'."

        VARIATION tRPAdminASPathGroupASPathName
            ACCESS  not-implemented
            DESCRIPTION
                "tRPAdminASPathGroupASPathName is not implemented."

        VARIATION tRPOperASPathGroupASPathName
            ACCESS  not-implemented
            DESCRIPTION
                "tRPOperASPathGroupASPathName is not implemented."

    ::= { tmnxSROSV10v0 35 }  -- ROUTE-POLICY

--
--  RSVP CAPABILITIES
--
tmnxSROSRsvpCapsV10v0    AGENT-CAPABILITIES
    PRODUCT-RELEASE "Alcatel-Lucent SROS"
    STATUS          current
    DESCRIPTION     "Implementation of RSVP protocol capabilities
                     for Alcatel-Lucent SROS release R10.0"

    SUPPORTS        RSVP-MIB
        INCLUDES    {
-- EXCLUDE  rsvpSessionGroup,
-- EXCLUDE  rsvpSenderGroup,
-- EXCLUDE  rsvpResvGroup,
-- EXCLUDE  rsvpResvFwdGroup,
            rsvpIfGroup,
            rsvpNbrGroup,
            rsvpNotificationGroup
        }

        VARIATION   rsvpNbrProtocol
            ACCESS  read-only
            DESCRIPTION
                    "rsvpNbrTable is implemented as read-only."

        VARIATION   rsvpNbrStatus
            ACCESS  read-only
            DESCRIPTION
                    "The rsvpNbrTable is implemented as read-only.  Row
                    entries cannot be created by SNMP SET requests."

        VARIATION   newFlow
            ACCESS  not-implemented
            DESCRIPTION
                    "newFlow notification is not implemented."

        VARIATION   lostFlow
            ACCESS  not-implemented
            DESCRIPTION
                    "lostFlow notification is not implemented."

        VARIATION   rsvpIfRefreshInterval
            ACCESS  not-implemented
            DESCRIPTION
                    "rsvpIfRefreshInterval is not implemented."

        VARIATION   rsvpIfUdpRequired
            ACCESS  read-only
            DESCRIPTION
                    "rsvpIfUdpRequired is implemented as read-only."

        VARIATION   rsvpIfRefreshBlockadeMultiple
            ACCESS  read-only
            DESCRIPTION
                    "rsvpIfRefreshBlockadeMultiple is implemented as read-only."

        VARIATION   rsvpIfRefreshMultiple
            ACCESS  read-only
            DESCRIPTION
                    "rsvpIfRefreshMultiple is implemented as read-only."

        VARIATION   rsvpIfTTL
            ACCESS  read-only
            DESCRIPTION
                    "rsvpIfTTL is implemented as read-only."

        VARIATION   rsvpIfRouteDelay
            ACCESS  read-only
            DESCRIPTION
                    "rsvpIfRouteDelay is implemented as read-only."

    SUPPORTS        TIMETRA-RSVP-MIB
        INCLUDES    {
            tmnxRsvpGeneralGroup,
            tmnxRsvpIfV5v0Group,
            tmnxRsvpSessionGroup,
            tmnxRsvpNotificationGroup,
            tmnxRsvpSessionV5v0Group,
            tmnxRsvpGeneralV6v0Group,
            tmnxRsvpGeneralV6v1Group,
            tmnxRsvpIfV6v0Group,
            tmnxRsvpSessionV6v0Group,
            tmnxRsvpNbrV6v0Group,
            tmnxRsvpSessionV6v0Group,
            tmnxRsvpGeneralV6v1Group,
            tmnxRsvpIfV7v0Group,
            tmnxRsvpDSTEV7v0Group,
            tmnxRsvpGeneralV7v0Group,
            tmnxRsvpSessionV7v0Group,
            tmnxRsvpGeneralV8v0Group,
            tmnxRsvpIfV8v0Group,
            tmnxRsvpGenTEThresholdV8v0Group,
            tmnxRsvpIfTEThresholdV8v0Group,
            tmnxRsvpGeneralV9v0Group,
            tmnxRsvpNotificationV9v0Group,
            tmnxRsvpGeneralV10v0Group
        }

        VARIATION   vRtrRsvpIfKeepMultiplier
            ACCESS  not-implemented
            DESCRIPTION
                    "vRtrRsvpIfKeepMultiplier is obsoleted in release 3.0."

        VARIATION   vRtrRsvpIfRefreshTime
            ACCESS  not-implemented
            DESCRIPTION
                    "vRtrRsvpIfRefreshTime is obsoleted in release 3.0."

        VARIATION   vRtrRsvpIfAggregate
            ACCESS  read-only
            DESCRIPTION
                    "vRtrRsvpIfAggregate is implemented as read-only."

        VARIATION   vRtrRsvpIfAuthChallenge
            ACCESS  not-implemented
            DESCRIPTION
                    "vRtrRsvpIfAuthChallenge is not supported in release 5.0."

        VARIATION   vRtrRsvpDSTEAdmCtlModel
            SYNTAX   INTEGER {
                     basic (0),
                     mam (1)
                     -- rdm (2)
                     }
            DESCRIPTION
                 "vRtrRsvpDSTEAdmCtlModel does not support the value 'rdm' in
                  release 8.0."

        VARIATION   vRtrRsvpDSTEFCMappingRowStatus
            SYNTAX  INTEGER {
                        active           (1),
                        -- notInService  (2),
                        -- notReady      (3),
                        createAndGo      (4),
                        --createAndWait  (5),
                        destroy          (6)
                    }
            DESCRIPTION
                    "vRtrRsvpDSTEFCMappingRowStatus supports only 'active (1)',
                     'createAndGo (4)', and 'destroy (6)'. "

    ::= { tmnxSROSV10v0 36 }  -- RSVP

--
--  SECURITY CAPABILITIES
--
tmnxSROSSecurityCapsV10v0    AGENT-CAPABILITIES
    PRODUCT-RELEASE "Alcatel-Lucent SROS"
    STATUS          current
    DESCRIPTION     "Implementation of Security capabilities
                     for Alcatel-Lucent SROS release R10.0"

    SUPPORTS        TIMETRA-SECURITY-MIB
        INCLUDES    {
            tmnxSecurityUserV6v0Group,
            tmnxSecurityUserActionGroup,
            tmnxSecurityMafV6v0Group,
            tmnxSecurityPasswordsV6v0Group,
            tmnxSecurityRadiusV5v0Group,
            tmnxSecurityRadiusAuthV5v0Group,
            tmnxSecurityTacPlusV8v0Group,
            tmnxSecurityServerCtlV4v0Group,
            tmnxSecurityCpmGroup,
            tmnxSecurityPasswordHashGroup,
            tmnxSecurityCpmIPv6FilterV4v0Group,
            tmnxSecurityCpmIpFilterV5v0Group,
            tmnxSSHServerV4v0Group,
            tmnxSecurityNotificationV5v0Group,
            tmnxSecuritySourceIpV4v0Group,
            tmnxSecurityKeyChainV5v0Group,
-- EXCLUDE  tmnxSecurityCpmProtectGroup,
            tmnxSecurityLiGroup,
-- EXCLUDE  tmnxSecurityCpmProtNotificationGroup,
-- EXCLUDE  tmnxSecurityCpmMacFilterGroup
            tmnxSecurityMafMacFilterGroup,
-- EXCLUDE  tmnxSecurityV7v0Group,
-- EXCLUDE  tmnxSecurityCpmProtNotifyV7v0Grp,
            tmnxSecurityNotifyObjsV8v0Group,
-- EXCLUDE  tmnxSecPkiV9v0Grp,      - 9.0 R4 feature
            tmnxSecurityNotificationV8v0Grp,
            tmnxSecurityNwExceptionsGroup,
            tmnxCertNotifyGroup,
            tmnxRadiusUserGroup,
            tmnxRadiusUserExGroup,
            tmnxCpmFltrPrefixListV10v0Group
        }

        VARIATION   tmnxRadiusServerRowStatus
            SYNTAX  INTEGER {
                        active      (1),
                        createAndGo (4),
                        destroy     (6)
                     }
            DESCRIPTION
                    "tmnxRadiusServerRowStatus supports only the values
                    'active (1)', 'createAndGo (4)' and 'destroy (6)'."

        VARIATION   tmnxRadiusServerInetAddressType
            SYNTAX  INTEGER {
                        unknown     (0),
                        ipv4        (1),
                        ipv6        (2)
                        -- ipv4z    (3),
                        -- ipv6z    (4),
                        -- dns      (16)
                    }
            DESCRIPTION
                    "tmnxRadiusServerInetAddressType object does not support
                    address of type 'ipv6z (4)'."

        VARIATION   tmnxRadiusServerInetAddress
            SYNTAX  InetAddress (SIZE(0|4|16))
            DESCRIPTION
                   "tmnxRadiusServerInetAddress supports only address of types
                   'ipv4 (1)' and 'ipv6 (2)'. tmnxRadiusServerInetAddress does
                   not support address of type 'ipv6z (4)'."

        VARIATION   tmnxTacPlusServerInetAddressType
            SYNTAX  INTEGER {
                        unknown     (0),
                        ipv4        (1),
                        ipv6        (2)
                        -- ipv4z    (3),
                        -- ipv6z    (4),
                        -- dns      (16)
                    }
            DESCRIPTION
                    "tmnxTacPlusServerInetAddressType object does not support
                    address of type 'ipv6z (4)'."

        VARIATION   tmnxTacPlusServerRowStatus
            SYNTAX  INTEGER {
                        active      (1),
                        createAndGo (4),
                        destroy     (6)
                     }
            DESCRIPTION
                    "tmnxTacPlusServerRowStatus supports only the values
                    'active (1)', 'createAndGo (4)' and 'destroy (6)'."

        VARIATION   tmnxTacPlusServerInetAddress
            SYNTAX  InetAddress (SIZE(0|4|16))
            DESCRIPTION
                   "tmnxTacPlusServerInetAddress supports only address of types
                   'ipv4 (1)' and 'ipv6 (2)'. tmnxTacPlusServerInetAddress does
                   not support address of type 'ipv6z (4)'."

        VARIATION   tmnxCpmProtPolRowStatus
            SYNTAX  INTEGER {
                        active      (1),
                        createAndGo (4),
                        destroy     (6)
                     }
            DESCRIPTION
                    "tmnxCpmProtPolRowStatus supports only the values
                    'active (1)', 'createAndGo (4)' and 'destroy (6)'."

        VARIATION   tmnxCpmProtViolVdoSvcEntry
            ACCESS  not-implemented
            DESCRIPTION
                    "tmnxCpmProtViolVdoSvcEntry is not implemented on SR-1
                     or ESS-1 where the value of TIMETRA-CHASSIS-MIB::
                     tmnxChassisType is '5'."

        VARIATION   tmnxCpmProtViolVdoVrtrEntry
            ACCESS  not-implemented
            DESCRIPTION
                    "tmnxCpmProtViolVdoVrtrEntry is not implemented on
                     SR-1 or ESS-1, where the value of
                     TIMETRA-CHASSIS-MIB::tmnxChassisType is '5'."

        VARIATION   tmnxCpmProtViolVdoSvcClient
            ACCESS  not-implemented
            DESCRIPTION
                    "tmnxCpmProtViolVdoSvcClient is not implemented on SR-1
                     or ESS-1, where the value of TIMETRA-CHASSIS-MIB::
                     tmnxChassisType is '5'."

        VARIATION   tmnxCpmProtViolVdoVrtrClient
            ACCESS  not-implemented
            DESCRIPTION
                    "tmnxCpmProtViolVdoVrtrClient is not implemented on SR-1
                     or ESS-1, where the value of TIMETRA-CHASSIS-MIB::
                     tmnxChassisType is '5'."

        VARIATION   tmnxCpmProtEthCfmPolLastChanged
            DESCRIPTION
                    "tmnxCpmProtEthCfmPolLastChanged is not supported on 7450
                     ESS-1 or 7750 SR-1."

        VARIATION   tmnxCpmProtEthCfmPolLevelSet
            DESCRIPTION
                    "tmnxCpmProtEthCfmPolLevelSet is not supported on 7450
                     ESS-1 or 7750 SR-1."

        VARIATION   tmnxCpmProtEthCfmPolOpCodeSet
            DESCRIPTION
                    "tmnxCpmProtEthCfmPolOpCodeSet is not supported on 7450
                     ESS-1 or 7750 SR-1."

        VARIATION   tmnxCpmProtEthCfmPolRateLimit
            DESCRIPTION
                    "tmnxCpmProtEthCfmPolRateLimit is not supported on 7450
                     ESS-1 or 7750 SR-1."

        VARIATION   tmnxCpmProtEthCfmPolRowStatus
            SYNTAX  INTEGER {
                        active      (1),
                        createAndGo (4),
                        destroy     (6)
                     }
            DESCRIPTION
                    "tmnxCpmProtEthCfmPolRowStatus supports only the values
                     'active (1)', 'createAndGo (4)' and 'destroy (6)'.  The
                     object is not supported on 7450 ESS-1 or 7750 SR-1."

        VARIATION   tmnxCpmProtEthCfmPolTableLastChg
            DESCRIPTION
                    "tmnxCpmProtEthCfmPolTableLastChg is not supported on 7450
                     ESS-1 or 7750 SR-1."

        VARIATION   tmnxCpmProtExcdSapEcmPeriods
            DESCRIPTION
                    "tmnxCpmProtExcdSapEcmPeriods is not supported on 7450
                     ESS-1 or 7750 SR-1."

        VARIATION   tmnxCpmProtExcdSapEcmStarted
            DESCRIPTION
                    "tmnxCpmProtExcdSapEcmStarted is not supported on 7450
                     ESS-1 or 7750 SR-1."

        VARIATION   tmnxCpmProtExcdSapEcmTblLChg
            DESCRIPTION
                    "tmnxCpmProtExcdSapEcmTblLChg is not supported on 7450
                     ESS-1 or 7750 SR-1."

        VARIATION   tmnxCpmProtExcdSapEcmTime
            DESCRIPTION
                    "tmnxCpmProtExcdSapEcmTime is not supported on 7450
                     ESS-1 or 7750 SR-1."

        VARIATION   tmnxCpmProtExcdSdpBindEcmPeriods
            DESCRIPTION
                    "tmnxCpmProtExcdSdpBindEcmPeriods is not supported on 7450
                     ESS-1 or 7750 SR-1."

        VARIATION   tmnxCpmProtExcdSdpBindEcmStarted
            DESCRIPTION
                    "tmnxCpmProtExcdSdpBindEcmStarted is not supported on 7450
                     ESS-1 or 7750 SR-1."

        VARIATION   tmnxCpmProtExcdSdpBindEcmTblLChg
            DESCRIPTION
                    "tmnxCpmProtExcdSdpBindEcmTblLChg is not supported on 7450
                     ESS-1 or 7750 SR-1."

        VARIATION   tmnxCpmProtExcdSdpBindEcmTime
            DESCRIPTION
                    "tmnxCpmProtExcdSdpBindEcmTime is not supported on 7450
                     ESS-1 or 7750 SR-1."

        VARIATION   tmnxCpmProtExcdSdpBindPeriods
            DESCRIPTION
                    "tmnxCpmProtExcdSdpBindPeriods is not supported on 7450
                     ESS-1 or 7750 SR-1."

        VARIATION   tmnxCpmProtExcdSdpBindTblLastChg
            DESCRIPTION
                    "tmnxCpmProtExcdSdpBindTblLastChg is not supported on 7450
                     ESS-1 or 7750 SR-1."

        VARIATION   tmnxCpmProtExcdSdpBindTime
            DESCRIPTION
                    "tmnxCpmProtExcdSdpBindTime is not supported on 7450
                     ESS-1 or 7750 SR-1."

        VARIATION   tmnxCpmProtExcdSdpBindTimeStartd
            DESCRIPTION
                    "tmnxCpmProtExcdSdpBindTimeStartd is not supported on 7450
                     ESS-1 or 7750 SR-1."

        VARIATION   tmnxCpmProtViolSdpBindPeriods
            DESCRIPTION
                    "tmnxCpmProtViolSdpBindPeriods is not supported on 7450
                     ESS-1 or 7750 SR-1."

        VARIATION   tmnxCpmProtViolSdpBindTblLastChg
            DESCRIPTION
                    "tmnxCpmProtViolSdpBindTblLastChg is not supported on 7450
                     ESS-1 or 7750 SR-1."

        VARIATION   tmnxCpmProtViolSdpBindTime
            DESCRIPTION
                    "tmnxCpmProtViolSdpBindTime is not supported on 7450
                     ESS-1 or 7750 SR-1."

        VARIATION   tmnxCpmProtViolSdpBindTimeStartd
            DESCRIPTION
                    "tmnxCpmProtViolSdpBindTimeStartd is not supported on 7450
                     ESS-1 or 7750 SR-1."
    ::= { tmnxSROSV10v0 37 }  -- SECURITY

tmnx7750SecurityCapsV10v0    AGENT-CAPABILITIES

    PRODUCT-RELEASE "Alcatel-Lucent SROS"
    STATUS          current
    DESCRIPTION     "Implementation of specific Security capabilities
                     for Alcatel-Lucent SROS 7750 release R10.0"

    SUPPORTS        TIMETRA-SECURITY-MIB
        INCLUDES    {
            tmnxSecurityCpmMacFilterGroup,
            tmnxSecurityCpmProtectGroup,
            tmnxSecurityV7v0Group,
            tmnxSecurityCpmProtNotificationGroup,
            tmnxSecurityCpmProtNotifyV7v0Grp,
            tmnxCpmProtEthCfmPolV8v0Grp,
            tmnxCpmProtPolV8v0Grp,
            tmnxCpmProtPolNotifyV8v0Grp,
            tmnxCpmProtExcdSapIpV9v0Group,
            tmnxCpmProtPolNotifyV9v0Group
        }
    ::= { tmnxSROSSecurityCapsV10v0 1 }  -- 7750 SECURITY

tmnx7450SecurityCapsV10v0    AGENT-CAPABILITIES

    PRODUCT-RELEASE "Alcatel-Lucent SROS"
    STATUS          current
    DESCRIPTION     "Implementation of specific Security capabilities
                     for Alcatel-Lucent SROS 7450 release R10.0"

    SUPPORTS        TIMETRA-SECURITY-MIB
        INCLUDES    {
            tmnxSecurityCpmMacFilterGroup,
            tmnxSecurityCpmProtectGroup,
            tmnxSecurityV7v0Group,
            tmnxSecurityCpmProtNotificationGroup,
            tmnxSecurityCpmProtNotifyV7v0Grp,
            tmnxCpmProtEthCfmPolV8v0Grp,
            tmnxCpmProtPolV8v0Grp,
            tmnxCpmProtPolNotifyV8v0Grp,
            tmnxCpmProtExcdSapIpV9v0Group,
            tmnxCpmProtPolNotifyV9v0Group
        }
    ::= { tmnxSROSSecurityCapsV10v0 2 }  -- 7450 SECURITY

tmnxSprSecurityCapsV10v0    AGENT-CAPABILITIES
    PRODUCT-RELEASE "Alcatel-Lucent SROS"
    STATUS          current
    DESCRIPTION     "Implementation of specific Security capabilities
                     for Alcatel-Lucent SROS SPR release R10.0"

    SUPPORTS        TIMETRA-SECURITY-MIB
        INCLUDES    {
            tmnxSecurityCpmIpFilterV5v0Group
-- EXCLUDE  tmnxCpmProtEthCfmPolV8v0Grp             no DOS Protection on SPR
-- EXCLUDE  tmnxCpmProtPolV8v0Grp                   no DOS Protection on SPR
-- EXCLUDE  tmnxCpmProtPolNotifyV8v0Grp             no DOS Protection on SPR
-- EXCLUDE  tmnxCpmProtExcdSapIpV9v0Group           no DOS Protection on SPR
-- EXCLUDE  tmnxCpmProtPolNotifyV9v0Group           no DOS Protection on SPR
         }

        VARIATION   tCpmIpFilterEntryId
            SYNTAX  TEntryId (1..1536)
            DESCRIPTION
                    "tCpmIpFilterEntryId supports a maximum of only 1536
                     row entries in the tCpmIpFilterTable on SROS SPR
                     systems."

    ::= { tmnxSROSSecurityCapsV10v0 3 }  -- SPR SECURITY

tmnx7710SecurityCapsV10v0    AGENT-CAPABILITIES
    PRODUCT-RELEASE "Alcatel-Lucent SROS"
    STATUS          current
    DESCRIPTION     "Implementation of specific Security capabilities
                     for Alcatel-Lucent SROS 7710 release R10.0"

    SUPPORTS        TIMETRA-SECURITY-MIB
        INCLUDES    {
            tmnxSecurityCpmIpFilterV5v0Group,
            tmnxSecurityCpmIPv6FilterV4v0Group
        }

        VARIATION   tCpmIpFilterEntryAction
            SYNTAX  INTEGER {
                        drop       (1),
                        forward    (2),
                        -- queue   (3),
                        default    (4)
                    }
            DESCRIPTION
                    "The value 'queue (3)' is not supported because
                     CPM-QUEUE is not supported on SROS 7710 systems."

        VARIATION   tCpmIpFilterEntryQueueId
            ACCESS  not-implemented
            DESCRIPTION
                    "tCpmIpFilterEntryQueueId is not implemented because
                     CPM-QUEUE is not supported on SROS 7710 systems."

        VARIATION   tCpmIPv6FilterEntryAction
            SYNTAX  INTEGER {
                        drop       (1),
                        forward    (2),
                        -- queue   (3),
                        default    (4)
                    }
            DESCRIPTION
                   "The value 'queue (3)' is not supported because
                    CPM-QUEUE is not supported on SROS 7710 systems."

        VARIATION tCpmIPv6FilterEntryQueueId
            ACCESS  not-implemented
            DESCRIPTION
                   "tCpmIPv6FilterEntryQueueId is not implemented because
                    CPM-QUEUE is not supported on SROS 7710 systems."

        VARIATION tCpmFilterQueueTable
            ACCESS  not-implemented
            DESCRIPTION
                   "tCpmFilterQueueTable is not implemented because
                    CPM-QUEUE is not supported on SROS 7710 systems."

    ::= { tmnxSROSSecurityCapsV10v0 4 }  -- 7710 SECURITY

tmnx7750cSecurityCapsV10v0    AGENT-CAPABILITIES

    PRODUCT-RELEASE "Alcatel-Lucent SROS"
    STATUS          current
    DESCRIPTION     "Implementation of specific Security capabilities
                     for Alcatel-Lucent SROS 7750c release R10.0"

    SUPPORTS        TIMETRA-SECURITY-MIB
        INCLUDES    {
            tmnxSecurityCpmMacFilterGroup
        }
    ::= { tmnxSROSSecurityCapsV10v0 5 }  -- 7750c SECURITY

--
--  SERVICES CAPABILITIES
--
tmnxSROSServicesCapsV10v0    AGENT-CAPABILITIES
    PRODUCT-RELEASE "Alcatel-Lucent SROS"
    STATUS          current
    DESCRIPTION     "Implementation of Services capabilities
                     for Alcatel-Lucent SROS release R10.0."

    SUPPORTS        TIMETRA-SERV-MIB
        INCLUDES    {
            svcIgmpTrkGroup,
            svcTlsEndPointV7v0Group,
            svcTlsMacV7v0Group,
            tmnxApipeV3v0Group,
            tmnxArpHostBgpGroup,
            tmnxArpHostNotifyGroup,
            tmnxArpHostV10v0Group,
            tmnxCustV8v0Group,
            tmnxCustV9v0Group,
            tmnxSvcDhcpV8v0Group,
            tmnxSvcDhcpV9v0Group,
            tmnxSvcDhcpV10v0Group,
            tmnxSvcEndPointV6v0Group,
            tmnxSvcEpipeV6v0Group,
            tmnxSvcEthCfmGroup,
            tmnxSvcIesIfV6v0Group,
            tmnxSvcIesIfV7v0Group,
            tmnxSvcIesIfV8v0Group,
            tmnxSvcIesIfV10v0Group,
            tmnxSvcIesIfNHV10v0Group,
            tmnxSvcIfDHCP6V6v0Group,
            tmnxSvcInterAsV8v0Group,
            tmnxSvcIpipeV8v0Group,
            tmnxSvcMCEPNotifyGroup,
            tmnxSvcMSPwPeV9v0Group,
            tmnxSvcMrpPolicyV8v0Group,
            tmnxSvcMvrpV8v0Group,
            tmnxSvcNotifyObjsV7v0Group,
            tmnxSvcNotifyV7v0Group,
            tmnxSvcNotifyV8v0Group,
            tmnxSvcNotifyV9v0Group,
            tmnxSvcOperGrpV9v0Group,
            tmnxSvcPEV6v0Group,
            tmnxSvcPbbMacV7v0Group,
            tmnxSvcPwV8v0Group,
            tmnxSvcRdntV6v0Group,
            tmnxSvcRoutedCOV9v0Group,
            tmnxSvcRoutedCOV10v0Group,
            tmnxSvcRoutedVplsV8v0Group,
            tmnxSvcSiteV8v0Group,
            tmnxSvcTlsBackbone6v1Group,
            tmnxSvcTlsBgpV8v0Group,
            tmnxSvcTlsEgrV6v0Group,
            tmnxSvcTlsFdbV7v0Group,
            tmnxSvcTlsMFibV6v0Group,
            tmnxSvcTlsMstiV6v0Group,
            tmnxSvcTlsPipV7v0Group,
            tmnxSvcTlsPipV8v0Group,
            tmnxSvcTlsShgV6v0Group,
            tmnxSvcTlsV6v0Group,
            tmnxSvcTlsV7v0Group,
            tmnxSvcV6v0Group,
            tmnxSvcV7v0Group,
            tmnxSvcV8v0Group,
            tmnxSvcV9v0Group,
            tmnxSvcMacReNotifyGroup,
            tmnxSvcSpbGroup,
            tmnxSvcVllBgpGroup,
            tmnxSvcP2mpGroup,
            tmnxSvcV10v0Group,
            tmnxSvcNotifyV10v0Group,
            tmnxSvcV9v0R4Group
-- EXCLUDE  tmnxSvcApipeInfoV9v0Group
-- EXCLUDE  tmnxSvcBsxV8v0Group
-- EXCLUDE  tmnxSvcDhcpBgpV7v0Group
        }

        VARIATION   svcType
            SYNTAX  INTEGER {
                        epipe   (1),   -- Ethernet pipe
                        p3pipe  (2),   -- POS pipe
                        tls     (3),   -- Virtual private LAN service
                        vprn    (4),   -- Virtual private routed network
                        ies     (5),   -- Internet enhanced service
                        mirror  (6),   -- Mirror service
                        apipe   (7),   -- ATM pipe service
                        fpipe   (8),   -- FR pipe service
                        ipipe   (9),   -- IP interworking pipe service
                        -- cpipe(10)   Circuit Emulation pipe service
                        --             no CPIPE on SROS 7750 or 7450
                        intTls  (11) -- Internal VPLS service
                    }
            DESCRIPTION
                    "The enumeration 'cpipe (10)' is not supported on
                     SROS 7750 or 7450 platforms."

        VARIATION   svcVllType
            SYNTAX  INTEGER {
                        undef     (1),
                        atmSdu    (6),
                        atmCell   (7),
                        atmVcc    (8),
                        atmVpc    (9),
                        frDlci    (10),
                        satopE1   (12),
                        satopT1   (13),
                        -- satopE3   (14),
                        -- satopT3   (15),
                        cesopsn   (16),
                        cesopsnCas(17)
                    }
            DESCRIPTION
                    "The enumerations
                        - satopE3 (14),
                        - satopT3 (15),
                        are not supported on the SROS, as they are not
                        implemented."

        VARIATION   svcApipeInterworking
            SYNTAX  INTEGER {
                        none             (1),
                        frf-5            (2)
                        -- frf-8-2-translate(3)
                    }
            DESCRIPTION
                    "The enumeration 'frf-8-2-translate (3)' is not supported."

        VARIATION   iesIfType
            SYNTAX  INTEGER {
                        service       (1),
                        subscriber    (2),
                        group         (3),
                        redundant     (4),
                        -- cem        (5),
                        ipsec         (6),
                        ipMirror      (7),
                        video         (8),
                        -- reserved9  (9),
                        aarp          (10)
                    }
            DESCRIPTION
                    "The values 'cem(5)' and 'reserved9(9)' are not supported
                     on SROS systems."

        VARIATION   tlsEgrMcGrpQinqFixedTagPosition
            ACCESS  read-only
            DESCRIPTION
                    "tlsEgrMcGrpQinqFixedTagPosition is supported as
                     read-only."

        VARIATION   iesIfDefaultPrimaryDnsIPv6Addr
            ACCESS  read-create
            DESCRIPTION
                    "The object iesIfDefaultPrimaryDnsIPv6Addr is not supported.

                     It is not allowed to set it to a value other than its
                     default value."

        VARIATION   iesIfDefaultSecondaryDnsIPv6Addr
            ACCESS  read-create
            DESCRIPTION
                    "The object iesIfDefaultSecondaryDnsIPv6Addr is not
                     supported.

                     It is not allowed to set it to a value other than its
                     default value."

        VARIATION   svcPEDiscPolServerRowStatus
            SYNTAX  INTEGER {
                        active      (1),
                        createAndGo (4),
                        destroy     (6)
                     }
            DESCRIPTION
                    "svcPEDiscPolServerRowStatus supports only the values
                    'active (1)', 'createAndGo (4)' and 'destroy (6)'."

        VARIATION   svcPEDiscoveryPolicyRowStatus
            SYNTAX  INTEGER {
                        active      (1),
                        createAndGo (4),
                        destroy     (6)
                     }
            DESCRIPTION
                    "svcPEDiscoveryPolicyRowStatus supports only the values
                    'active (1)', 'createAndGo (4)' and 'destroy (6)'."

        VARIATION   svcMrpPolicyParamsRowStatus
            SYNTAX  INTEGER {
                        active      (1),
                        createAndGo (4),
                        destroy     (6)
                     }
            DESCRIPTION
                    "svcMrpPolicyParamsRowStatus supports only the values
                    'active (1)', 'createAndGo (4)' and 'destroy (6)'."

    ::= { tmnxSROSV10v0 38 }  -- SERVICES

tmnx7750ServicesCapsV10v0    AGENT-CAPABILITIES
    PRODUCT-RELEASE "Alcatel-Lucent SROS"
    STATUS          current
    DESCRIPTION     "Implementation of specific Services capabilities
                     for Alcatel-Lucent SROS 7750 release R10.0."

    SUPPORTS        TIMETRA-SERV-MIB
        INCLUDES    {
            tmnxSvcApipeInfoV9v0Group,
            tmnxSvcBsxV8v0Group,
            tmnxSvcDhcpBgpV7v0Group,
            tmnxSvcV6v0Group
        }

        VARIATION   svcType
            SYNTAX  INTEGER {
                        epipe   (1),   -- Ethernet pipe
                        p3pipe  (2),   -- POS pipe
                        tls     (3),   -- Virtual private LAN service
                        vprn    (4),   -- Virtual private routed network
                        ies     (5),   -- Internet enhanced service
                        mirror  (6),   -- Mirror service
                        apipe   (7),   -- ATM pipe service
                        fpipe   (8),   -- FR pipe service
                        ipipe   (9)    -- IP interworking pipe service
                        cpipe  (10)    -- Circuit Emulation pipe service
                    }
            DESCRIPTION
                    "The enumeration 'cpipe (10)' is not supported on
                     SROS 7750 or 7450 platforms."

        VARIATION   svcInterASMvpn
            ACCESS  not-implemented
            DESCRIPTION
                    "The object svcInterASMvpn is not implemented."

    ::= { tmnxSROSServicesCapsV10v0 1 }  -- 7750 SERVICES

tmnx7450ServicesCapsV10v0    AGENT-CAPABILITIES
    PRODUCT-RELEASE "Alcatel-Lucent SROS"
    STATUS          current
    DESCRIPTION     "Implementation of specific Services capabilities
                     for Alcatel-Lucent SROS 7450 release R10.0."

    SUPPORTS        TIMETRA-SERV-MIB
        INCLUDES    {
            tmnxSvcV6v0Group,
            tmnxSvcTlsV6v0Group,
            tmnxSvcIesIfV6v0Group,
            tmnxSvcBsxV8v0Group,
            tmnxSvcDhcpBgpV7v0Group
        }

        VARIATION   svcType
            SYNTAX  INTEGER {
                        epipe   (1),   -- Ethernet pipe
                        p3pipe  (2),   -- POS pipe
                        tls     (3),   -- Virtual private LAN service
                        vprn    (4),   -- Virtual private routed network
                        ies     (5),   -- Internet enhanced service
                        mirror  (6),   -- Mirror service
                        apipe   (7),   -- ATM pipe service
                        fpipe   (8),   -- FR pipe service
                        ipipe   (9)    -- IP interworking pipe service
                    -- cpipe   (10)    -  Circuit Emulation pipe service
                    --                    (no CPIPE on SROS 7450)
                    }
            DESCRIPTION
                    "The enumeration 'cpipe (10)' is not supported on
                     SROS 7750 or 7450 platforms."

        VARIATION   svcVllType
            SYNTAX  INTEGER {
                        undef     (1),
                        atmSdu    (6),
                        atmCell   (7),
                        atmVcc    (8),
                        atmVpc    (9),
                        frDlci    (10)
                    -- satopE1    (12)
                    -- satopT1    (13)
                    -- satopE3    (14)
                    -- satopT3    (15)
                    -- cesopsn    (16)
                        -- cesopsnCas(17)
                    }
            DESCRIPTION
                    "The values
                        - satopE3     (14),
                        - satopT3     (15),
                        are not supported on the 7450, as they are not
                        implemented.
                     The values
                        - 'satopE1    (12)',
                        - 'satopT1    (13)',
                        - 'cesopsn    (16)',
                        - 'cesopsnCas (17)'
                     are not supported on a 7450 system, as CEM is
                     not implemented."

        VARIATION   iesIfType
            SYNTAX  INTEGER {
                        service       (1),
                        subscriber    (2),
                        group         (3),
                        redundant     (4),
                    -- cem           (5)
                    -- ipsec         (6)
                       ipMirror      (7),
                       video         (8),
                    -- reserved9     (9)
                       aarp         (10)
                    }
            DESCRIPTION
                    "The values
                        - 'cem        (5)',
                        - 'ipsec      (6)'
                     are not supported on 7450 systems."

        VARIATION   svcInterASMvpn
            ACCESS  not-implemented
            DESCRIPTION
                    "The object svcInterASMvpn is not implemented."

    ::= { tmnxSROSServicesCapsV10v0 2 }  -- 7450 SERVICES

tmnx7710ServicesCapsV10v0    AGENT-CAPABILITIES
    PRODUCT-RELEASE "Alcatel-Lucent SROS"
    STATUS          current
    DESCRIPTION     "Implementation of specific Services capabilities
                     for Alcatel-Lucent SROS 7710 release R10.0."

    SUPPORTS        TIMETRA-SERV-MIB
        INCLUDES    {
            tmnxSvcApipeInfoV9v0Group,
            tmnxSvcIesIfV6v0Group,
            tmnxSvcPbbMacV7v0Group,
            tmnxSvcV8v0Group
        }

        VARIATION   iesIfType
            SYNTAX  INTEGER {
                        service       (1),
                        subscriber    (2),
                        group         (3),
                        redundant     (4),
                    -- cem           (5)
                    -- ipsec         (6)
                        ipMirror      (7)
                    }
            DESCRIPTION
                "The values
                    - 'cem        (5)'
                    - 'ipsec      (6)'
                 are not supported on SROS 7710 systems."

        VARIATION   svcTlsMacNotifInterval
            ACCESS  not-implemented
            DESCRIPTION
                "svcTlsMacNotifInterval is not implemented on SROS
                 7710 systems."

        VARIATION   svcTlsMacNotifCount
            ACCESS  not-implemented
            DESCRIPTION
                "svcTlsMacNotifCount is not implemented on SROS
                 7710 systems."

        VARIATION   svcTlsMacNotifAdminState
            ACCESS  not-implemented
            DESCRIPTION
                "svcTlsMacNotifAdminState is not implemented on SROS
                 7710 systems."

        VARIATION   svcMacNotifInterval
            ACCESS  not-implemented
            DESCRIPTION
                "svcMacNotifInterval is not implemented on SROS
                 7710 systems."

        VARIATION   svcMacNotifCount
            ACCESS  not-implemented
            DESCRIPTION
                "svcMacNotifCount is not implemented on SROS
                 7710 systems."

        VARIATION   svcTlsPerSvcHashing
            ACCESS  not-implemented
            DESCRIPTION
                "svcTlsPerSvcHashing is not implemented on SROS
                 7710 systems."

        VARIATION   svcEpipePerSvcHashing
            ACCESS  not-implemented
            DESCRIPTION
                "svcEpipePerSvcHashing is not implemented on SROS
                 7710 systems."

        VARIATION   svcTlsBackboneForceQTagFwd
            ACCESS  not-implemented
            DESCRIPTION
                "svcTlsBackboneForceQTagFwd is not implemented on SROS
                 7710 systems."

        VARIATION   svcEpipeBackboneForceQTagFwd
            ACCESS  not-implemented
            DESCRIPTION
                "svcEpipeBackboneForceQTagFwd is not implemented on SROS
                 7710 systems."

        VARIATION   svcInterASMvpn
            ACCESS  not-implemented
            DESCRIPTION
                    "The object svcInterASMvpn is not implemented."

    ::= { tmnxSROSServicesCapsV10v0 3 }  -- 7710 SERVICES

--
--  SNMP CAPABILITIES
--
tmnxSROSSnmpCapsV10v0    AGENT-CAPABILITIES
    PRODUCT-RELEASE "Alcatel-Lucent SROS"
    STATUS          current
    DESCRIPTION     "Implementation of SNMP capabilities
                     for Alcatel-Lucent SROS release R10.0"

    SUPPORTS        SNMPv2-MIB
        INCLUDES    {
            snmpGroup,
            snmpCommunityGroup,
            systemGroup,
            snmpBasicNotificationsGroup,
            snmpWarmStartNotificationGroup,
            snmpNotificationGroup,
            snmpObsoleteGroup
-- EXCLUDE  snmpSetGroup
        }

        VARIATION   sysName
            SYNTAX  DisplayString (SIZE(0..32))
            DESCRIPTION
                    "The maximum length supported for the system name is 32
                    characters.  Setting sysName to the empty string, ''H,
                    resets sysName to the TiMOS default value."

        VARIATION   sysContact
            SYNTAX  DisplayString (SIZE(0..80))
            DESCRIPTION
                    "The maximum length supported for the system contact is
                    80 characters."

        VARIATION   sysLocation
            SYNTAX  DisplayString (SIZE(0..80))
            DESCRIPTION
                    "The maximum length supported for the system location is
                    80 characters."

        VARIATION   sysORLastChange
            ACCESS  not-implemented
            DESCRIPTION
                    "The sysORLastChange is not supported."

        VARIATION   sysORTable
            ACCESS  not-implemented
            DESCRIPTION
                    "The sysORTable is not supported."

        VARIATION   coldStart
            DESCRIPTION
                    "The coldStart notification is generated on all system
                    reboots - not only for power cycle reboots."

        VARIATION   warmStart
            DESCRIPTION
                    "The warmStart notification is generated by the new active
                    CPM following a CPM switchover.  This notification has
                    been supported starting with the SROS 2.1 release.

                    When the standby CPM card takes over following a failure
                    or reboot of the active CPM card, tmnxRedPrimaryCPMFail,
                    sbiBootConfig and sbiBootSnmpd events from the
                    TIMETRA-SYSTEM-MIB are generated to indicate the
                    secondary CPM has successfully taken control of the
                    system."

        VARIATION   snmpOutPkts
            DESCRIPTION
                    "This object was defined in RFC1213 for SNMPv1 agents
                    but it was made obsolete in SNMPv2-MIB.  However,
                    many customers and NMS developers find this counter
                    useful so this agent continues to support it."

        VARIATION   snmpInTooBigs
            DESCRIPTION
                    "This object was defined in RFC1213 for SNMPv1 agents
                    but it was made obsolete in SNMPv2-MIB.  However,
                    many customers and NMS developers find this counter
                    useful so this agent continues to support it."

        VARIATION   snmpInNoSuchNames
            DESCRIPTION
                    "This object was defined in RFC1213 for SNMPv1 agents
                    but it was made obsolete in SNMPv2-MIB.  However,
                    many customers and NMS developers find this counter
                    useful so this agent continues to support it."

        VARIATION   snmpInBadValues
            DESCRIPTION
                    "This object was defined in RFC1213 for SNMPv1 agents
                    but it was made obsolete in SNMPv2-MIB.  However,
                    many customers and NMS developers find this counter
                    useful so this agent continues to support it."

        VARIATION   snmpInReadOnlys
            DESCRIPTION
                    "This object was defined in RFC1213 for SNMPv1 agents
                    but it was made obsolete in SNMPv2-MIB.  However,
                    many customers and NMS developers find this counter
                    useful so this agent continues to support it."

        VARIATION   snmpInGenErrs
            DESCRIPTION
                    "This object was defined in RFC1213 for SNMPv1 agents
                    but it was made obsolete in SNMPv2-MIB.  However,
                    many customers and NMS developers find this counter
                    useful so this agent continues to support it."

        VARIATION   snmpInTotalReqVars
            DESCRIPTION
                    "This object was defined in RFC1213 for SNMPv1 agents
                    but it was made obsolete in SNMPv2-MIB.  However,
                    many customers and NMS developers find this counter
                    useful so this agent continues to support it."

        VARIATION   snmpInTotalSetVars
            DESCRIPTION
                    "This object was defined in RFC1213 for SNMPv1 agents
                    but it was made obsolete in SNMPv2-MIB.  However,
                    many customers and NMS developers find this counter
                    useful so this agent continues to support it."

        VARIATION   snmpInGetRequests
            DESCRIPTION
                    "This object was defined in RFC1213 for SNMPv1 agents
                    but it was made obsolete in SNMPv2-MIB.  However,
                    many customers and NMS developers find this counter
                    useful so this agent continues to support it."

        VARIATION   snmpInGetNexts
            DESCRIPTION
                    "This object was defined in RFC1213 for SNMPv1 agents
                    but it was made obsolete in SNMPv2-MIB.  However,
                    many customers and NMS developers find this counter
                    useful so this agent continues to support it."

        VARIATION   snmpInSetRequests
            DESCRIPTION
                    "This object was defined in RFC1213 for SNMPv1 agents
                    but it was made obsolete in SNMPv2-MIB.  However,
                    many customers and NMS developers find this counter
                    useful so this agent continues to support it."

        VARIATION   snmpInGetResponses
            DESCRIPTION
                    "This object was defined in RFC1213 for SNMPv1 agents
                    but it was made obsolete in SNMPv2-MIB.  However,
                    many customers and NMS developers find this counter
                    useful so this agent continues to support it."

        VARIATION   snmpInTraps
            DESCRIPTION
                    "This object was defined in RFC1213 for SNMPv1 agents
                    but it was made obsolete in SNMPv2-MIB.  However,
                    many customers and NMS developers find this counter
                    useful so this agent continues to support it."

        VARIATION   snmpOutTooBigs
            DESCRIPTION
                    "This object was defined in RFC1213 for SNMPv1 agents
                    but it was made obsolete in SNMPv2-MIB.  However,
                    many customers and NMS developers find this counter
                    useful so this agent continues to support it."

        VARIATION   snmpOutNoSuchNames
            DESCRIPTION
                    "This object was defined in RFC1213 for SNMPv1 agents
                    but it was made obsolete in SNMPv2-MIB.  However,
                    many customers and NMS developers find this counter
                    useful so this agent continues to support it."

        VARIATION   snmpOutBadValues
            DESCRIPTION
                    "This object was defined in RFC1213 for SNMPv1 agents
                    but it was made obsolete in SNMPv2-MIB.  However,
                    many customers and NMS developers find this counter
                    useful so this agent continues to support it."

        VARIATION   snmpOutGenErrs
            DESCRIPTION
                    "This object was defined in RFC1213 for SNMPv1 agents
                    but it was made obsolete in SNMPv2-MIB.  However,
                    many customers and NMS developers find this counter
                    useful so this agent continues to support it."

        VARIATION   snmpOutGetRequests
            DESCRIPTION
                    "This object was defined in RFC1213 for SNMPv1 agents
                    but it was made obsolete in SNMPv2-MIB.  However,
                    many customers and NMS developers find this counter
                    useful so this agent continues to support it."

        VARIATION   snmpOutGetNexts
            DESCRIPTION
                    "This object was defined in RFC1213 for SNMPv1 agents
                    but it was made obsolete in SNMPv2-MIB.  However,
                    many customers and NMS developers find this counter
                    useful so this agent continues to support it."

        VARIATION   snmpOutSetRequests
            DESCRIPTION
                    "This object was defined in RFC1213 for SNMPv1 agents
                    but it was made obsolete in SNMPv2-MIB.  However,
                    many customers and NMS developers find this counter
                    useful so this agent continues to support it."

        VARIATION   snmpOutGetResponses
            DESCRIPTION
                    "This object was defined in RFC1213 for SNMPv1 agents
                    but it was made obsolete in SNMPv2-MIB.  However,
                    many customers and NMS developers find this counter
                    useful so this agent continues to support it."

        VARIATION   snmpOutTraps
            DESCRIPTION
                    "This object was defined in RFC1213 for SNMPv1 agents
                    but it was made obsolete in SNMPv2-MIB.  However,
                    many customers and NMS developers find this counter
                    useful so this agent continues to support it."


    SUPPORTS        SNMP-COMMUNITY-MIB
        INCLUDES    {
            snmpCommunityTableGroup
        }

        VARIATION   snmpCommunityContextEngineID
            ACCESS  read-only
            DESCRIPTION
                    "The snmpCommunityContextEngineID is implemented as
                    read-only because only one SNMP Engine ID is supported.
                    The engine ID may change when a redundancy failover
                    from active to standby CPM happens."

    SUPPORTS        SNMP-FRAMEWORK-MIB
        INCLUDES    {
            snmpEngineGroup
        }

    SUPPORTS        SNMP-MPD-MIB
        INCLUDES    {
            snmpMPDGroup
        }

    SUPPORTS        SNMP-NOTIFICATION-MIB
        INCLUDES    {
            snmpNotifyGroup,
            snmpNotifyFilterGroup
        }

        VARIATION   snmpNotifyRowStatus
            DESCRIPTION
                    "The only values allowed for the snmpNotifyName index is
                    the ASCII numerical value of the TiMOS event log ID that
                    the notification group is associated with.  Event log
                    IDs have a range of [1..100].  Leading zero, '0',
                    characters are not allowed."

        VARIATION   snmpNotifyType
            SYNTAX  INTEGER {
                        trap(1)
                    }
            DESCRIPTION
                    "The only value allowed for the snmpNotifyType object is
                    'trap'.  The TiMOS agent does not support 'inform'."

    SUPPORTS        SNMP-TARGET-MIB
        INCLUDES    {
            snmpTargetBasicGroup
-- EXCLUDE  snmpTargetResponseGroup
-- EXCLUDE  snmpTargetCommandResponderGroup,
        }

        VARIATION   snmpTargetParamsSecurityName
            SYNTAX  DisplayString (SIZE(0..32))
            DESCRIPTION
                    "The maximum length supported for the taraget parameters
                    security name is 32 characters."

    SUPPORTS        SNMP-USER-BASED-SM-MIB
        INCLUDES    {
            usmMIBBasicGroup
        }

        VARIATION   usmUserStorageType
            SYNTAX  INTEGER {
                        nonVolatile (3)
                    }
            DESCRIPTION
                    "Only the StorageType TC value 'nonVolatile (3)' is
                    supported for usmUserStorageType."

    SUPPORTS        SNMP-VIEW-BASED-ACM-MIB
        INCLUDES    {
            vacmBasicGroup
        }

    ::= { tmnxSROSV10v0 39 }  -- SNMP

--
--  SONET CAPABILITIES
--
tmnxSROSSonetCapsV10v0    AGENT-CAPABILITIES
    PRODUCT-RELEASE "Alcatel-Lucent SROS"
    STATUS          current
    DESCRIPTION     "Implementation of SONET Interface Types capabilities
                     for Alcatel-Lucent SROS release R10.0"

    SUPPORTS        SONET-MIB
        INCLUDES    {
            sonetMediumStuff2,
            sonetSectionStuff2,
            sonetLineStuff2,
            sonetFarEndLineStuff2,
            sonetPathStuff2,
            sonetFarEndPathStuff2,
            sonetVTStuff2
        }

        VARIATION   sonetMediumType
            ACCESS  read-only
            DESCRIPTION
                    "The sonetMediumTable is implemented as read-only."

        VARIATION   sonetMediumLineCoding
            ACCESS  read-only
            DESCRIPTION
                    "The sonetMediumTable is implemented as read-only."

        VARIATION   sonetMediumLineType
            ACCESS  read-only
            DESCRIPTION
                    "The sonetMediumTable is implemented as read-only."

        VARIATION   sonetMediumCircuitIdentifier
            ACCESS  read-only
            DESCRIPTION
                    "The sonetMediumTable is implemented as read-only."

        VARIATION   sonetMediumLoopbackConfig
            ACCESS  read-only
            DESCRIPTION
                    "The sonetMediumTable is implemented as read-only."

        VARIATION   sonetSESthresholdSet
            ACCESS  read-only
            DESCRIPTION
                    "The sonetSESthresholdSet is implemented as read-only."

        VARIATION   sonetPathCurrentWidth
            ACCESS  read-only
            DESCRIPTION
                    "The sonetPathCurrentTable is implemented as read-only."

        VARIATION   sonetVTCurrentWidth
            ACCESS  read-only
            DESCRIPTION
                    "The sonetVTCurrentWidth is implemented as read-only."

    ::= { tmnxSROSV10v0 40 }  -- SONET

tmnx7950SonetCapsV10v0    AGENT-CAPABILITIES
    PRODUCT-RELEASE "Alcatel-Lucent SROS"
    STATUS          current
    DESCRIPTION     "Implementation of SONET Interface Types capabilities
                     for Alcatel-Lucent 7950 release R10.0"

--  SUPPORTS        SONET-MIB
--    INCLUDES    {
--    }

    ::= { tmnxSROSSonetCapsV10v0   1 }  -- 7950 SONET

--
--  SYSTEM CAPABILITIES
--
tmnxSROSSystemCapsV10v0    AGENT-CAPABILITIES
    PRODUCT-RELEASE "Alcatel-Lucent SROS"
    STATUS          current
    DESCRIPTION     "Implementation of System capabilities
                     for Alcatel-Lucent SROS release R10.0"

    SUPPORTS        TIMETRA-SYSTEM-MIB
        INCLUDES    {
            tmnxPersistenceV9v0Group,
            tmnxPersistenceV9v0Group,
            tmnxSysBofV6v0Group,
            tmnxSysConfigV8v0Group,
            tmnxSysEthInfoGroup,
            tmnxSysGeneralV3v0Group,
            tmnxSysGeneralV7v0Group,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNotificationV6v0Group,
            tmnxSysNotificationV9v0Group,
            tmnxSysNotificationV10v0Group,
            tmnxSysRadiusServerV5v0Group,
            tmnxSysRollbackV9v0Group,
            tmnxSysTacPlusServerV5v0Group,
            tmnxSysTimeV4v0Group,
            tmnxSystemCpuMonitorGroup,
            tmnxSysCertGroup,
            tmnxSysBootedBofGroup,
            tmnxSysRollbackRescueGroup,
            tmnxSysNotifyObjsV10v0Group,
            tmnxSysNotificationRBGroup,
            tmnxSysNotifyObjsGenGroup
        }

        VARIATION   sntpTimeDiffExceedsThreshold
            ACCESS  not-implemented
            DESCRIPTION
                    "sntpTimeDiffExceedsThreshold notification is not
                     implemented."

        VARIATION  stiDateAndTime
            DESCRIPTION
                    "The maximum date and time (in UTC) supported for
                     the system is 2038/01/19 03:14:07"

    ::= { tmnxSROSV10v0 41 }  -- SYSTEM

tmnx7950SystemCapsV10v0    AGENT-CAPABILITIES
    PRODUCT-RELEASE "Alcatel-Lucent SROS"
    STATUS          current
    DESCRIPTION     "Implementation of System capabilities
                     for Alcatel-Lucent 7950 release R10.0"

    SUPPORTS        TIMETRA-SYSTEM-MIB
        INCLUDES    {
            tmnxPersistenceV9v0Group,
            tmnxPersistenceV9v0Group,
            tmnxSysBofV6v0Group,
            tmnxSysConfigV8v0Group,
-- EXCLUDE  tmnxSysEthInfoGroup
            tmnxSysGeneralV3v0Group,
            tmnxSysGeneralV7v0Group,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNotificationV6v0Group,
            tmnxSysNotificationV9v0Group,
            tmnxSysNotificationV10v0Group,
            tmnxSysRadiusServerV5v0Group,
            tmnxSysRollbackV9v0Group,
            tmnxSysTacPlusServerV5v0Group,
            tmnxSysTimeV4v0Group,
            tmnxSystemCpuMonitorGroup,
            tmnxSysCertGroup,
            tmnxSysBootedBofGroup,
            tmnxSysRollbackRescueGroup,
            tmnxSysNotifyObjsV10v0Group,
            tmnxSysNotificationRBGroup
        }

    ::= { tmnxSROSSystemCapsV10v0   1 }  -- 7950 SYSTEM

--
--  VRRP CAPABILITIES
--
tmnxSROSVrrpCapsV10v0    AGENT-CAPABILITIES
    PRODUCT-RELEASE "Alcatel-Lucent SROS"
    STATUS          current
    DESCRIPTION     "Implementation of VRRP protocol capabilities
                     for Alcatel-Lucent SROS release R10.0"

    SUPPORTS        VRRP-MIB
        INCLUDES    {
            vrrpOperGroup,
            vrrpStatsGroup,
            vrrpTrapGroup,
            vrrpNotificationGroup
        }

        VARIATION   vrrpOperPrimaryIpAddr
            ACCESS  read-only
            DESCRIPTION
                    "vrrpOperPrimaryIpAddr is implemented as read-only."

        VARIATION   vrrpOperAdvertisementInterval
            SYNTAX  Integer32 (0..255)
            DESCRIPTION
                    "The range for vrrpOperAdvertisementInterval is changed
                    from (1..255) to (0..255) to support the interval time
                    to be less than 1 sec. To set milliseconds time interval
                    the object tmnxVrrpOperAdvIntervalMilSec should be
                    specified.  To get the total interval time, add the
                    value for vrrpOperAdvertisementInterval in seconds and
                    tmnxVrrpOperAdvIntervalMilSec in milliseconds."

        VARIATION   vrrpOperAuthType
            ACCESS  read-only
            DESCRIPTION
                    "vrrpOperAuthType is implemented as read-only."

    SUPPORTS        TIMETRA-VRRP-MIB
        INCLUDES    {
            tVrrpHostUnreachableV7v0Group,
            tVrrpMasterV7v0Group,
            tVrrpNotificationV7v0Group,
            tVrrpOpV7v0Group,
            tVrrpRouteUnknownV7v0Group,
            tVrrpRouterAdverV7v0Group,
            tVrrpStatV7v0Group,
            tmnxVrrpNotificationV6v1Group,
            tmnxVrrpOperV6v1Group,
            tmnxVrrpPolicyV5v0Group,
            tmnxVrrpPriorityEventsGroup,
            tmnxVrrpRouteMasterGroup,
            tVrrpBfdV9v0Group,
            tmnxVrrpStatsGroup
        }

    SUPPORTS TIMETRA-VRRP-V3-MIB
        INCLUDES    {
            vrrpOperationsGroup,
            vrrpStatisticsGroup,
            vrrpTrapInfoGroup,
            vrrpNotificationsGroup,
            vrrpNotifyObjsGroup
        }

        VARIATION   vrrpOperationsPrimaryIpAddr
            ACCESS  read-only
            DESCRIPTION
                    "vrrpOperationsPrimaryIpAddr  is implemented as read-only."

        VARIATION   vrrpOperationsAcceptMode
            ACCESS  not-implemented
            DESCRIPTION
                    "vrrpOperationsAcceptMode is not supported. Instead
                     tVrrpOpPingReply, tVrrpOpTelnetReply and
                     tVrrpOpTracerouteReply should be used."

        VARIATION   vrrpAssociatedIpAddrRowStatus
            SYNTAX  INTEGER {
                        active        (1),
                        -- notReady      (2),
                        -- notInService(3),
                        createAndGo   (4),
                        -- createAndWait (5),
                        destroy       (6)
                    }
            DESCRIPTION
                    "vrrpAssociatedIpAddrRowStatus supports only 'active(1)',
                     'createAndGo(4)' and 'destroy(6)'.
                     i.e. vrrpAssociatedIpAddr cannot be brought down
                     administratively."

        VARIATION   vrrpAssociatedStorageType
            SYNTAX  INTEGER {
                        nonVolatile    (3)
                    }
            DESCRIPTION
                   "vrrpAssociatedStorageType supports only 'nonVolatile'
                    storage type."

        VARIATION   vrrpTrapProtoError
            ACCESS  not-implemented
            DESCRIPTION
                    "vrrpTrapProtoError notification is not supported."

        VARIATION   vrrpOperationsAdvInterval
            SYNTAX  TimeInterval (10..4095)
            DESCRIPTION
                    "The range for vrrpOperationsAdvInterval is changed
                     from (1..4095) to (10..4095) as minimum time-interval
                     supported on the system is 10 centiseconds."

    ::= { tmnxSROSV10v0 42 }  -- VRRP

--
--  VIRTUAL ROUTER CAPABILITIES
--
tmnxSROSVRtrCapsV10v0    AGENT-CAPABILITIES
    PRODUCT-RELEASE "Alcatel-Lucent SROS"
    STATUS          current
    DESCRIPTION     "Implementation of Virtual Router capabilities
                     for Alcatel-Lucent SROS release R10.0"

    SUPPORTS        TIMETRA-VRTR-MIB
        INCLUDES    {
            tmnxDscpAppV6v0Group,
            tmnxVRtrBfdV7v0Group,
            tmnxVRtrBfdV9v0Group,
            tmnxVRtrFibStatsV8v0Group,
            tmnxVRtrGlobalV6v0Group,
            tmnxVRtrIPv6IfV4v0Group,
            tmnxVRtrIPv6IpV5v0Group,
            tmnxVRtrIPv6V4v0Group,
            tmnxVRtrIfCpmProtectGroup,
            tmnxVRtrIfDHCP6V9v0Group,
            tmnxVRtrIfDHCP6V10v0Group,
            tmnxVRtrIfDHCPRelayV6v1Group,
            tmnxVRtrIfDHCPRelayV9v0Group,
            tmnxVRtrIfDhcpServerGroup,
            tmnxVRtrIfIpReasV9v0Group,
            tmnxVRtrIfIpcpV6v0Group,        -- ??? IPCP on 7450??? with VPRNs?
            tmnxVRtrIfStatsV9v0Group,
            tmnxVRtrIfSubscrAuthV3v0Group,
            tmnxVRtrInetAllCidrRouteV7v0Group,
            tmnxVRtrInetStaticRouteV7v0Group,
            tmnxVRtrIpV7v0Group,
            tmnxVRtrMvpnPmsiV8v0Group,
            tmnxVRtrNetDomainGroup,
            tmnxVRtrNotificationV8v0Group,
            tmnxVRtrQPPBV9v0R4Group,
            tmnxVRtrStaticRteCPEChkV6v0Group,
            tmnxVRtrTunIntV8v0Group,
            tmnxVRtrV6v1Group,
            tmnxVRtrV9v0Group,
            tmnxVRtrV10v0Group,
            tmnxVRtrPolicyGroup,
            tmnxVRtrNatRedGroup,
            tmnxVRtrMSPwV9v0Group,
            tmnxVRtruRPFV7v0Group,
-- EXCLUDE  tmnxVRtrIPv6MgtIfV7v0Group   -  ??? Still only on 7450 ???
            tmnxVRtrMvpnSrcRedV9v0R4Group,
            tmnxVRtrStatV9v0Group,
            tmnxVRtruRPFV10v0Group,
            tmnxVRtrIpPoolGroup,
            tmnxVRtrGlobalV10v0Group,
            tmnxVRtrQosQGrplV10v0Group,
            tmnxVRtrStatV10v0Group,
            tmnxVRtrIfV10v0Group,
            tmnxVRtrNotificationV10v0Group,
            tmnxVRtrGrtLocalMgmtV10v0Group
        }

        VARIATION   vRtrNextVRtrID
            ACCESS  read-only
            DESCRIPTION
                    "vRtrNextVRtrID is implemented as read-only."

        VARIATION   vRtrRouteThresholdSoakTime
            ACCESS  read-only
            DESCRIPTION
                    "vRtrRouteThresholdSoakTime is implemented as read-only."

        VARIATION   vRtrIPv6RouteThresholdSoakTime
            ACCESS  read-only
            DESCRIPTION
                    "vRtrIPv6RouteThresholdSoakTime is implemented as
                     read-only."

        VARIATION   vRtrIfAlias
            ACCESS  read-only
            DESCRIPTION
                    "vRtrIfAlias is implemented as read-only."

        VARIATION   vRtrIpCidrRoutePreference
            ACCESS  read-only
            DESCRIPTION
                    "vRtrIpCidrRoutePreference is implemented as read-only."

        VARIATION   vRtrType
            ACCESS  read-only
            DESCRIPTION
                    "vRtrType is implemented as read-only."

        VARIATION   vRtrInetStaticRouteIndexEntry
            DESCRIPTION
                    "The index vRtrInetStaticRouteDestType supports the values
                     'ipv4Mcast (128)' and 'ipv6Mcast (129)' in addition to
                     those defined by the InetAddressType textual convention.
                     'ipv4Mcast (128)' and 'ipv6Mcast (129)' are implemented
                     for 'ipv4'/'ipv6' addresses for multicast extensions."

        VARIATION   vRtrInetStaticRouteEntry
            DESCRIPTION
                    "The index vRtrInetStaticRouteDestType support the values
                     'ipv4Mcast (128)' and 'ipv6Mcast (129)' in addition to
                     those defined by the InetAddressType textual convention.
                     'ipv4Mcast (128)' and 'ipv6Mcast (129)' are implemented
                     for 'ipv4'/'ipv6' addresses for multicast extensions."

        VARIATION   vRtrIfDHCPLeasePopulate
            DESCRIPTION
                    "The default value of vRtrIfDHCPLeasePopulate is '1',
                     not '0', when the interface running DHCP has vRtrIfType
                     'serviceIesGroup'."

        VARIATION   vRtrIgnoreIcmpRedirect
            DESCRIPTION
                    "The default value of vRtrIgnoreIcmpRedirect is changed
                     to 'true' from 'false' in release 4.0-R13 and 5.0-R3."

        VARIATION   vRtrIfIpcpPeerAddrType
            SYNTAX  INTEGER {
                        unknown     (0),
                        ipv4        (1)
                        -- ipv6     (2),
                        -- ipv4z    (3),
                        -- ipv6z    (4),
                        -- dns      (16)
                    }
            DESCRIPTION
                    "vRtrIfIpcpPeerAddrType supports only InetAddressType
                     values 'unknown (0)' and 'ipv4 (1)'."

        VARIATION   vRtrIfIpcpPeerAddr
            SYNTAX  InetAddress (SIZE (0|4))
            DESCRIPTION
                    "vRtrIfIpcpPeerAddr supports only InetAddressType
                     values 'unknown' and 'ipv4'."

        VARIATION   vRtrIfIpcpPriDnsAddrType
            SYNTAX  INTEGER {
                        unknown     (0),
                        ipv4        (1)
                        -- ipv6     (2),
                        -- ipv4z    (3),
                        -- ipv6z    (4),
                        -- dns      (16)
                    }
            DESCRIPTION
                    "vRtrIfIpcpPriDnsAddrType supports only InetAddressType
                     values 'unknown (0)' and 'ipv4 (1)'."

        VARIATION   vRtrIfIpcpPriDnsAddr
            SYNTAX  InetAddress (SIZE (0|4))
            DESCRIPTION
                    "vRtrIfIpcpPriDnsAddr supports only InetAddressType
                     values 'unknown' and 'ipv4'."

        VARIATION   vRtrIfIpcpSecDnsAddrType
            SYNTAX  INTEGER {
                        unknown     (0),
                        ipv4        (1)
                        -- ipv6     (2),
                        -- ipv4z    (3),
                        -- ipv6z    (4),
                        -- dns      (16)
                    }
            DESCRIPTION
                    "vRtrIfIpcpSecDnsAddrType supports only InetAddressType
                     values 'unknown (0)' and 'ipv4 (1)'."

        VARIATION   vRtrIfIpcpSecDnsAddr
            SYNTAX  InetAddress (SIZE (0|4))
            DESCRIPTION
                    "vRtrIfIpcpSecDnsAddr supports only InetAddressType
                     values 'unknown' and 'ipv4'."

        VARIATION   vRtrInetStaticRouteCpeAddrType
            SYNTAX  INTEGER {
                        unknown     (0),
                        ipv4        (1)
                        -- ipv6     (2),
                        -- ipv4z    (3),
                        -- ipv6z    (4),
                        -- dns      (16)
                    }
            DESCRIPTION
                    "vRtrInetStaticRouteCpeAddrType supports only
                     InetAddressType values 'unknown' and 'ipv4'."

        VARIATION   vRtrInetStaticRouteCpeAddr
            SYNTAX  InetAddress (SIZE (0|4))
            DESCRIPTION
                    "vRtrInetStaticRouteCpeAddr supports only
                     InetAddressType values 'unknown' and 'ipv4'."

        VARIATION   vRtrLdpShortcut
            SYNTAX  TmnxEnabledDisabled
            DESCRIPTION
                    "vRtrLdpShortcut is only supported in the default or base
                     routing instance."

        VARIATION   vRtrRsvpTunIfSenderAddrType
            SYNTAX  INTEGER {
                        -- unknown  (0),
                        ipv4        (1)
                        -- ipv6     (2),
                        -- ipv4z    (3),
                        -- ipv6z    (4),
                        -- dns      (16)
                    }
            DESCRIPTION
                    "vRtrRsvpTunIfSenderAddrType supports only InetAddressType
                    'ipv4'."

        VARIATION   vRtrRsvpTunIfSenderAddr
            SYNTAX  InetAddress (SIZE (4))
            DESCRIPTION
                    "vRtrRsvpTunIfSenderAddr supports only InetAddressType
                    'ipv4'."

        VARIATION   vRtrRsvpTunIfStandbyAddrType
            SYNTAX  INTEGER {
                        -- unknown  (0),
                        ipv4        (1)
                        -- ipv6     (2),
                        -- ipv4z    (3),
                        -- ipv6z    (4),
                        -- dns      (16)
                     }
            DESCRIPTION
                    "vRtrRsvpTunIfStandbyAddrType supports only InetAddressType
                    'ipv4'."

        VARIATION   vRtrRsvpTunIfStandbyAddr
            SYNTAX  InetAddress (SIZE (4))
            DESCRIPTION
                    "vRtrRsvpTunIfStandbyAddr supports only InetAddressType
                    'ipv4'."

        VARIATION   vRtrRsvpTunIfSrcAddrType
            SYNTAX  INTEGER {
                        -- unknown  (0),
                        ipv4        (1)
                        -- ipv6     (2),
                        -- ipv4z    (3),
                        -- ipv6z    (4),
                        -- dns      (16)
                    }
            DESCRIPTION
                    "vRtrRsvpTunIfSrcAddrType supports only InetAddressType
                    'ipv4'."

        VARIATION   vRtrRsvpTunIfSrcAddr
            SYNTAX  InetAddress (SIZE (4))
            DESCRIPTION
                    "vRtrRsvpTunIfSrcAddr supports only InetAddressType
                    'ipv4'."

        VARIATION   vRtrLdpTunIfSenderAddrType
            SYNTAX  INTEGER {
                        -- unknown  (0),
                        ipv4        (1)
                        -- ipv6     (2),
                        -- ipv4z    (3),
                        -- ipv6z    (4),
                        -- dns      (16)
                    }
            DESCRIPTION
                    "vRtrLdpTunIfSenderAddrType supports only InetAddressType
                    'ipv4'."

        VARIATION   vRtrLdpTunIfSenderAddr
            SYNTAX  InetAddress (SIZE (4))
            DESCRIPTION
                    "vRtrLdpTunIfSenderAddr supports only InetAddressType
                     'ipv4'."

        VARIATION   vRtrIfBfdType
            SYNTAX  INTEGER {
                        cpmNp(1),
                        auto(2)
                    }
            DESCRIPTION
                    "cpmNp(1) is not supported on SROS SR-1 or ESS-1."

        VARIATION   vRtrMvpnIpmsiType
            SYNTAX  INTEGER {
                        none    (0),
                        --rsvp  (1),
                        pim     (2)

                    }
            DESCRIPTION
                    "The value 'rsvp(1)' is not supported in the release 8.0R1."

        VARIATION   vRtrMvpnSpmsiType
            SYNTAX  INTEGER {
                        none    (0),
                        --rsvp  (1),
                        pim     (2)

                    }
            DESCRIPTION
                    "The value 'rsvp(1)' is not supported in the release 8.0R1."

        VARIATION   vRtrFibStatMobileHostRoutes
            ACCESS  not-implemented
            DESCRIPTION
                    "The object vRtrFibStatMobileHostRoutes is not implemented."

        VARIATION   vRtrFibStatV6MobileHostRoutes
            ACCESS  not-implemented
            DESCRIPTION
                    "The object vRtrFibStatV6MobileHostRoutes is not
                     implemented."

        VARIATION   vRtrMobileHostRoutes
            ACCESS  not-implemented
            DESCRIPTION
                    "The object vRtrMobileHostRoutes is not implemented."

        VARIATION   vRtrMobileHostActiveRoutes
            ACCESS  not-implemented
            DESCRIPTION
                    "The object vRtrMobileHostActiveRoutes is not implemented."

        VARIATION   vRtrV6MobileHostRoutes
            ACCESS  not-implemented
            DESCRIPTION
                    "The object vRtrV6MobileHostRoutes is not implemented."

        VARIATION   vRtrV6MobileHostActiveRoutes
            ACCESS  not-implemented
            DESCRIPTION
                    "The object vRtrV6MobileHostActiveRoutes is not
                     implemented."

        VARIATION   vRtrIllegalLabelThreshold
            ACCESS  read-only
            DESCRIPTION
                    "The object vRtrIllegalLabelThreshold is currently
                     implemented as read-only."

        VARIATION   vRtrDnsRowStatus
            SYNTAX  INTEGER {
                        active(1),
                        createAndGo(4),
                        destroy(6)
                    }
            DESCRIPTION
                    "The only allowed values for this object are 
                    'active', 'createAndGo' and 'destroy'."
                    
        VARIATION   vRtrDnsPrimaryAddrType
            SYNTAX  INTEGER {
                        unknown(0),
                        ipv4(1),
                        ipv6(2)
                    }
            DESCRIPTION
                    "The only allowed values for this object are 
                    'unknown', 'ipv4' and 'ipv6'."
                    
        VARIATION   vRtrDnsSecondaryAddrType
            SYNTAX  INTEGER {
                        unknown(0),
                        ipv4(1),
                        ipv6(2)
                    }
            DESCRIPTION
                    "The only allowed values for this object are 
                    'unknown', 'ipv4' and 'ipv6'." 
                    
        VARIATION   vRtrDnsTertiaryAddrType
            SYNTAX  INTEGER {
                        unknown(0),
                        ipv4(1),
                        ipv6(2)
                    }
            DESCRIPTION
                    "The only allowed values for this object are 
                    'unknown', 'ipv4' and 'ipv6'."

        VARIATION    vRtrIfIpReasPortID
            ACCESS  not-implemented
            DESCRIPTION
                    "The object vRtrIfIpReasPortID is not
                     implemented."

        VARIATION    vRtrIfIpReasContextValue
            ACCESS  not-implemented
            DESCRIPTION
                    "The object vRtrIfIpReasContextValue is not
                     implemented."

        VARIATION    vRtrIfIpReasFragPktsRcvd
            ACCESS  not-implemented
            DESCRIPTION
                    "The object vRtrIfIpReasFragPktsRcvd is not
                     implemented."  

        VARIATION    vRtrIfIpReasFragPktsRcvdLow32
            ACCESS  not-implemented
            DESCRIPTION
                    "The object vRtrIfIpReasFragPktsRcvdLow32 is not
                     implemented."  

        VARIATION    vRtrIfIpReasFragPktsRcvdHigh32
            ACCESS  not-implemented
            DESCRIPTION
                    "The object vRtrIfIpReasFragPktsRcvdHigh32 is not
                     implemented."

        VARIATION    vRtrIfIpReasFragBytesRcvd
            ACCESS  not-implemented
            DESCRIPTION
                    "The object vRtrIfIpReasFragBytesRcvd is not
                     implemented."  

        VARIATION    vRtrIfIpReasFragBytesRcvdLow32
            ACCESS  not-implemented
            DESCRIPTION
                    "The object vRtrIfIpReasFragBytesRcvdLow32 is not
                     implemented."  

        VARIATION    vRtrIfIpReasFragBytesRcvdHigh32
            ACCESS  not-implemented
            DESCRIPTION
                    "The object vRtrIfIpReasFragBytesRcvdHigh32 is not
                     implemented."

        VARIATION    vRtrIfIpReasFragPktsReas
            ACCESS  not-implemented
            DESCRIPTION
                    "The object vRtrIfIpReasFragPktsReas is not
                     implemented."  

        VARIATION    vRtrIfIpReasFragPktsReasLow32
            ACCESS  not-implemented
            DESCRIPTION
                    "The object vRtrIfIpReasFragPktsReasLow32 is not
                     implemented."  

        VARIATION    vRtrIfIpReasFragPktsReasHigh32
            ACCESS  not-implemented
            DESCRIPTION
                    "The object vRtrIfIpReasFragPktsReasHigh32 is not
                     implemented."

        VARIATION    vRtrIfIpReasFragBytesReas
            ACCESS  not-implemented
            DESCRIPTION
                    "The object vRtrIfIpReasFragBytesReas is not
                     implemented."  

        VARIATION    vRtrIfIpReasFragBytesReasLow32
            ACCESS  not-implemented
            DESCRIPTION
                    "The object vRtrIfIpReasFragBytesReasLow32 is not
                     implemented."  

        VARIATION    vRtrIfIpReasFragBytesReasHigh32
            ACCESS  not-implemented
            DESCRIPTION
                    "The object vRtrIfIpReasFragBytesReasHigh32 is not
                     implemented."

        VARIATION    vRtrIfIpReasFragReasErrors
            ACCESS  not-implemented
            DESCRIPTION
                    "The object vRtrIfIpReasFragReasErrors is not
                     implemented."

        VARIATION    vRtrIfIpReasFragReasErrorsLow32
            ACCESS  not-implemented
            DESCRIPTION
                    "The object vRtrIfIpReasFragReasErrorsLow32 is not
                     implemented."

        VARIATION    vRtrIfIpReasFragReasErrorsHigh32
            ACCESS  not-implemented
            DESCRIPTION
                    "The object vRtrIfIpReasFragReasErrorsHigh32 is not
                     implemented."

        VARIATION    vRtrIfIpReasFragDisc
            ACCESS  not-implemented
            DESCRIPTION
                    "The object vRtrIfIpReasFragDisc is not
                     implemented."  

        VARIATION    vRtrIfIpReasFragDiscLow32
            ACCESS  not-implemented
            DESCRIPTION
                    "The object vRtrIfIpReasFragDiscLow32 is not
                     implemented."  

        VARIATION    vRtrIfIpReasFragDiscHigh32
            ACCESS  not-implemented
            DESCRIPTION
                    "The object vRtrIfIpReasFragDiscHigh32 is not
                     implemented."

        VARIATION    vRtrIfIpReasOutBufRes
            ACCESS  not-implemented
            DESCRIPTION
                    "The object vRtrIfIpReasOutBufRes is not
                     implemented."  

        VARIATION    vRtrIfIpReasOutBufResLow32
            ACCESS  not-implemented
            DESCRIPTION
                    "The object vRtrIfIpReasOutBufResLow32 is not
                     implemented."

        VARIATION    vRtrIfIpReasOutBufResHigh32
            ACCESS  not-implemented
            DESCRIPTION
                    "The object vRtrIfIpReasOutBufResHigh32 is not
                     implemented."

        VARIATION    vRtrIfIpReasPktsRx
            ACCESS  not-implemented
            DESCRIPTION
                    "The object vRtrIfIpReasPktsRx is not
                     implemented."  

        VARIATION    vRtrIfIpReasPktsRxLow32
            ACCESS  not-implemented
            DESCRIPTION
                    "The object vRtrIfIpReasPktsRxLow32 is not
                     implemented."

        VARIATION    vRtrIfIpReasPktsRxHigh32
            ACCESS  not-implemented
            DESCRIPTION
                    "The object vRtrIfIpReasPktsRxHigh32 is not
                     implemented."

        VARIATION    vRtrIfIpReasBytesRx
            ACCESS  not-implemented
            DESCRIPTION
                    "The object vRtrIfIpReasBytesRx is not
                     implemented."   

        VARIATION    vRtrIfIpReasBytesRxLow32
            ACCESS  not-implemented
            DESCRIPTION
                    "The object vRtrIfIpReasBytesRxLow32 is not
                     implemented."

        VARIATION    vRtrIfIpReasBytesRxHigh32
            ACCESS  not-implemented
            DESCRIPTION
                    "The object vRtrIfIpReasBytesRxHigh32 is not
                     implemented."

        VARIATION    vRtrIfIpReasPktsTx
            ACCESS  not-implemented
            DESCRIPTION
                    "The object vRtrIfIpReasPktsTx is not
                     implemented."  

        VARIATION    vRtrIfIpReasPktsTxLow32
            ACCESS  not-implemented
            DESCRIPTION
                    "The object vRtrIfIpReasPktsTxLow32 is not
                     implemented."

        VARIATION    vRtrIfIpReasPktsTxHigh32
            ACCESS  not-implemented
            DESCRIPTION
                    "The object vRtrIfIpReasPktsTxHigh32 is not
                     implemented."

        VARIATION    vRtrIfIpReasBytesTx
            ACCESS  not-implemented
            DESCRIPTION
                    "The object vRtrIfIpReasBytesTx is not
                     implemented."  

        VARIATION    vRtrIfIpReasBytesTxLow32
            ACCESS  not-implemented
            DESCRIPTION
                    "The object vRtrIfIpReasBytesTxLow32 is not
                     implemented."

        VARIATION    vRtrIfIpReasBytesTxHigh32
            ACCESS  not-implemented
            DESCRIPTION
                    "The object vRtrIfIpReasBytesTxHigh32 is not
                     implemented."

        VARIATION    vRtrIfIpReasV6FragPktsRcvd
            ACCESS  not-implemented
            DESCRIPTION
                    "The object vRtrIfIpReasV6FragPktsRcvd is not
                     implemented."  

        VARIATION    vRtrIfIpReasV6FragPktsRcvdLow32
            ACCESS  not-implemented
            DESCRIPTION
                    "The object vRtrIfIpReasV6FragPktsRcvdLow32 is not
                     implemented."  

        VARIATION    vRtrIfIpReasV6FragPktsRcvdHigh32
            ACCESS  not-implemented
            DESCRIPTION
                    "The object vRtrIfIpReasV6FragPktsRcvdHigh32 is not
                     implemented."

        VARIATION    vRtrIfIpReasV6FragBytesRcvd
            ACCESS  not-implemented
            DESCRIPTION
                    "The object vRtrIfIpReasV6FragBytesRcvd is not
                     implemented."  

        VARIATION    vRtrIfIpReasV6FragBytesRcvdL32
            ACCESS  not-implemented
            DESCRIPTION
                    "The object vRtrIfIpReasV6FragBytesRcvdL32 is not
                     implemented."  

        VARIATION    vRtrIfIpReasV6FragBytesRcvdH32
            ACCESS  not-implemented
            DESCRIPTION
                    "The object vRtrIfIpReasV6FragBytesRcvdH32 is not
                     implemented."

        VARIATION    vRtrIfIpReasV6FragPktsReas
            ACCESS  not-implemented
            DESCRIPTION
                    "The object vRtrIfIpReasV6FragPktsReas is not
                     implemented."  

        VARIATION    vRtrIfIpReasV6FragPktsReasLow32
            ACCESS  not-implemented
            DESCRIPTION
                    "The object vRtrIfIpReasV6FragPktsReasLow32 is not
                     implemented."  

        VARIATION    vRtrIfIpReasV6FragPktsReasHigh32
            ACCESS  not-implemented
            DESCRIPTION
                    "The object vRtrIfIpReasV6FragPktsReasHigh32 is not
                     implemented."

        VARIATION    vRtrIfIpReasV6FragBytesReas
            ACCESS  not-implemented
            DESCRIPTION
                    "The object vRtrIfIpReasV6FragBytesReas is not
                     implemented."  

        VARIATION    vRtrIfIpReasV6FragBytesReasL32
            ACCESS  not-implemented
            DESCRIPTION
                    "The object vRtrIfIpReasV6FragBytesReasL32 is not
                     implemented."  

        VARIATION    vRtrIfIpReasV6FragBytesReasH32
            ACCESS  not-implemented
            DESCRIPTION
                    "The object vRtrIfIpReasV6FragBytesReasH32 is not
                     implemented."

        VARIATION    vRtrIfIpReasV6FragReasErrors
            ACCESS  not-implemented
            DESCRIPTION
                    "The object vRtrIfIpReasV6FragReasErrors is not
                     implemented."

        VARIATION    vRtrIfIpReasV6FragReasErrorsL32
            ACCESS  not-implemented
            DESCRIPTION
                    "The object vRtrIfIpReasV6FragReasErrorsL32 is not
                     implemented."

        VARIATION    vRtrIfIpReasV6FragReasErrorsH32
            ACCESS  not-implemented
            DESCRIPTION
                    "The object vRtrIfIpReasV6FragReasErrorsH32 is not
                     implemented."  

        VARIATION    vRtrIfIpReasV6FragDisc
            ACCESS  not-implemented
            DESCRIPTION
                    "The object vRtrIfIpReasV6FragDisc is not
                     implemented."  

        VARIATION    vRtrIfIpReasV6FragDiscLow32
            ACCESS  not-implemented
            DESCRIPTION
                    "The object vRtrIfIpReasV6FragDiscLow32 is not
                     implemented."  

        VARIATION    vRtrIfIpReasV6FragDiscHigh32
            ACCESS  not-implemented
            DESCRIPTION
                    "The object vRtrIfIpReasV6FragDiscHigh32 is not
                     implemented."

        VARIATION    vRtrIfIpReasV6OutBufRes
            ACCESS  not-implemented
            DESCRIPTION
                    "The object vRtrIfIpReasV6OutBufRes is not
                     implemented."  

        VARIATION    vRtrIfIpReasV6OutBufResLow32
            ACCESS  not-implemented
            DESCRIPTION
                    "The object vRtrIfIpReasV6OutBufResLow32 is not
                     implemented."

        VARIATION    vRtrIfIpReasV6OutBufResHigh32
            ACCESS  not-implemented
            DESCRIPTION
                    "The object vRtrIfIpReasV6OutBufResHigh32 is not
                     implemented."

        VARIATION    vRtrIfIpReasV6PktsRx
            ACCESS  not-implemented
            DESCRIPTION
                    "The object vRtrIfIpReasV6PktsRx is not
                     implemented."  

        VARIATION    vRtrIfIpReasV6PktsRxLow32
            ACCESS  not-implemented
            DESCRIPTION
                    "The object vRtrIfIpReasV6PktsRxLow32 is not
                     implemented."

        VARIATION    vRtrIfIpReasV6PktsRxHigh32
            ACCESS  not-implemented
            DESCRIPTION
                    "The object vRtrIfIpReasV6PktsRxHigh32 is not
                     implemented."

        VARIATION    vRtrIfIpReasV6BytesRx
            ACCESS  not-implemented
            DESCRIPTION
                    "The object vRtrIfIpReasV6BytesRx is not
                     implemented."   

        VARIATION    vRtrIfIpReasV6BytesRxLow32
            ACCESS  not-implemented
            DESCRIPTION
                    "The object vRtrIfIpReasV6BytesRxLow32 is not
                     implemented."

        VARIATION    vRtrIfIpReasV6BytesRxHigh32
            ACCESS  not-implemented
            DESCRIPTION
                    "The object vRtrIfIpReasV6BytesRxHigh32 is not
                     implemented."

        VARIATION    vRtrIfIpReasV6PktsTx
            ACCESS  not-implemented
            DESCRIPTION
                    "The object vRtrIfIpReasV6PktsTx is not
                     implemented."  

        VARIATION    vRtrIfIpReasV6PktsTxLow32
            ACCESS  not-implemented
            DESCRIPTION
                    "The object vRtrIfIpReasV6PktsTxLow32 is not
                     implemented."

        VARIATION    vRtrIfIpReasV6PktsTxHigh32
            ACCESS  not-implemented
            DESCRIPTION
                    "The object vRtrIfIpReasV6PktsTxHigh32 is not
                     implemented."

        VARIATION    vRtrIfIpReasV6BytesTx
            ACCESS  not-implemented
            DESCRIPTION
                    "The object vRtrIfIpReasV6BytesTx is not
                     implemented."  

        VARIATION    vRtrIfIpReasV6BytesTxLow32
            ACCESS  not-implemented
            DESCRIPTION
                    "The object vRtrIfIpReasV6BytesTxLow32 is not
                     implemented."

        VARIATION    vRtrIfIpReasV6BytesTxHigh32
            ACCESS  not-implemented
            DESCRIPTION
                    "The object vRtrIfIpReasV6BytesTxHigh32 is not
                     implemented."

        VARIATION   vRtrInterASMvpn
            ACCESS  not-implemented
            DESCRIPTION
                    "The object vRtrInterASMvpn is not implemented."
        
    ::= { tmnxSROSV10v0 43 }  -- VRTR

tmnxSprVRtrCapsV10v0    AGENT-CAPABILITIES
    PRODUCT-RELEASE "Alcatel-Lucent SROS"
    STATUS          current
    DESCRIPTION     "Implementation of Virtual Router capabilities
                     for Alcatel-Lucent SROS SPR release R10.0"

    SUPPORTS        TIMETRA-VRTR-MIB
        INCLUDES    {
            tmnxVRtrIfV10v0Group,
            tmnxVRtrBfdV9v0Group
-- EXCLUDE  tmnxVRtrIfCpmProtectGroup,                  no DOS Protection on SPR
        }

        VARIATION vRtrIfType
            SYNTAX  INTEGER {
                        network                  (1),
                        service                  (2),
                        serviceIes               (3),
                        -- serviceRtdVpls        (4)
                        serviceVprn              (5),
                        serviceIesSubscriber     (6),
                        serviceIesGroup          (7),
                        serviceVprnSubscriber    (8),
                        serviceVprnGroup         (9),
                        serviceIesRedundant      (10),
                        serviceVprnRedundant     (11),
                        serviceVpls              (12),
                        serviceIesCem            (13),
                        serviceVprnCem           (14),
                        -- serviceVprnIPsec      (15)
                        serviceVprnIPMirror      (16)
                    }
            DESCRIPTION
                    "The values
                        - 'serviceRtdVpls        (4)'  (obsoleted)
                        - 'serviceVprnIPsec      (15)' (IPsec Tunneling)
                     are not suppoted on SROS SPR systems."

        VARIATION   vRtrIfBfdType
            SYNTAX  INTEGER {
                        -- cpmNp(1),
                        auto(2)
                    }
            DESCRIPTION
                    "cpmNp(1) is not supported on SROS SPR."

    ::= { tmnxSROSVRtrCapsV10v0 3 }  -- SPR VRTR

--
--  NTP CAPABILITIES
--
tmnxSROSNtpCapsV10v0    AGENT-CAPABILITIES
    PRODUCT-RELEASE "Alcatel-Lucent SROS"
    STATUS          current
    DESCRIPTION     "Implementation of NTP capabilities
                     for Alcatel-Lucent SROS release R10.0"

    SUPPORTS        TIMETRA-NTP-MIB
        INCLUDES    {
            tmnxNtpGlobalV8v0Group,
            tmnxNtpV8v0Group,
            tmnxNtpBroadcastGroup,
            tmnxNtpMulticastGroup,
            tmnxNtpServersGroup,
            tmnxNtpPeersGroup,
            tmnxNtpAuthKeyGroup,
            tmnxNtpNotificationV6v0Group
        }

        VARIATION   tmnxNtpMulticastAddressType
            SYNTAX  INTEGER {
                        -- unknown  (0),
                        ipv4        (1)
                        -- ipv6     (2),
                        -- ipv4z    (3),
                        -- ipv6z    (4),
                        -- dns      (16)
                    }
            DESCRIPTION
                    "tmnxNtpMulticastAddressType supports only InetAddressType
                    'ipv4 (1)'."

        VARIATION   tmnxNtpMulticastAddress
            SYNTAX  InetAddress (SIZE (4))
            DESCRIPTION
                    "tmnxNtpMulticastAddress supports only InetAddressType
                    'ipv4'."

        VARIATION   tmnxNtpServersAddrType
            SYNTAX  INTEGER {
                        -- unknown  (0),
                        ipv4        (1)
                        -- ipv6     (2),
                        -- ipv4z    (3),
                        -- ipv6z    (4),
                        -- dns      (16)
                    }
            DESCRIPTION
                    "The tmnxNtpServersAddrType supports only InetAddressType
                    'ipv4 (1)'."

        VARIATION   tmnxNtpServersAddress
            SYNTAX  InetAddress (SIZE (4))
            DESCRIPTION
                    "tmnxNtpServersAddress supports only InetAddressType
                    'ipv4'."

        VARIATION   tmnxNtpPeersAddrType
            SYNTAX  INTEGER {
                        -- unknown  (0),
                        ipv4        (1)
                        -- ipv6     (2),
                        -- ipv4z    (3),
                        -- ipv6z    (4),
                        -- dns      (16)
                    }
            DESCRIPTION
                    "The tmnxNtpPeersAddrType supports only InetAddressType
                    'ipv4 (1)'."

        VARIATION   tmnxNtpPeersAddress
            SYNTAX  InetAddress (SIZE (4))
            DESCRIPTION
                    "tmnxNtpPeersAddress supports only InetAddressType
                    'ipv4'."

        VARIATION   tmnxNtpPeersPeerAddrType
            SYNTAX  INTEGER {
                        -- unknown  (0),
                        ipv4        (1)
                        -- ipv6     (2),
                        -- ipv4z    (3),
                        -- ipv6z    (4),
                        -- dns      (16)
                    }
            DESCRIPTION
                    "tmnxNtpPeersPeerAddrType supports only InetAddressType
                    'ipv4 (1)'."

        VARIATION   tmnxNtpPeersPeerAddress
            SYNTAX  InetAddress (SIZE (4))
            DESCRIPTION
                    "tmnxNtpPeersPeerAddress supports only InetAddressType
                    'ipv4'."

        VARIATION   tmnxNtpAuthKeyEntry
            CREATION-REQUIRES   { tmnxNtpAuthKeyType }
            DESCRIPTION
                    "A value must be set for tmnxNtpAuthKeyType in order for
                     tmnxNtpAuthKeyEntryStatus to successfully transition
                     to the 'active' state."

        VARIATION   tmnxNtpAuthKeyType
            SYNTAX  INTEGER {
                        -- des          (1),
                        messageDigest   (2)
                    }
            DESCRIPTION
                    "The tmnxNtpAuthKeyType supports only
                    'messageDigest (2)'."

        VARIATION   tmnxNtpUtcOffsetExThreshold
            ACCESS  not-implemented
            DESCRIPTION
                    "The tmnxNtpUtcOffsetExThreshold is not implemented.
                     This notification was made obsolete in 4.0 R-12
                     release and 5.0 R-2 release."

        VARIATION   tmnxNtpUtcOffsetInThreshold
            ACCESS  not-implemented
            DESCRIPTION
                    "The tmnxNtpUtcOffsetInThreshold  is not implemented.
                     This notification was made obsolete in 4.0 R-12
                     release and 5.0 R-2 release."

        VARIATION   tmnxNtpMaxFreqDftExceed
            ACCESS  not-implemented
            DESCRIPTION
                    "The tmnxNtpMaxFreqDftExceed  is not implemented.
                     This notification was made obsolete in 6.0 R-15
                     release."

    ::= { tmnxSROSV10v0 44 }  -- NTP

--
--  SUBSCRIBER MANAGEMENT CAPABILITIES
--
tmnxSROSSubscrMgmtCapsV10v0  AGENT-CAPABILITIES
    PRODUCT-RELEASE "Alcatel-Lucent SROS"
    STATUS          current
    DESCRIPTION     "Implementation of Subscriber Management capabilities
                     for Alcatel-Lucent SROS release R10.0"

    SUPPORTS        TIMETRA-SUBSCRIBER-MGMT-MIB
        INCLUDES    {
            tmnxCcIpFltrV8v0Group,
            tmnxCcIpv6FltrV8v0Group,
-- EXCLUDE  tmnxHsmdaSubscriberV10v0Group,     Not supported on SPR
            tmnxSubAccountingV8v0Group,
            tmnxSubAccountingV10v0Group,
            tmnxSubAuthenticationV8v0Group,
            tmnxSubAuthenticationV10v0Group,
-- EXCLUDE  tmnxSubBsxObjV9v0Group,           Not supported on SPR
            tmnxSubCreditControlV8v0Group,
            tmnxSubFrameBasedAccntV6v0Group,
            tmnxSubHostTrackingV9v0Group,
            tmnxSubMgmtIPv6V8v0Group,
            tmnxSubMgmtV7v0NotifGroup,
            tmnxSubMgmtV9v0NotifGroup,
            tmnxSubMgmtV10v0NotifGroup,
            tmnxSubMgmtV10v0Group,
-- EXCLUDE  tmnxSubNatGroup                   Not supported on 7450 or SPR
            tmnxSubProfileMssExtensionsGroup,
            tmnxSubCreditControlV9v0Group,
            tmnxSubCreditControlV10v0Group,
            tmnxSubAutoSubIdV10v0Group,
            tmnxSubIpoeLinkV10v0Group,
            tmnxSubPppGroup,
            tmnxSubPppV10v0Group,
            tmnxSubSlaacV10v0Group,
            tmnxSubProfileV9v0Group,
            tmnxSubRadNotifStatsV6v0Group,
            tmnxSubRadusPlcyCustomRecordV7v0Group,
            tmnxSubV6GrpIfRAV8v0Group,
            tmnxSubAleGroup
-- EXCLUDE  tmnxSubHsmdaGroup                 Not supported on SPR
-- EXCLUDE  tmnxSubFlterProfGroup             Not supported
-- EXCLUDE  tmnxSubL2tpGroup                  L2tp not supported on 7710
        }

        VARIATION   tmnxSubAuthPlcyPppoeAccessMethod
            SYNTAX INTEGER {
                none     (1),
                padi     (2),
                pap-chap (3)
             -- eap      (4)
            }
            DESCRIPTION
                    "The value 'eap' is not allowed in this
                    release."

        VARIATION   tmnxSubIPolRejectUnknownStrings
            ACCESS  not-implemented
            DESCRIPTION
                    "This object is not implemented."

        VARIATION   tmnxSubRadiusAcceptRowStatus
            SYNTAX  INTEGER {
                        active      (1),
                        createAndGo (4),
                        destroy     (6)
                     }
            DESCRIPTION
                    "The only allowed values for this object are
                    'active (1)', 'createAndGo (4)' and 'destroy (6)'."

        VARIATION   tmnxSubAutoSubIdIpoeKey1
            SYNTAX  INTEGER {
                        none      (0),
                        mac       (1),
                        sapId     (2),
                        circuitId (3),
                        remoteId  (4)
                        -- sessionId (5)
                    }
            DESCRIPTION
                    "Value 'sessionId (5)' is not allowed for this object."

        VARIATION   tmnxSubAutoSubIdIpoeKey2
            SYNTAX  INTEGER {
                        none      (0),
                        mac       (1),
                        sapId     (2),
                        circuitId (3),
                        remoteId  (4)
                        -- sessionId (5)
                    }
            DESCRIPTION
                    "Value 'sessionId (5)' is not allowed for this object."

        VARIATION   tmnxSubAutoSubIdIpoeKey3
            SYNTAX  INTEGER {
                        none      (0),
                        mac       (1),
                        sapId     (2),
                        circuitId (3),
                        remoteId  (4)
                        -- sessionId (5)
                    }
            DESCRIPTION
                    "Value 'sessionId (5)' is not allowed for this object."

        VARIATION   tmnxSubAutoSubIdIpoeKey4
            SYNTAX  INTEGER {
                        none      (0),
                        mac       (1),
                        sapId     (2),
                        circuitId (3),
                        remoteId  (4)
                        -- sessionId (5)
                    }
            DESCRIPTION
                    "Value 'sessionId (5)' is not allowed for this object."

        VARIATION   tmnxSubAcctPlcyHostAccounting
            SYNTAX  INTEGER {
                        enabled     (1),
                        disabled    (2),
                        interim     (3)
                        -- host        (4),
                        -- interimHost (5)  
                    }
            DESCRIPTION
                    "Values 'host (4)' and 'interimHost (5)' are not allowed
                     for this object."

        VARIATION   tmnxSubAcctPlcyQueueInstAcct
            SYNTAX  INTEGER {
                        enabled     (1),
                        disabled    (2),
                        interim     (3)
                        -- host        (4),
                        -- interimHost (5)  
                    }
            DESCRIPTION
                    "Values 'host (4)' and 'interimHost (5)' are not allowed
                     for this object."

    ::= { tmnxSROSV10v0 45 } -- SUBSCRIBER MANAGEMENT

tmnx7750SubscrMgmtCapsV10v0  AGENT-CAPABILITIES
    PRODUCT-RELEASE "Alcatel-Lucent SROS"
    STATUS          current
    DESCRIPTION     "Implementation of specific Subscriber Management
                     capabilities for Alcatel-Lucent SROS 7750 release R10.0"

    SUPPORTS        TIMETRA-SUBSCRIBER-MGMT-MIB
        INCLUDES    {
            tmnxSubNatGroup,
            tmnxSubBsxObjV9v0Group,
            tmnxHsmdaSubscriberV10v0Group,
            tmnxSubHsmdaGroup,
            tmnxSubL2tpGroup
        }

    ::= { tmnxSROSSubscrMgmtCapsV10v0 1 } -- 7750 SUBSCRIBER MANAGEMENT

tmnx7450SubscrMgmtCapsV10v0  AGENT-CAPABILITIES
    PRODUCT-RELEASE "Alcatel-Lucent SROS"
    STATUS          current
    DESCRIPTION     "Implementation of specific Subscriber Management
                     capabilities for Alcatel-Lucent SROS 7450 release R10.0"

    SUPPORTS        TIMETRA-SUBSCRIBER-MGMT-MIB
        INCLUDES    {
            tmnxHsmdaSubscriberV10v0Group,
            tmnxSubBsxObjV9v0Group,
            tmnxSubHsmdaGroup,
            tmnxSubL2tpGroup
        }

    ::= { tmnxSROSSubscrMgmtCapsV10v0 2 } -- 7450 SUBSCRIBER MANAGEMENT


tmnx7710SubscrMgmtCapsV10v0  AGENT-CAPABILITIES
    PRODUCT-RELEASE "Alcatel-Lucent SROS"
    STATUS          current
    DESCRIPTION     "Implementation of specific Subscriber Management
                     capabilities for Alcatel-Lucent SROS 7710 release R10.0"

    SUPPORTS        TIMETRA-SUBSCRIBER-MGMT-MIB
        INCLUDES    {
            tmnxSubCreditControlV8v0Group
        }

        VARIATION   tmnxSubApCategoryIngressPolicers
            ACCESS  not-implemented
            DESCRIPTION
                "tmnxSubApCategoryIngressPolicers is not implemented on
                 Alcatel-Lucent 7710 systems."

        VARIATION   tmnxSubApCategoryEgressPolicers
            ACCESS  not-implemented
            DESCRIPTION
                "tmnxSubApCategoryEgressPolicers is not implemented on
                 Alcatel-Lucent 7710 systems."

    ::= { tmnxSROSSubscrMgmtCapsV10v0 3 } -- 7710 SUBSCRIBER MANAGEMENT

tmnx7950SubscrMgmtCapsV10v0  AGENT-CAPABILITIES
    PRODUCT-RELEASE "Alcatel-Lucent SROS"
    STATUS          current
    DESCRIPTION     "Subscriber Management is not supported
                     on Alcatel-Lucent SROS 7950 release R10.0."

--    SUPPORTS        TIMETRA-SUBSCRIBER-MGMT-MIB
--        INCLUDES    { }

    ::= { tmnxSROSSubscrMgmtCapsV10v0 4 } -- 7950 SUBSCRIBER MANAGEMENT

--
--  CRON CAPABILITIES
--
tmnxSROSCronCapsV10v0    AGENT-CAPABILITIES
    PRODUCT-RELEASE "Alcatel-Lucent SROS"
    STATUS          current
    DESCRIPTION     "Implementation of CRON capabilities
                     for Alcatel-Lucent SROS release R10.0"

    SUPPORTS        DISMAN-SCHEDULE-MIB
        INCLUDES    {
            schedGroup2,
            schedCalendarGroup,
            schedNotificationsGroup
        }

        VARIATION   schedOwner
            SYNTAX  SnmpAdminString (SIZE (1..32))
            DESCRIPTION
                    "The minimum length of schedOwner is 1 when creating
                     new entries in tables via SNMP SET requests."

        VARIATION   schedInterval
            SYNTAX  Unsigned32 (30..42949672)
            DESCRIPTION
                    "The values supported for schedInterval are between
                    30 and 42949672 seconds.  42949672 seconds creates
                    a maximum interval of 497 days, 2 hours, 27 minutes
                    and 52 seconds."


    SUPPORTS        DISMAN-SCRIPT-MIB
        INCLUDES    {
            smLanguageGroup,
            smScriptGroup2,
            smLaunchGroup2,
            smRunGroup2,
            smNotificationsGroup2
        }

        VARIATION   smScriptEntry
            DESCRIPTION
                    "A maximum of 255 smScriptEntry rows are allowed to be
                    created."

        VARIATION   smScriptOwner
            SYNTAX  SnmpAdminString (SIZE (1..32))
            DESCRIPTION
                    "The minimum length of smScriptOwner is 1 when creating
                     new entries in tables via SNMP SET requests."

        VARIATION   smScriptDescr
            SYNTAX  SnmpAdminString (SIZE (0..80))
            DESCRIPTION
                    "The maximum size string supported for smScriptDescr
                    is 80 octets."

        VARIATION   smScriptLanguage
            SYNTAX  Integer32 (1)
            DESCRIPTION
                    "The only script language supported is the TiMOS CLI
                    that has an smLangIndex value equal 1.  smScriptLanguage
                    can only be set to the value 1."

        VARIATION   smScriptSource
            DESCRIPTION
                    "The mib requires that when smScriptAdminStatus is
                    set to 'enabled', the agent at that point should
                    'pull' the script from local cflash or remote URL
                    if one is specified.  This agent does not 'pull'
                    scripts to its local storage.  The URL specified in
                    smScriptSource is passed as an argument to the CLI
                    'exec' command when the smRunState transitions to
                    'executing'.

                    The mib states that an empty URL implies that the
                    script scource is already in local storage and are
                    located by some implementation specific mapping
                    scheme between the local storage file name and the
                    smScriptName index.  This agent does not support
                    this behavior.  An empty smScriptSource URL causes
                    an attempt to set a value to smLaunchStart to return
                    an 'inconsistentValue' error."

        VARIATION   smScriptAdminStatus
            SYNTAX  INTEGER {
                        enabled     (1),
                        disabled    (2)
                        -- editing  (3)
                    }
            DESCRIPTION
                    "The smScriptAdminStatus state 'editing (3)' is not
                    supported because smCodeTable is not supported."

        VARIATION   smScriptStorageType
            DEFVAL  { nonVolatile }
            DESCRIPTION
                    "This agent supports only 'nonVolatile' storage type.
                    This is interpreted to be the desired storage type
                    for the configuration of the script row entry.

                    When smLaunchStorageType has a value of 'nonVolatile'
                    its configuration is written to the configuration
                    file upon a 'save configuration' operation.  If the
                    system reboots between the time this row entry is
                    created and before a 'save configuration' operation is
                    made, this row entry will NOT be restored following
                    the reboot."

        VARIATION   smLaunchEntry
            DESCRIPTION
                    "A maximum of 255 smLaunchEntry rows are allowed to be
                    created."

        VARIATION   smLaunchOwner
            SYNTAX  SnmpAdminString (SIZE (1..32))
            DESCRIPTION
                    "The minimum length of smLaunchOwner is 1 when creating
                     new entries in tables via SNMP SET requests."

        VARIATION   smLaunchMaxRunning
            SYNTAX  Unsigned32 (1)
            DESCRIPTION
                    "Concurrently running scripts are not supported by
                    this agent.  Scripts are queued and executed one
                    at a time.  An attempt to set smLaunchMaxRunning
                    to any value other than 1 results in an
                    'wrong`Value' error."

        VARIATION   smLaunchArgument
            DESCRIPTION
                    "This agent uses smLaunchArgument to specify the
                    URL of the file that is created to hold the CLI
                    session output from the 'exec' of the CLI script
                    specified in smScriptSource.  The script specified
                    in smScriptSource is executed as if the 'exec' '-echo'
                    switch was specified in a CLI CONSOLE/Telnet session
                    and the command echo and any display from CLI 'show'
                    commands specified in the script is redirected to the
                    results file specified in smLaunchArgument.

                    The smLaunchArgument URL should consist of the
                    path and a filename prefix.  It refer to either the
                    local cflash drives or a remote file accessed through
                    a remote ftp URL.  When the exec results file is created
                    for a specific run of the script, a timestamp of the
                    form '_yyyymmdd-hhmmss.out' is appended on the end of
                    the smLaunchArgument filename prefix.  For example,
                    setting smLaunchArgument to
                    'ftp://<user>:<passwd>@<a.b.c.d>/cron/results/test-res'
                    causes a script results file to be created named
                    'cron/results/test-res_yyyymmdd-hhmmss.out'.

                    NOTE: The agent does not have any capability to age out,
                    rotate, delete, or otherwise manage these script
                    results files.  It is up to the SROS system operator or
                    manager to manage retrieval and cleanup of these files."

        VARIATION   smLaunchMaxCompleted
            SYNTAX  Unsigned32 (1..255)
            DESCRIPTION
                    "A maximum of 255 finished scripts invoked from this
                     entry in the smLaunchTable are allowed to be retained in
                     the smRunTable. Whenever the value of this object is
                     changed and whenever a script terminates, entries in the
                     smRunTable are deleted if necessary until the number of
                     completed scripts is smaller than the value of this
                     object. Scripts whose smRunEndTime value indicates the
                     oldest completion time are deleted first."

        VARIATION   smLaunchExpireTime
            DESCRIPTION
                    "Unlike smLaunchLifeTime, the mib does not specify a
                    value for smLaunchExpireTime that can be used to
                    indicate an associated smRunEntry with a smRunState
                    equal to 'terminated' should be kept forever and
                    never aged out.  This agent uses the maximum value
                    (2147483647) to specify that an smRunEntry does not
                    age out after their smRunState transitions to
                    'terminated'.  A terminated smRunEntry with a maximum
                    smRunExpireTime value will never be removed from
                    the table."

        VARIATION   smLaunchStart
            DESCRIPTION
                    "In the 4.0 release there is no user access rights
                    checking to verify that the user setting smLaunchStart
                    has read-access to the script.  A user command
                    access profile with RADIUS/TACACS+ authentication will
                    be associated to the script in a later release.

                    The mib requires that in order for a set to smLaunchStart
                    to succede th number of concurrently executing scripts
                    must be less than the value of smLaunchMaxRunning.
                    This agent does not support execution of more than one
                    script at a time.  Instead, a smRunEntry is created
                    with smRunState equal to 'initializing' and sequentially
                    queued for later execution.  The maximum number of
                    smRunEntry rows is limited to 255 regardless of the value
                    of smRunState.

                    The mib specifies that when the smRunEntry is created
                    by setting smLaunchStart, the smRunStartTime should be
                    set to the current time.  Because of the one-at-a-time
                    queuing for execution there may be a long time between
                    entering the 'initializing' state and transitioning
                    to the 'executing' state, this agent does not set
                    smRunStartTime until smRunState transitions to
                    'executing'."

        VARIATION   smLaunchControl
            SYNTAX  INTEGER {
                       abort        (1),
                       -- suspend   (2),
                       -- resume    (3),
                       nop          (4)
                    }
            DESCRIPTION
                    "The 'suspend (2)' and 'resume (3)' controls are not
                    supported.  An attempt to set either value results
                    in an 'wrongValue' error. A read on this object always
                    returns 'nop (4)'."

        VARIATION   smLaunchAdminStatus
            SYNTAX  INTEGER {
                        enabled     (1),
                        disabled    (2)
                        -- autostart(3)
                    }
            DESCRIPTION
                    "The 'autostart (3)' state is not supported.

                    The mib is not clear if smLaunchAdminStatus can be
                    set to 'disabled' if there are associated entries
                    in the smRunTable.  This agent does not allow
                    smLaunchAdminStatus to be set to 'disabled (2)' if there
                    are any associated entries in the smRunTable.  Any
                    associated smRunEntry must be aborted and aged out
                    before smLaunchAdminStatus can be set to 'disabled (2)'."

        VARIATION   smLaunchRunIndexNext
            DESCRIPTION
                    "The mib requires that subsequent reads of
                    smLaunchRunIndexNext must return different values.
                    This agent does not increment the value with every
                    read.  A read always returns the next available
                    index value."

        VARIATION   smLaunchStorageType
            SYNTAX  INTEGER {
                        -- other        (1),
                        -- volatile     (2),
                        nonVolatile     (3)  -- e.g., in NVRAM
                        -- permanent    (4),
                        -- readOnly     (5)
                    }
            DEFVAL  { nonVolatile }
            DESCRIPTION
                    "This agent supports only 'nonVolatile (3)' storage type.
                    This is interpreted to be the desired storage type
                    for the configuration of the launch entry.

                    When smLaunchStorageType has a value of 'nonVolatile (3)'
                    its configuration is written to the configuration
                    file upon a 'save configuration' operation.  If the
                    system reboots between the time this row entry is
                    created and before a 'save configuration' operation is
                    made, this row entry will NOT be restored following
                    the reboot."

        VARIATION   smLaunchRowExpireTime
            ACCESS  read-only
            DESCRIPTION
                    "smLaunchRowExpireTime functionality is not supported.
                    The default value 2147483647 is always returned to
                    indicate that the smLaunchTable row entry will never
                    be aged out."

        VARIATION   smRunEntry
            DESCRIPTION
                    "A maximum of 255 smRunEntry rows are allowed to be created
                    regardless of the value of smRunState."

        VARIATION   smRunArgument
            SYNTAX  OCTET STRING (SIZE (0..255))
            DESCRIPTION
                    "The maximum size string returned by a read of
                    smRunArgument is 255 octets."

        VARIATION   smRunLifeTime
            DESCRIPTION
                    "It is not clear from the mib if smRunLifeTime starts
                    to tick backwards when smRunState equals 'initializing'
                    or when smRunState equals 'executing'.  This agent
                    implementation starts to decrement smRunLifeTime
                    when smRunState transitions to 'executing'."

        VARIATION   smRunExpireTime
            DESCRIPTION
                    "Unlike smRunLifeTime, the mib does not specify a
                    value for smRunExpireTime that can be used to
                    indicate this smRunEntry should be kept forever and
                    never aged out.  This agent uses the maximum value
                    (2147483647) to specify that this smRunEntry does not
                    age out after its smRunState transitions to
                    'terminated'.

                    If smRunExpireTime is set to its maximum value
                    (2147483647), either by a set operation or by its
                    initialization from the smLaunchExpireTime object,
                    then it does not tick backwards. A terminated script
                    with a maximum smRunExpireTime value thus is never
                    aged out and removed from the table."

        VARIATION   smRunResult
            SYNTAX  OCTET STRING (SIZE (0..255))
            DESCRIPTION
                    "The maximum size string returned by a read of
                    smRunResult is 255 octets."

        VARIATION   smRunControl
            SYNTAX  INTEGER {
                        abort       (1),
                        -- suspend  (2),
                        -- resume   (3),
                        nop         (4)
                    }
            DESCRIPTION
                    "The 'suspend (2)' and 'resume (3)' controls are not
                    supported.  An attempt to set either value results in
                    an 'inconsistentValue' error."

        VARIATION   smRunState
            SYNTAX  INTEGER {
                        initializing    (1),
                        executing       (2),
                        -- suspending   (3),
                        -- suspended    (4),
                        -- resuming     (5),
                        aborting        (6),
                        terminated      (7)
                    }
            DESCRIPTION
                    "The 'suspending (3)', 'suspended (4)', and 'resuming (5)'
                    states are not supported."

        VARIATION   smRunStartTime
            DESCRIPTION
                    "It is not clear from the mib if smRunStartTime is
                    set when smRunState transitions to 'initializing' or
                    not until smRunState transitions to 'executing'.
                    This agent implementation sets smRunStartTime when
                    smRunState transitions to 'executing'."

    ::= { tmnxSROSV10v0 46 }  -- CRON SCHEDULE & SCRIPT

--
--  TOD CAPABILITIES
--
tmnxSROSSchedulerCapsV10v0 AGENT-CAPABILITIES
    PRODUCT-RELEASE "Alcatel-Lucent SROS"
    STATUS current
    DESCRIPTION
        "Implementation of time of day (tod) policies on
         Alcatel-Lucent SROS release R10.0"

    SUPPORTS TIMETRA-SCHEDULER-MIB
        INCLUDES    {
            tmnxTodPolicyV5v0Group,
            tmnxCronSchedV5v0Group
        }
    ::= { tmnxSROSV10v0 47 }  -- TOD

--
--  GSMP CAPABILITIES
--
tmnxSROSGsmpCapsV10v0 AGENT-CAPABILITIES
    PRODUCT-RELEASE "Alcatel-Lucent SROS"
    STATUS current
    DESCRIPTION
        "Implementation of the General Switch Management Protocol (GSMP)
         and the Access Node Control Protocol (ANCP) on Alcatel-Lucent SROS
         release R10.0."

    SUPPORTS TIMETRA-GSMP-MIB
        INCLUDES    {
            tmnxGsmpV5v0Group,
            tmnxGsmpV5v0GNotificationGroup
        }

        VARIATION   tmnxGsmpCfgAdminState
            SYNTAX  INTEGER {
                        -- noop         (1),
                        inService       (2),
                        outOfService    (3)
                    }
            DESCRIPTION
                    "The only allowed values for tmnxGsmpCfgAdminState are
                    'inService (2)' and 'outOfService (3)'."

        VARIATION   tmnxGsmpGrpCfgAdminState
            SYNTAX  INTEGER {
                        -- noop         (1),
                        inService       (2),
                        outOfService    (3)
                    }
            DESCRIPTION
                    "The only allowed values for this object are
                    'inService (2)' and 'outOfService (3)'."

        VARIATION   tmnxGsmpGrpCfgAncpOamCap
            SYNTAX  INTEGER {
                        -- noop         (1),
                        inService       (2),
                        outOfService    (3)
                    }
            DESCRIPTION
                    "The only allowed values for this object are
                    'inService (2)' and 'outOfService (3)'."

        VARIATION   tmnxGsmpGrpCfgAncpDynTopoDiscCap
            SYNTAX  INTEGER {
                        -- noop         (1),
                        inService       (2),
                        outOfService    (3)
                    }
            DESCRIPTION
                    "The only allowed values for this object are
                    'inService (2)' and 'outOfService (3)'."

        VARIATION   tmnxGsmpGrpNbrAdminState
            SYNTAX  INTEGER {
                        -- noop         (1),
                        inService       (2),
                        outOfService    (3)
                    }
            DESCRIPTION
                    "The only allowed values for this object are
                    'inService (2)' and 'outOfService (3)'."

        VARIATION   tmnxGsmpGrpCfgRowStatus
            SYNTAX  INTEGER {
                        active      (1),
                        createAndGo (4),
                        destroy     (6)
                     }
            DESCRIPTION
                    "tmnxGsmpGrpCfgRowStatus supports only the values
                    'active (1)', 'createAndGo (4)' and 'destroy (6)'."

        VARIATION   tmnxGsmpGrpNbrRowStatus
            SYNTAX  INTEGER {
                        active      (1),
                        createAndGo (4),
                        destroy     (6)
                     }
            DESCRIPTION
                    "tmnxGsmpGrpNbrRowStatus supports only the values
                    'active (1)', 'createAndGo (4)' and 'destroy (6)'."

        VARIATION   tmnxAncpStaticMapSapRowStatus
            SYNTAX  INTEGER {
                        active      (1),
                        createAndGo (4),
                        destroy     (6)
                     }
            DESCRIPTION
                    "tmnxAncpStaticMapSapRowStatus supports only the values
                    'active (1)', 'createAndGo (4)' and 'destroy (6)'."

        VARIATION   tmnxAncpStaticMapMssRowStatus
            SYNTAX  INTEGER {
                        active      (1),
                        createAndGo (4),
                        destroy     (6)
                     }
            DESCRIPTION
                    "tmnxAncpStaticMapMssRowStatus supports only the values
                    'active (1)', 'createAndGo (4)' and 'destroy (6)'."

        VARIATION   tmnxAncpPlcyRowStatus
            SYNTAX  INTEGER {
                        active      (1),
                        createAndGo (4),
                        destroy     (6)
                     }
            DESCRIPTION
                    "tmnxAncpPlcyRowStatus supports only the values
                    'active (1)', 'createAndGo (4)' and 'destroy (6)'."

    ::= { tmnxSROSV10v0 48 }  -- GSMP

--
--  MC-REDUNDANCY CAPABILITIES
--
tmnxSROSMcRedundancyCapsV10v0 AGENT-CAPABILITIES
    PRODUCT-RELEASE "Alcatel-Lucent SROS"
    STATUS current
    DESCRIPTION
        "Implementation of the Multi-Chassis Redundancy feature
         on Alcatel-Lucent SROS release R10.0."

    SUPPORTS TIMETRA-MC-REDUNDANCY-MIB
        INCLUDES    {
            tmnxMcRedundancyV9v0Group,
            tmnxMcRedundancyV10v0Group,
            tmnxSrrpV5v0Group,
            tmnxSrrpV6v1Group,
-- EXCLUDE  tmnxSrrpNotifV6v1Group,           no support on SPR
            tmnxMcRedundancyV5v0NotifGroup,
            tmnxMcRedundancySrrpNotifGroup,
            tmnxMcRingV6v0Group,
            tmnxMcRingV6v0NotifGroup,
            tmnxMcPeerSyncGroup,
            tmnxMcsDhcpsV6v0Group,
            tmnxMcsSubHostTrkGroup,
            tmnxMcL3RingGroup,
            tmnxMcLagPbbGroup,
            tmnxMcPeerEPGroup,
            tmnxMcPeerEPNotifyObjsV7v0Group,
            tmnxMcPeerEPV7v0NotifGroup,
            tmnxMcRedBgpMultiHomeGroup,
            tmnxSrrpV8v0Group,
            tmnxSrrpV9v0Group,
            tmnxMcPeerNotifyObjsV10v0Group,
            tmnxMcPeerV10v0NotifGroup,
            tmnxMcTlsSapGroup
        }

        VARIATION   tmnxMcLagConfigPeerAdminstate
            SYNTAX  INTEGER {
                        -- noop         (1),
                        inService       (2),
                        outOfService    (3)
                    }
            DESCRIPTION
                    "The only allowed values for this object are 'inService (2)'
                    and 'outOfService (3)'."

        VARIATION   tmnxMcLagConfigLagRowStatus
            SYNTAX  INTEGER {
                        active      (1),
                        createAndGo (4),
                        destroy     (6)
                     }
            DESCRIPTION
                    "tmnxMcLagConfigLagRowStatus supports only the values
                    'active (1)', 'createAndGo (4)' and 'destroy (6)'."

        VARIATION   tmnxSrrpOperRowStatus
            SYNTAX  INTEGER {
                        active      (1),
                        createAndGo (4),
                        destroy     (6)
                     }
            DESCRIPTION
                    "tmnxSrrpOperRowStatus supports only the values
                    'active (1)', 'createAndGo (4)' and 'destroy (6)'."

        VARIATION   tmnxMcRingRowStatus
            SYNTAX  INTEGER {
                        active      (1),
                        createAndGo (4),
                        destroy     (6)
                    }
            DESCRIPTION
                    "tmnxMcRingRowStatus supports only the values
                    'active (1)', 'createAndGo (4)' and 'destroy (6)'."

        VARIATION   tmnxMcRingAdminState
            SYNTAX  INTEGER {
                        -- noop         (1),
                        inService       (2),
                        outOfService    (3)
                    }
            DESCRIPTION
                    "The only allowed values for this object are 'inService (2)'
                     and 'outOfService (3)'."

        VARIATION   tmnxMcRingNodeRowStatus
            SYNTAX  INTEGER {
                        active      (1),
                        createAndGo (4),
                        destroy     (6)
                    }
            DESCRIPTION
                    "tmnxMcRingNodeRowStatus supports only the values
                    'active (1)', 'createAndGo (4)' and 'destroy (6)'."

        VARIATION   tmnxMcRingNodeRncvAdminState
            SYNTAX  INTEGER {
                        -- noop      (1),
                        inService    (2),
                        outOfService (3)
                    }
            DESCRIPTION
                    "The only allowed values for this object are 'inService (2)'
                     and 'outOfService (3)'."

        VARIATION   tmnxMcEpipeSapRowStatus
            SYNTAX  INTEGER {
                        active      (1),
                        createAndGo (4),
                        destroy     (6)
                    }
            DESCRIPTION
                    "tmnxMcEpipeSapRowStatus supports only the values
                    'active (1)', 'createAndGo (4)' and 'destroy (6)'."

        VARIATION   tmnxMcRingInbCtrlDestIpType
            SYNTAX  INTEGER {
                        unknown     (0),
                        ipv4        (1)
                        -- ipv6     (2),
                        -- ipv4z    (3),
                        -- ipv6z    (4),
                        -- dns      (16)
                    }
            DESCRIPTION
                    "tmnxMcRingInbCtrlDestIpType supports only InetAddressType
                    values 'unknown (0)' and 'ipv4 (1)'."

        VARIATION   tmnxMcRingInbCtrlDestIp
            SYNTAX  InetAddress (SIZE (0|4))
            DESCRIPTION
                    "tmnxMcRingInbCtrlDestIp supports only InetAddressType
                    values 'unknown (0)' and 'ipv4 (1)'."

        VARIATION   tmnxMcRingInfoInbCtrlSrcIpType
            SYNTAX  INTEGER {
                        unknown     (0),
                        ipv4        (1)
                        -- ipv6     (2),
                        -- ipv4z    (3),
                        -- ipv6z    (4),
                        -- dns      (16)
                    }
            DESCRIPTION
                    "tmnxMcRingInfoInbCtrlSrcIpType supports only
                    InetAddressType values 'unknown (0)' and 'ipv4 (1)'."

        VARIATION   tmnxMcRingInfoInbCtrlSrcIp
            SYNTAX  InetAddress (SIZE (0|4))
            DESCRIPTION
                    "tmnxMcRingInfoInbCtrlSrcIp supports only InetAddressType
                    values 'unknown (0)' and 'ipv4 (1)'."

        VARIATION   tmnxMcRingNodeRncvSrcIpType
            SYNTAX  INTEGER {
                        unknown     (0),
                        ipv4        (1)
                        -- ipv6     (2),
                        -- ipv4z    (3),
                        -- ipv6z    (4),
                        -- dns      (16)
                    }
            DESCRIPTION
                    "tmnxMcRingNodeRncvSrcIpType supports only
                    InetAddressType values 'unknown (0)' and 'ipv4 (1)'."

        VARIATION   tmnxMcRingNodeRncvSrcIp
            SYNTAX  InetAddress (SIZE (0|4))
            DESCRIPTION
                    "tmnxMcRingNodeRncvSrcIp supports only InetAddressType
                    values 'unknown (0)' and 'ipv4 (1)'."

        VARIATION   tmnxMcRingNodeRncvDestIpType
            SYNTAX  INTEGER {
                        unknown     (0),
                        ipv4        (1)
                        -- ipv6     (2),
                        -- ipv4z    (3),
                        -- ipv6z    (4),
                        -- dns      (16)
                    }
            DESCRIPTION
                    "tmnxMcRingNodeRncvDestIpType supports only
                    InetAddressType values 'unknown (0)' and 'ipv4 (1)'."

        VARIATION   tmnxMcRingNodeRncvDestIp
            SYNTAX  InetAddress (SIZE (0|4))
            DESCRIPTION
                    "tmnxMcRingNodeRncvDestIp supports only InetAddressType
                    values 'unknown (0)' and 'ipv4 (1)'."

        VARIATION   tmnxMcTlsCfgDefGwIpType
            SYNTAX  INTEGER {
                        unknown     (0),
                        ipv4        (1)
                        -- ipv6     (2),
                        -- ipv4z    (3),
                        -- ipv6z    (4),
                        -- dns      (16)
                    }
            DESCRIPTION
                    "tmnxMcTlsCfgDefGwIpType supports only
                    InetAddressType values 'unknown (0)' and 'ipv4 (1)'."

        VARIATION   tmnxMcTlsCfgDefGwIp
            SYNTAX  InetAddress (SIZE (0|4))
            DESCRIPTION
                    "tmnxMcTlsCfgDefGwIp supports only InetAddressType
                    values 'unknown (0)' and 'ipv4 (1)'."

        VARIATION   tMcPeerIPsecTnlGrpPreempt
            SYNTAX  INTEGER {
                    -- true  (1)
                       false (2)
                    }
            DESCRIPTION
                    "tMcPeerIPsecTnlGrpPreempt supports only 'false (2)' value."

        VARIATION tMcPeerIPsecBfdEnableSvc
            SYNTAX       TmnxServId (0)
            DESCRIPTION
                "tMcPeerIPsecBfdEnableSvc supports only default value of zero."

        VARIATION tMcPeerIPsecBfdIntfIfName
            SYNTAX       TNamedItemOrEmpty
            DESCRIPTION
                "tMcPeerIPsecBfdIntfIfName supports only default value of ''H."

        VARIATION tMcPeerIPsecBfdIntfDestIpType
            SYNTAX       InetAddressType
            DESCRIPTION
                "tMcPeerIPsecBfdIntfDestIpType supports only default value of
                 'unknown'."

        VARIATION tMcPeerIPsecBfdIntfDestIp
            SYNTAX       InetAddress
            DESCRIPTION
                "tMcPeerIPsecBfdIntfDestIp supports only default value of ''H."

    ::= { tmnxSROSV10v0 49 }  -- MC-RED

tmnx7750McRedundancyCapsV10v0 AGENT-CAPABILITIES
    PRODUCT-RELEASE "Alcatel-Lucent SROS"
    STATUS current
    DESCRIPTION
        "Implementation of the Multi-Chassis Redundancy feature
         on Alcatel-Lucent 7750 release R10.0."

    SUPPORTS TIMETRA-MC-REDUNDANCY-MIB
        INCLUDES    {
            tmnxSrrpNotifV6v1Group
        }

    ::= { tmnxSROSMcRedundancyCapsV10v0 1 }  -- 7750 MC-RED

tmnx7450McRedundancyCapsV10v0 AGENT-CAPABILITIES
    PRODUCT-RELEASE "Alcatel-Lucent SROS"
    STATUS current
    DESCRIPTION
        "Implementation of the Multi-Chassis Redundancy feature
         on Alcatel-Lucent 7450 release R10.0."

    SUPPORTS TIMETRA-MC-REDUNDANCY-MIB
        INCLUDES    {
            tmnxSrrpNotifV6v1Group
        }

    ::= { tmnxSROSMcRedundancyCapsV10v0 2 }  -- 7450 MC-RED


tmnx7710McRedundancyCapsV10v0 AGENT-CAPABILITIES
    PRODUCT-RELEASE "Alcatel-Lucent SROS"
    STATUS current
    DESCRIPTION
        "Implementation of the Multi-Chassis Redundancy feature
         on Alcatel-Lucent SROS 7710 release R10.0."

    SUPPORTS TIMETRA-MC-REDUNDANCY-MIB
        INCLUDES    {
            tmnxMcLagPbbGroup
        }

        VARIATION   tmnxMcLagConfigLagSrcBMacLSB
            ACCESS  not-implemented
            DESCRIPTION
                "tmnxMcLagConfigLagSrcBMacLSB is not implemented on
                 Alcatel-Lucent 7710 systems."

    ::= { tmnxSROSMcRedundancyCapsV10v0 3 }  -- 7710 MC-RED


tmnxMobGwMcRedundancyCapsV10v0 AGENT-CAPABILITIES
    PRODUCT-RELEASE "Alcatel-Lucent SROS"
    STATUS current
    DESCRIPTION
        "Implementation of the Mobile Gw Multi-Chassis Redundancy feature
         on Alcatel-Lucent SROS 7xxx release R10.0."

    SUPPORTS TIMETRA-MC-REDUNDANCY-MIB
        INCLUDES    {
            tmnxMcMobRedundancyV4v0Group            
        }

        VARIATION   tmnxMcMobRedundancyV4v0Group 
            ACCESS  not-implemented
            DESCRIPTION
                "tmnxMcMobRedundancyV4v0Group is not implemented on
                 Alcatel-Lucent 7xxx systems."

    ::= { tmnxSROSMcRedundancyCapsV10v0 4 }  -- 7710 MC-RED

--
--    Multicast CAC CAPABILITIES
--
tmnxSROSMCastCACCapsV10v0 AGENT-CAPABILITIES
     PRODUCT-RELEASE "Alcatel-Lucent SROS"
     STATUS          current
     DESCRIPTION     "Implementation of the Multi-cast CAC (connection access
                      control) feature on Alcatel-Lucent SROS release R10.0."

     SUPPORTS TIMETRA-MCAST-CAC-MIB
         INCLUDES    {
            tmnxMcacV5v0Group,
            tmnxMcacStatV5v0Group,
            tmnxMcacOperV5v0Group,
            tmnxMcacPolicyUserV5v0Group
         }

         VARIATION   tmnxMcacBdlChlStartAddrType
            SYNTAX  INTEGER {
                        -- unknown  (0),
                        ipv4        (1)
                        -- ipv6     (2),
                        -- ipv4z    (3),
                        -- ipv6z    (4),
                        -- dns      (16)
                    }
             DESCRIPTION
                     "tmnxMcacBdlChlStartAddrType supports only InetAddressType
                     'ipv4 (1)'."

         VARIATION   tmnxMcacBdlChlStartAddr
             SYNTAX  InetAddress (SIZE (4))
             DESCRIPTION
                     "tmnxMcacBdlChlStartAddr supports only InetAddressType
                     'ipv4 (1)'."

         VARIATION   tmnxMcacBdlChlEndAddrType
             SYNTAX  INTEGER {
                        -- unknown  (0),
                        ipv4        (1)
                        -- ipv6     (2),
                        -- ipv4z    (3),
                        -- ipv6z    (4),
                        -- dns      (16)
                     }
             DESCRIPTION
                     "tmnxMcacBdlChlEndAddrType supports only InetAddressType
                     'ipv4 (1)'."

         VARIATION   tmnxMcacBdlChlEndAddr
             SYNTAX  InetAddress (SIZE (4))
             DESCRIPTION
                     "tmnxMcacBdlChlEndAddr supports only InetAddressType
                     'ipv4 (1)'."

    ::= { tmnxSROSV10v0 50 }  -- MCAC

--
--  MSDP CAPABILITIES
--
tmnxSROSMsdpCapsV10v0    AGENT-CAPABILITIES
    PRODUCT-RELEASE "Alcatel-Lucent SROS"
    STATUS          current
    DESCRIPTION     "Implementation of MSDP protocol capabilities
                     for Alcatel-Lucent SROS release R10.0"

    SUPPORTS        MSDP-MIB
        INCLUDES    {
            msdpMIBGlobalsGroup,
            msdpMIBEncapsulationGroup,
            msdpMIBSACacheGroup,
            msdpMIBNotificationGroup,
            msdpMIBRPGroup,
            msdpMIBMeshGroupGroup,
            msdpMIBPeerGroup2
        }
        VARIATION   msdpEnabled
            ACCESS  read-only
            DESCRIPTION
                    "msdpEnabled is implemented as read-only."

        VARIATION   msdpCacheLifetime
            ACCESS  read-only
            DESCRIPTION
                    "msdpCacheLifetime is implemented as read-only."

        VARIATION   msdpRPAddress
            ACCESS  read-only
            DESCRIPTION
                    "msdpRPAddress is implemented as read-only."

        VARIATION   msdpPeerLocalAddress
            ACCESS  read-only
            DESCRIPTION
                    "msdpPeerLocalAddress is implemented as read-only."

        VARIATION   msdpPeerConnectRetryInterval
            ACCESS  read-only
            DESCRIPTION
                    "msdpPeerConnectRetryInterval is implemented as read-only."

        VARIATION   msdpPeerHoldTimeConfigured
            ACCESS  read-only
            DESCRIPTION
                    "msdpPeerHoldTimeConfigured is implemented as read-only."

        VARIATION   msdpPeerKeepAliveConfigured
            ACCESS  read-only
            DESCRIPTION
                    "msdpPeerKeepAliveConfigured is implemented as read-only."

        VARIATION   msdpPeerDataTtl
            ACCESS  read-only
            DESCRIPTION
                    "msdpPeerDataTtl is implemented as read-only."

        VARIATION   msdpPeerStatus
            ACCESS  read-only
            DESCRIPTION
                    "msdpPeerStatus is implemented as read-only."

        VARIATION   msdpPeerEncapsulationType
            ACCESS  read-only
            DESCRIPTION
                    "msdpPeerEncapsulationType is implemented as read-only."

        VARIATION   msdpSACacheStatus
            ACCESS  read-only
            DESCRIPTION
                    "msdpSACacheStatus is implemented as read-only."

        VARIATION   msdpMeshGroupStatus
            ACCESS  read-only
            DESCRIPTION
                    "msdpMeshGroupStatus is implemented as read-only."

    SUPPORTS        TIMETRA-MSDP-MIB
        INCLUDES    {
            tmnxMsdpGlobalGroup,
            tmnxMsdpPeerGroup,
            tmnxMsdpPeerGroupGroup,
            tmnxMsdpSourceGroup,
            tmnxMsdpSrcActiveGroup,
            tmnxMsdpSrcActiveRejGroup,
            tmnxMsdpNotificationGroup
        }

        VARIATION   tmnxMsdpLocalAddressType
            SYNTAX  INTEGER {
                        unknown     (0),
                        ipv4        (1)
                        -- ipv6     (2),
                        -- ipv4z    (3),
                        -- ipv6z    (4),
                        -- dns      (16)
                    }
            DESCRIPTION
                    "tmnxMsdpLocalAddressType supports only InetAddressType
                    values 'unknown (0)' and 'ipv4 (1)'."

        VARIATION   tmnxMsdpLocalAddress
            SYNTAX     InetAddress (SIZE (0|4))
            DESCRIPTION
                    "tmnxMsdpLocalAddress supports only InetAddressType
                    values 'unknown (0)' and 'ipv4 (1)'."

        VARIATION   tmnxMsdpPeerAddressType
            SYNTAX  INTEGER {
                        --unknown     (0),
                        ipv4        (1)
                        -- ipv6     (2),
                        -- ipv4z    (3),
                        -- ipv6z    (4),
                        -- dns      (16)
                    }
            DESCRIPTION
                    "tmnxMsdpPeerAddressType supports only InetAddressType
                    'ipv4 (1)'."

        VARIATION   tmnxMsdpPeerAddress
            SYNTAX  InetAddress (SIZE (4))
            DESCRIPTION
                    "tmnxMsdpPeerAddress supports only InetAddressType
                    'ipv4 (1)'."

        VARIATION   tmnxMsdpPeerLocalAddressType
            SYNTAX  INTEGER {
                        unknown     (0),
                        ipv4        (1)
                        -- ipv6     (2),
                        -- ipv4z    (3),
                        -- ipv6z    (4),
                        -- dns      (16)
                    }
            DESCRIPTION
                    "tmnxMsdpPeerLocalAddressType supports only
                    InetAddressType values 'unknown (0)' and 'ipv4 (1)'."

        VARIATION   tmnxMsdpPeerLocalAddress
            SYNTAX  InetAddress (SIZE (0|4))
            DESCRIPTION
                    "tmnxMsdpPeerLocalAddress supports only InetAddressType
                    values 'unknown (0)' and 'ipv4 (1)'."

        VARIATION   tmnxMsdpPeerGroupLocalAddrType
            SYNTAX  INTEGER {
                        unknown     (0),
                        ipv4        (1)
                        -- ipv6     (2),
                        -- ipv4z    (3),
                        -- ipv6z    (4),
                        -- dns      (16)
                    }
            DESCRIPTION
                    "tmnxMsdpPeerGroupLocalAddrType supports only
                    InetAddressType values 'unknown (0)' and 'ipv4 (1)'."

        VARIATION   tmnxMsdpPeerGroupLocalAddress
            SYNTAX  InetAddress (SIZE (0|4))
            DESCRIPTION
                    "tmnxMsdpPeerGroupLocalAddress supports only
                    InetAddressType values 'unknown (0)' and 'ipv4 (1)'."

        VARIATION   tmnxMsdpPeerGrpPeerAddressType
            SYNTAX  INTEGER {
                        -- unknown  (0),
                        ipv4        (1)
                        -- ipv6     (2),
                        -- ipv4z    (3),
                        -- ipv6z    (4),
                        -- dns      (16)
                    }
            DESCRIPTION
                    "tmnxMsdpPeerGrpPeerAddressType supports only
                    InetAddressType 'ipv4 (1)'."

        VARIATION   tmnxMsdpPeerGrpPeerAddress
            SYNTAX  InetAddress (SIZE (4))
            DESCRIPTION
                    "tmnxMsdpPeerGrpPeerAddress supports only InetAddressType
                    'ipv4 (1)'."

        VARIATION   tmnxMsdpPeerGrpPeerLocAddrType
            SYNTAX  INTEGER {
                        unknown     (0),
                        ipv4        (1)
                        -- ipv6     (2),
                        -- ipv4z    (3),
                        -- ipv6z    (4),
                        -- dns      (16)
                    }
            DESCRIPTION
                    "The tmnxMsdpPeerGrpPeerLocAddrType supports only
                    InetAddressType values'unknown (0)' and 'ipv4 (1)'."

        VARIATION   tmnxMsdpPeerGrpPeerLocalAddress
            SYNTAX  InetAddress (SIZE (0|4))
            DESCRIPTION
                    "tmnxMsdpPeerGrpPeerLocalAddress supports only
                    InetAddressType values 'unknown (0)' and 'ipv4 (1)'."

        VARIATION   tmnxMsdpSourcePrefixType
            SYNTAX  INTEGER {
                        -- unknown  (0),
                        ipv4        (1)
                        -- ipv6     (2),
                        -- ipv4z    (3),
                        -- ipv6z    (4),
                        -- dns      (16)
                    }
            DESCRIPTION
                    "tmnxMsdpSourcePrefixType supports only InetAddressType
                    'ipv4 (1)'."

        VARIATION   tmnxMsdpSourcePrefix
            SYNTAX  InetAddress (SIZE (4))
            DESCRIPTION
                    "tmnxMsdpSourcePrefix supports only InetAddressType
                    'ipv4 (1)'."

    ::= { tmnxSROSV10v0 51 }  -- MSDP

--
--  EFM OAM CAPABILITIES
--
tmnxSROSDot3OamCapsV10v0    AGENT-CAPABILITIES
    PRODUCT-RELEASE "Alcatel-Lucent SROS"
    STATUS          current
    DESCRIPTION     "Implementation of Ethernet OAM (802.3ah) capabilities
                     for Alcatel-Lucent SROS release R10.0"

    SUPPORTS        DOT3-OAM-MIB
        INCLUDES    {
            dot3OamControlGroup,
            dot3OamPeerGroup,
            dot3OamStatsBaseGroup,
            dot3OamLoopbackGroup,
            dot3OamEventLogGroup,
            dot3OamNotificationGroup
        }

        VARIATION    dot3OamEventLogWindowHi
            ACCESS   not-implemented
            DESCRIPTION
                 "dot3OamEventLogWindowHi is not implemented on the
                  Alcatel-Lucent SROS release R10.0"

        VARIATION    dot3OamEventLogWindowLo
            ACCESS   not-implemented
            DESCRIPTION
                 "dot3OamEventLogWindowLo is not implemented on the
                  Alcatel-Lucent SROS release R10.0"

        VARIATION    dot3OamEventLogThresholdHi
            ACCESS   not-implemented
            DESCRIPTION
                 "dot3OamEventLogThresholdHi is not implemented on the
                  Alcatel-Lucent SROS release R10.0"

        VARIATION    dot3OamEventLogThresholdLo
            ACCESS   not-implemented
            DESCRIPTION
                 "dot3OamEventLogThresholdLo is not implemented on the
                  Alcatel-Lucent SROS release R10.0"

        VARIATION    dot3OamEventLogValue
            ACCESS   not-implemented
            DESCRIPTION
                 "dot3OamEventLogValue is not implemented on the
                  Alcatel-Lucent SROS release R10.0"

        VARIATION    dot3OamEventLogRunningTotal
            ACCESS   not-implemented
            DESCRIPTION
                 "dot3OamEventLogRunningTotal is not implemented on the
                  Alcatel-Lucent SROS release R10.0"

        VARIATION    dot3OamThresholdEvent
            ACCESS   not-implemented
            DESCRIPTION
                 "This NOTIFICATION-TYPE is not implemented on the
                  Alcatel-Lucent SROS release R10.0"

    SUPPORTS        TIMETRA-DOT3-OAM-MIB
        INCLUDES    {
            tmnxDot3OamV6v0Group,
            tmnxDot3OamV6v1Group,
            tmnxDot3OamLoopbackGroup,
            tmnxDot3OamNotificationV6v0Group
        }

    ::= { tmnxSROSV10v0 52 }  -- DOT3-OAM

--
--  MLD SNOOPING CAPABILITIES
--
tmnxSROSMldSnoopingCapsV10v0    AGENT-CAPABILITIES
    PRODUCT-RELEASE "Alcatel-Lucent SROS"
    STATUS          current
    DESCRIPTION     "Implementation of MLD snooping capabilities
                     for Alcatel-Lucent SROS release R10.0"

    SUPPORTS        TIMETRA-MLD-SNOOPING-MIB
        INCLUDES    {
            tmnxMldSnpgConfigGroup,
            tmnxMldSnpgQuerierGroup,
            tmnxMldSnpgProxyGroup,
            tmnxMldSnpgMRouterGroup,
            tmnxMldMvrGroup,
            tmnxMldSnpgGroup,
            tmnxMldSnpgStaticGroup,
            tmnxMldSnpgStatsGroup,
            tmnxMldSnpgNotifyGroup,
            tmnxMldSnpgConfigV8v0Group
        }

        VARIATION   tlsMldSnpgCfgAdminState
            SYNTAX  INTEGER {
                        -- noop         (1),
                        inService       (2),
                        outOfService    (3)
                    }
            DESCRIPTION
                    "The only allowed values for this object are 'inService (2)'
                     and 'outOfService (3)'."

        VARIATION   tlsMldSnpgCfgMvrAdminState
            SYNTAX  INTEGER {
                        -- noop         (1),
                        inService       (2),
                        outOfService    (3)
                    }
            DESCRIPTION
                    "The only allowed values for this object are 'inService (2)'
                     and 'outOfService (3)'."

        VARIATION   tlsMldSnpgCfgReportSrcAddrType
            SYNTAX  INTEGER {
                        unknown     (0),
                        -- ipv4     (1),
                        ipv6        (2)
                        -- ipv4z    (3),
                        -- ipv6z    (4),
                        -- dns      (16)
                    }
            DESCRIPTION
                    "Only values 'ipv6 (2)' or 'unknown (0)' are supported."

        VARIATION   tlsMldSnpgCfgReportSrcAddr
            SYNTAX  InetAddress (SIZE (0|16))
            DESCRIPTION
                    "Only an IP address of type 'ipv6 (2)'
                     or a zero-length string are supported."

        VARIATION   tlsMldSnpgQuerierAddressType
            SYNTAX  INTEGER {
                        -- unknown  (0),
                        -- ipv4     (1),
                        ipv6        (2)
                        -- ipv4z    (3),
                        -- ipv6z    (4),
                        -- dns      (16)
                    }
            DESCRIPTION
                    "Only value 'ipv6 (2)' is supported."

        VARIATION   tlsMldSnpgQuerierAddress
            SYNTAX  InetAddress (SIZE (16))
            DESCRIPTION
                    "Only an IP address of type 'ipv6 (2)' is supported."

        VARIATION   tlsMldSnpgProxyGroupAddressType
            SYNTAX  INTEGER {
                        -- unknown  (0),
                        -- ipv4     (1),
                        ipv6        (2)
                        -- ipv4z    (3),
                        -- ipv6z    (4),
                        -- dns      (16)
                    }
            DESCRIPTION
                    "Only value 'ipv6 (2)' is supported."

        VARIATION   tlsMldSnpgProxyGroupAddress
            SYNTAX  InetAddress (SIZE (16))
            DESCRIPTION
                    "Only an IP address of type 'ipv6 (2)' is supported."

        VARIATION   tlsMldSnpgProxyGrpSrcAddrTp
            SYNTAX  INTEGER {
                        -- unknown  (0),
                        -- ipv4     (1),
                        ipv6        (2)
                        -- ipv4z    (3),
                        -- ipv6z    (4),
                        -- dns      (16)
                    }
            DESCRIPTION
                    "Only value 'ipv6 (2)' is supported."

        VARIATION   tlsMldSnpgProxyGrpSrcAddr
            SYNTAX  InetAddress (SIZE (16))
            DESCRIPTION
                    "Only an IP address of type 'ipv6 (2)' is supported."

        VARIATION   tlsMldSnpgMRouterAddressType
            SYNTAX  INTEGER {
                        -- unknown  (0),
                        -- ipv4     (1),
                        ipv6        (2)
                        -- ipv4z    (3),
                        -- ipv6z    (4),
                        -- dns      (16)
                    }
            DESCRIPTION
                    "Only value 'ipv6 (2)' is supported."

        VARIATION   tlsMldSnpgMRouterAddress
            SYNTAX  InetAddress (SIZE (16))
            DESCRIPTION
                    "Only an IP address of type 'ipv6 (2)' is supported."

        VARIATION   sapMldSnpgCfgFastLeave
            SYNTAX  INTEGER {
                        -- noop         (1),
                        inService       (2),
                        outOfService    (3)
                    }
            DESCRIPTION
                    "The only allowed values for this object are 'inService (2)'
                     and 'outOfService (3)'."

        VARIATION   sapMldSnpgCfgSendQueries
            SYNTAX  INTEGER {
                        -- noop         (1),
                        inService       (2),
                        outOfService    (3)
                    }
            DESCRIPTION
                    "The only allowed values for this object are 'inService (2)'
                     and 'outOfService (3)'."

        VARIATION   sapMldSnpgGrpAddressType
            SYNTAX  INTEGER {
                        -- unknown  (0),
                        -- ipv4     (1),
                        ipv6        (2)
                        -- ipv4z    (3),
                        -- ipv6z    (4),
                        -- dns      (16)
                    }
            DESCRIPTION
                    "Only value 'ipv6 (2)' is supported."

        VARIATION   sapMldSnpgGrpAddress
            SYNTAX  InetAddress (SIZE (16))
            DESCRIPTION
                    "Only an IP address of type 'ipv6 (2)' is supported."

        VARIATION   sapMldSnpgGrpSrcAddrType
            SYNTAX  INTEGER {
                        -- unknown  (0),
                        -- ipv4     (1),
                        ipv6        (2)
                        -- ipv4z    (3),
                        -- ipv6z    (4),
                        -- dns      (16)
                    }
            DESCRIPTION
                    "Only value 'ipv6 (2)' is supported."

        VARIATION   sapMldSnpgGrpSrcAddr
            SYNTAX  InetAddress (SIZE (16))
            DESCRIPTION
                    "Only an IP address of type 'ipv6 (2)' is supported."

        VARIATION   sapMldSnpgStaticGroupAddrType
            SYNTAX  INTEGER {
                        -- unknown  (0),
                        -- ipv4     (1),
                        ipv6        (2)
                        -- ipv4z    (3),
                        -- ipv6z    (4),
                        -- dns      (16)
                    }
            DESCRIPTION
                    "Only value 'ipv6 (2)' is supported."

        VARIATION   sapMldSnpgStaticGroupAddr
            SYNTAX  InetAddress (SIZE (16))
            DESCRIPTION
                    "Only an IP address of type 'ipv6 (2)' is supported."

        VARIATION   sapMldSnpgStaticSourceAddrType
            SYNTAX  INTEGER {
                        -- unknown  (0),
                        -- ipv4     (1),
                        ipv6        (2)
                        -- ipv4z    (3),
                        -- ipv6z    (4),
                        -- dns      (16)
                    }
            DESCRIPTION
                    "Only value 'ipv6 (2)' is supported."

        VARIATION   sapMldSnpgStaticSourceAddr
            SYNTAX  InetAddress (SIZE (16))
            DESCRIPTION
                    "Only an IP address of type 'ipv6 (2)' is supported."

        VARIATION   sdpBndMldSnpgCfgFastLeave
            SYNTAX  INTEGER {
                        -- noop         (1),
                        inService       (2),
                        outOfService    (3)
                    }
            DESCRIPTION
                    "The only allowed values for this object are 'inService (2)'
                     and 'outOfService (3)'."

        VARIATION   sdpBndMldSnpgCfgSendQueries
            SYNTAX  INTEGER {
                        -- noop         (1),
                        inService       (2),
                        outOfService    (3)
                    }
            DESCRIPTION
                    "The only allowed values for this object are 'inService (2)'
                     and 'outOfService (3)'."

        VARIATION   sdpBndMldSnpgGrpAddressType
            SYNTAX  INTEGER {
                        -- unknown  (0),
                        -- ipv4     (1),
                        ipv6        (2)
                        -- ipv4z    (3),
                        -- ipv6z    (4),
                        -- dns      (16)
                    }
            DESCRIPTION
                    "Only value 'ipv6 (2)' is supported."

        VARIATION   sdpBndMldSnpgGrpAddress
            SYNTAX  InetAddress (SIZE (16))
            DESCRIPTION
                    "Only an IP address of type 'ipv6 (2)' is supported."

        VARIATION   sdpBndMldSnpgGrpSrcAddrType
            SYNTAX  INTEGER {
                        -- unknown  (0),
                        -- ipv4     (1),
                        ipv6        (2)
                        -- ipv4z    (3),
                        -- ipv6z    (4),
                        -- dns      (16)
                    }
            DESCRIPTION
                    "Only value 'ipv6 (2)' is supported."

        VARIATION   sdpBndMldSnpgGrpSrcAddr
            SYNTAX  InetAddress (SIZE (16))
            DESCRIPTION
                    "Only an IP address of type 'ipv6 (2)' is supported."

        VARIATION   sdpBndMldSnpgStaticGroupAddrType
            SYNTAX  INTEGER {
                        -- unknown  (0),
                        -- ipv4     (1),
                        ipv6        (2)
                        -- ipv4z    (3),
                        -- ipv6z    (4),
                        -- dns      (16)
                    }
            DESCRIPTION
                    "Only value 'ipv6 (2)' is supported."

        VARIATION   sdpBndMldSnpgStaticGroupAddr
            SYNTAX  InetAddress (SIZE (16))
            DESCRIPTION
                    "Only an IP address of type 'ipv6 (2)' is supported."

        VARIATION   sdpBndMldSnpgStaticSourceAddrTp
            SYNTAX  INTEGER {
                        -- unknown  (0),
                        -- ipv4     (1),
                        ipv6        (2)
                        -- ipv4z    (3),
                        -- ipv6z    (4),
                        -- dns      (16)
                    }
            DESCRIPTION
                    "Only value 'ipv6 (2)' is supported."

        VARIATION   sdpBndMldSnpgStaticSourceAddr
            SYNTAX  InetAddress (SIZE (16))
            DESCRIPTION
                    "Only an IP address of type 'ipv6 (2)' is supported."

    ::= { tmnxSROSV10v0 53 }  -- MLD-SNOOPING

--
--  IPsec CAPABILITIES
--
tmnxSROSIPsecCapsV10v0    AGENT-CAPABILITIES
    PRODUCT-RELEASE "Alcatel-Lucent SROS"
    STATUS          current
    DESCRIPTION     "Implementation of IPsec tunneling, encryption and
                     other related features capabilities for Alcatel-Lucent SROS
                     release R10.0"
    SUPPORTS        TIMETRA-IPSEC-MIB
        INCLUDES    {
            tmnxIPsecV6v0Group,
            tmnxIPsecMdaDpStatsV6v1Group,
            tIPsecTnlTempGroup,
            tmnxIPsecTnlBfdGroup,
            tmnxIPsecNotifGroup,
            tmnxIPsecNotifyObjsGroup,
            tmnxIPsecGWV10v0Group,
            tmnxIPsecCertGroup,
            tmnxIPsecIkeGroup,
            tmnxIPsecMdaDpGroup,
            tmnxIPsecV10v0Group,
            tmnxIPsecMdaDpStatsV10v0Group
        }

        VARIATION   tmnxIPsecTransformRowStatus
            SYNTAX  INTEGER {
                        active      (1),
                        createAndGo (4),
                        destroy     (6)
                     }
            DESCRIPTION
                    "tmnxIPsecTransformRowStatus supports only the values
                    'active (1)', 'createAndGo (4)' and 'destroy (6)'."

        VARIATION   tmnxIkePolicyRowStatus
            SYNTAX  INTEGER {
                        active      (1),
                        createAndGo (4),
                        destroy     (6)
                     }
            DESCRIPTION
                    "tmnxIkePolicyRowStatus supports only the values
                    'active (1)', 'createAndGo (4)' and 'destroy (6)'."

        VARIATION   tmnxIkePolicyAuthAlgorithm
            SYNTAX  INTEGER {
                        md5      (2),
                        sha1     (3)
                     }
            DESCRIPTION
                    "tmnxIkePolicyAuthAlgorithm supports only the values
                    'md5 (1)' and 'sha1 (3)'."

        VARIATION   tmnxIkePolicyEncrAlgorithm
            SYNTAX  INTEGER {
                        des    (2),
                        des3   (3),
                        aes128 (4),
                        aes192 (5),
                        aes256 (6)
                      }
            DESCRIPTION
                    "tmnxIkePolicyEncrAlgorithm supports only the values
                    'des (2)', 'des3 (3)', 'aes128 (4)', 'aes192 (5)' and
                    'aes256 (6)'."

        VARIATION   tmnxIPsecTunnelRowStatus
            SYNTAX  INTEGER {
                        active      (1),
                        createAndGo (4),
                        destroy     (6)
                     }
            DESCRIPTION
                    "tmnxIPsecTunnelRowStatus supports only the values
                    'active (1)', 'createAndGo (4)' and 'destroy (6)'."

        VARIATION   tmnxIPsecTunnelLclGwAddrType
            SYNTAX  INTEGER {
                        unknown     (0),
                        ipv4        (1)
                        -- ipv6     (2),
                        -- ipv4z    (3),
                        -- ipv6z    (4),
                        -- dns      (16)
                    }
            DESCRIPTION
                    "tmnxIPsecTunnelLclGwAddrType supports only InetAddressType
                    values 'unknown (0)' and 'ipv4 (1)'."

        VARIATION   tmnxIPsecTunnelLclGwAddr
            SYNTAX  InetAddress (SIZE (0|4))
            DESCRIPTION
                    "tmnxIPsecTunnelLclGwAddr supports only InetAddressType
                    values 'unknown (0)' and 'ipv4 (1)'."

        VARIATION   tmnxIPsecTunnelRemGwAddrType
            SYNTAX  INTEGER {
                        unknown     (0),
                        ipv4        (1)
                        -- ipv6     (2),
                        -- ipv4z    (3),
                        -- ipv6z    (4),
                        -- dns      (16)
                    }
            DESCRIPTION
                    "tmnxIPsecTunnelRemGwAddrType supports only InetAddressType
                    values 'unknown (0)' and 'ipv4 (1)'."

        VARIATION   tmnxIPsecTunnelRemGwAddr
            SYNTAX  InetAddress (SIZE (0|4))
            DESCRIPTION
                    "tmnxIPsecTunnelRemGwAddr supports only InetAddressType
                    values 'unknown (0)' and 'ipv4 (1)'."

        VARIATION   tmnxIPsecPolicyRowStatus
            SYNTAX  INTEGER {
                        active      (1),
                        createAndGo (4),
                        destroy     (6)
                     }
            DESCRIPTION
                    "tmnxIPsecPolicyRowStatus supports only the values
                    'active (1)', 'createAndGo (4)' and 'destroy (6)'."

        VARIATION   tmnxIPsecPolicyParamsRowStatus
            SYNTAX  INTEGER {
                        active      (1),
                        createAndGo (4),
                        destroy     (6)
                     }
            DESCRIPTION
                    "The tmnxIPsecPolicyParamsRowStatus supports only the
                     values 'active(1)', 'createAndGo(4)' and 'destroy(6)'."

        VARIATION   tmnxIPsecPolicyParamsLclAddrType
            SYNTAX  INTEGER {
                        unknown     (0),
                        ipv4        (1)
                        -- ipv6     (2),
                        -- ipv4z    (3),
                        -- ipv6z    (4),
                        -- dns      (16)
                    }
            DESCRIPTION
                    "tmnxIPsecPolicyParamsLclAddrType supports only
                    InetAddressType values 'unknown (0)' and 'ipv4 (1)'."

        VARIATION   tmnxIPsecPolicyParamsLclAddr
            SYNTAX  InetAddress (SIZE (0|4))
            DESCRIPTION
                    "tmnxIPsecPolicyParamsLclAddr supports only InetAddressType
                    values 'unknown (0)' and 'ipv4 (1)'."

        VARIATION   tmnxIPsecPolicyParamsLclAPrefLen
            SYNTAX  Unsigned32 (0..32)
            DESCRIPTION
                    "The tmnxIPsecPolicyParamsLclAPrefLen supports values
                     between 0 and 32 and setting to any other value
                     results in an 'inconsistentValue' error."

        VARIATION   tmnxIPsecPolicyParamsRemAddrType
            SYNTAX  INTEGER {
                        unknown     (0),
                        ipv4        (1)
                        -- ipv6     (2),
                        -- ipv4z    (3),
                        -- ipv6z    (4),
                        -- dns      (16)
                    }
            DESCRIPTION
                    "tmnxIPsecPolicyParamsRemAddrType supports only
                    InetAddressType values 'unknown (0)' and 'ipv4 (1)'."

        VARIATION   tmnxIPsecPolicyParamsRemAddr
            SYNTAX  InetAddress (SIZE (0|4))
            DESCRIPTION
                    "tmnxIPsecPolicyParamsRemAddr supports only InetAddressType
                    values 'unknown (0)' and 'ipv4 (1)'."

        VARIATION   tmnxIPsecPolicyParamsRemAPrefLen
            SYNTAX  Unsigned32 (0..32)
            DESCRIPTION
                    "tmnxIPsecPolicyParamsRemAPrefLen supports values
                     between 0 and 32 and setting to any other value
                     results in an 'inconsistentValue' error."

        VARIATION   tmnxIPsecTunnelAdminState
            SYNTAX  INTEGER {
                        -- noop         (1),
                        inService       (2),
                        outOfService    (3)
                    }
            DESCRIPTION
                    "tmnxIPsecTunnelAdminState supports only
                     'inService(2)' and 'outOfService(3)'."

        VARIATION   tIPsecRUTnlInetAddrType
            SYNTAX  INTEGER {
                        ipv4        (1)
                        -- unknown     (0),
                        -- ipv6     (2),
                        -- ipv4z    (3),
                        -- ipv6z    (4),
                        -- dns      (16)
                    }
            DESCRIPTION
                    "tIPsecRUTnlInetAddrType supports only
                    InetAddressType value 'ipv4 (1)'."

        VARIATION   tIPsecRUTnlInetAddress
            SYNTAX          InetAddress (SIZE(4))
            DESCRIPTION
                    "tIPsecRUTnlInetAddress supports only
                    InetAddressType value 'ipv4 (1)'."

        VARIATION   tmnxIkePolicyAuthMethod
            SYNTAX  INTEGER {
                        psk           (1),
                        plainPskXAuth (4)
                    }
            DESCRIPTION
                 "tmnxIkePolicyAuthMethod supports only 'psk (1)' and
                 'plainPskXAuth (4)'."

        VARIATION   tIPsecTnlTempReverseRoute
            SYNTAX  INTEGER {
                            none              (0),
                            -- reverseRoute      (1),
                            useSecurityPolicy (2)
                    }
            DESCRIPTION
                    "tIPsecTnlTempReverseRoute supports only
                    'none(0)' and 'useSecurityPolicy (2)'."

    ::= { tmnxSROSV10v0 54 }  -- IPSEC

tmnx7450IPsecCapsV10v0    AGENT-CAPABILITIES
    PRODUCT-RELEASE "Alcatel-Lucent SROS"
    STATUS          current
    DESCRIPTION     "Implementation of specific IPsec tunneling, encryption and
                     other related feature capabilities for Alcatel-Lucent SROS
                     7450 release R10.0."

--    SUPPORTS        TIMETRA-IPSEC-MIB
--        INCLUDES    {
--        }

-- IPSEC is not supported on the SROS 7450 platform.

    ::= { tmnxSROSIPsecCapsV10v0 1 }  -- 7450 IPSEC


tmnxSprIPsecCapsV10v0    AGENT-CAPABILITIES
    PRODUCT-RELEASE "Alcatel-Lucent SROS"
    STATUS          current
    DESCRIPTION     "Implementation of specific IPsec tunneling, encryption and
                     other related feature capabilities for Alcatel-Lucent SROS
                     SPR release R10.0."

--    SUPPORTS        TIMETRA-IPSEC-MIB
--        INCLUDES    {
--        }

-- IPSEC is not supported on the SROS SPR platform.

    ::= { tmnxSROSIPsecCapsV10v0 2 }  -- SPR IPSEC

--
--  DHCP SERVER CAPABILITIES
--
tmnxSROSDhcpServerCapsV10v0    AGENT-CAPABILITIES
    PRODUCT-RELEASE "Alcatel-Lucent SROS"
    STATUS          current
    DESCRIPTION     "Implementation of DHCP server capabilities
                     for Alcatel-Lucent SROS release R10.0"

    SUPPORTS        TIMETRA-DHCP-SERVER-MIB
        INCLUDES    {
            tmnxDhcpServerV8v0Group,
            tmnxDhcpServerV9v0Group,
            tmnxDhcpServerV10v0Group,
            tmnxDhcpLeaseGroup,
            tmnxDhcpStatsV8v0Group,
            tmnxDhcpStatsV9v0Group,
            tmnxDhcpAddrListGroup,
            tmnxDhcpToolsGroup,
            tmnxDhcpsFailoverGroup,
            tmnxDhcpSvrFoNotifGroup,
            tmnxDhcpSvrNotifGroup,
            tmnxDhcpSvrNotifV10v0Group
        }

        VARIATION   tmnxDhcpServerCfgAdminState
            SYNTAX  INTEGER {
                        -- noop         (1),
                        inService       (2),
                        outOfService    (3)
                    }
            DESCRIPTION
                    "The only allowed values for this object are 'inService (2)'
                     and 'outOfService (3)'."

    ::= { tmnxSROSV10v0 55 }  -- DHCP Server
tmnx7950DhcpServerCapsV10v0    AGENT-CAPABILITIES
    PRODUCT-RELEASE "Alcatel-Lucent SROS"
    STATUS          current
    DESCRIPTION     "DHCP server is not supported
                     for Alcatel-Lucent SROS release R10.0"

--    SUPPORTS        TIMETRA-DHCP-SERVER-MIB
--        INCLUDES    { }

    ::= { tmnxSROSDhcpServerCapsV10v0 1 }  -- 7950 DHCP Server


--
--  PPPoE CAPABILITIES
--
tmnxSROSPPPoECapsV10v0  AGENT-CAPABILITIES
    PRODUCT-RELEASE "Alcatel-Lucent SROS"
    STATUS          current
    DESCRIPTION
        "Implementation of PPPoE capabilities for Alcatel-Lucent
         SROS release R10.0"

    SUPPORTS  TIMETRA-PPPOE-MIB
        INCLUDES  {
            tmnxPPPoEV8v0Group,
            tmnxPPPoEV9v0Group,
            tmnxPPPoEV10v0NotifyGroup,
-- EXCLUDE  tmnxPPPoEV6v0BsxGroup        no Application Assurance on SPR
            tmnxPPPV9v0Group,
            tmnxPPPMlpppGroup,
            tmnxPPPRejectDisabledNcp
        }

        VARIATION   tmnxPppoePlcyOptionType
            SYNTAX  INTEGER {
                        ipv4(1),
                        ascii(2),
                        hex(3)
                        -- ipv6(4)
                        -- domain(5)
                    }
            DESCRIPTION
                "The value 'ipv6(4)' and 'domain(5)' is not supported."

    ::= { tmnxSROSV10v0 56 }  -- PPPoE

tmnx7750PPPoECapsV10v0  AGENT-CAPABILITIES
    PRODUCT-RELEASE "Alcatel-Lucent SROS"
    STATUS          current
    DESCRIPTION
        "Implementation of specific PPPoE capabilities for Alcatel-Lucent
         SROS 7750 release R10.0"

    SUPPORTS  TIMETRA-PPPOE-MIB
        INCLUDES  {
            tmnxPPPoEV6v0BsxGroup
        }

    ::= { tmnxSROSPPPoECapsV10v0 1 }  -- 7750 PPPoE

tmnx7450PPPoECapsV10v0  AGENT-CAPABILITIES
    PRODUCT-RELEASE "Alcatel-Lucent SROS"
    STATUS          current
    DESCRIPTION
        "Implementation of specific PPPoE capabilities for Alcatel-Lucent
         SROS 7450 release R10.0"

    SUPPORTS  TIMETRA-PPPOE-MIB
        INCLUDES  {
            tmnxPPPoEV6v0BsxGroup
        }

    ::= { tmnxSROSPPPoECapsV10v0 2 }  -- 7450 PPPoE

tmnx7710PPPoECapsV10v0  AGENT-CAPABILITIES
    PRODUCT-RELEASE "Alcatel-Lucent SROS"
    STATUS          current
    DESCRIPTION
        "Implementation of specific PPPoE capabilities for Alcatel-Lucent
         SROS 7710 release R10.0"

    SUPPORTS  TIMETRA-PPPOE-MIB
        INCLUDES  {
            tmnxPPPoEV8v0Group
        }

        VARIATION   tmnxPppoeSessionL2tpVrtrId
            ACCESS  not-implemented
            DESCRIPTION
                "tmnxPppoeSessionL2tpVrtrId is not implemented on Alcatel-Lucent
                 7710 systems."

        VARIATION   tmnxPppoeSessionL2tpConnectionId
            ACCESS  not-implemented
            DESCRIPTION
                "tmnxPppoeSessionL2tpConnectionId is not implemented on
                 Alcatel-Lucent 7710 systems."

    ::= { tmnxSROSPPPoECapsV10v0 3 }  -- 7710 PPPoE
tmnx7950PPPoECapsV10v0  AGENT-CAPABILITIES
    PRODUCT-RELEASE "Alcatel-Lucent SROS"
    STATUS          current
    DESCRIPTION
        "PPPoE is not supported on Alcatel-Lucent
         SROS 7950 release R10.0"

--    SUPPORTS  TIMETRA-PPPOE-MIB
--        INCLUDES  { }
    ::= { tmnxSROSPPPoECapsV10v0 4 }  -- 7950 PPPoE


--
--  MLD CAPABILITIES
--
tmnxSROSMldCapsV10v0     AGENT-CAPABILITIES
    PRODUCT-RELEASE "Alcatel-Lucent SROS"
    STATUS          current
    DESCRIPTION     "Implementation of MLD capabilities
                     for Alcatel-Lucent SROS release R10.0"

    SUPPORTS        TIMETRA-MLD-MIB
        INCLUDES    {
            tmnxMldGlobalGroup,
            tmnxMldIfGroup,
            tmnxMldNotificationGroup,
            tmnxMldIfV6v1Group,
            tmnxMldIfV8v0Group
        }
        VARIATION   vRtrMldIfSsmTransRowStatus
            SYNTAX  RowStatus
            DESCRIPTION
                    "vRtrMldIfSsmTransRowStatus only supports 'ipv6' indices."

    ::= { tmnxSROSV10v0 57 }  -- MLD

--
-- Dot1ag CFM CAPABILITIES
--

tmnxSROSDot1agCfmCapsV10v0 AGENT-CAPABILITIES
    PRODUCT-RELEASE "Alcatel-Lucent SROS"
    STATUS          current
    DESCRIPTION     "Implementation of Dot1ag CFM capabilities
                     for Alcatel-Lucent SROS release R10.0"

    SUPPORTS        TIMETRA-IEEE8021-CFM-MIB
        INCLUDES    {
            tmnxDot1agCfmGPGroupV10v0,
            tmnxDot1agCfmGlobalGroupV9v0,
            tmnxDot1agCfmMaGroupV10v0,
            tmnxDot1agCfmMaGroupV9v0,
            tmnxDot1agCfmMepGroupV10v0,
            tmnxDot1agCfmMepGroupV7v0,
            tmnxDot1agCfmMepGroupV8v0,
            tmnxDot1agCfmMepGroupV9v0,
            tmnxDot1agCfmMepMcastLbmGroup,
            tmnxDot1agCfmMepSlmGroupV9v0,
            tmnxDot1agCfmMepSlmNotifyGroup,
            tmnxDot1agCfmMepSlmTWGroupV10v0,
            tmnxDot1agCfmMipGroupV8v0,
            tmnxDot1agCfmMipNotifyGroup,
            tmnxDot1agCfmNotificationGroup,
            tmnxDot1agCfmSapStackGroup,
            tmnxDot1agCfmSdpBindStackGroup,
            tmnxDot1agCfmStatsGroupV10v0,
            tmnxY1731CfmNotificationGroup
        }

        VARIATION   tmnxDot1agCfmMepEthTestPattern
            SYNTAX  INTEGER {
                        allZerosNoCrc  (0),
                        allZerosCrc    (1),
                        -- prbsNoCrc   (2),
                        -- prbsCrc     (3),
                        allOnesNoCrc   (4),
                        allOnesCrc     (5)
                    }
            DESCRIPTION
                    "tmnxDot1agCfmMepEthTestPattern supports all zero and all
                     one patterns only."

        VARIATION   tmnxDot1agCfmMepSlmOWTestTable
            ACCESS  not-implemented
            DESCRIPTION
                    "tmnxDot1agCfmMepSlmOWTestTable is not supported on the SROS
                     series systems."

        VARIATION   tmnxDot1agCfmMepSlmTestRsltTable
            DESCRIPTION
                    "tmnxDot1agCfmMepSlmTestRsltTable supports two-way tests
                     only.  The index, tmnxDot1agCfmMepSlmTestType, is fixed to
                     the value 'twoWayTest (2)'."

    SUPPORTS        IEEE8021-CFM-MIB
        INCLUDES    {
-- EXCLUDE  dot1agCfmStackGroup,
-- EXCLUDE  dot1agCfmDefaultMdGroup,
-- EXCLUDE  dot1agCfmVlanIdGroup,
-- EXCLUDE  dot1agCfmConfigErrorListGroup,
            dot1agCfmMdGroup,
            dot1agCfmMaGroup,
            dot1agCfmMepGroup,
            dot1agCfmMepDbGroup,
            dot1agCfmNotificationsGroup
        }

       VARIATION   dot1agCfmMdName
            SYNTAX  OCTET STRING (SIZE (0..43))
            DESCRIPTION
                    "dot1agCfmMdName supports a zero-length name when
                     dot1agCfmMdFormat is set to 'none (1)'."

        VARIATION   dot1agCfmMaComponentId
            DESCRIPTION
                    "dot1agCfmMaComponentId supports a smaller range than
                     specified in the IEEE-8021-CFM-MIB. The SROS series
                     supports the range of 1..2147483647."

        VARIATION   dot1agCfmMdMhfCreation
            SYNTAX  Dot1agCfmMhfCreation {
                        defMHFnone (1)
                        -- defMHFdefault (2),
                        -- defMHFexplicit (3)
                    }
            DESCRIPTION
                    "dot1agCfmMdMhfCreation only supports 'defMHFnone'."

        VARIATION   dot1agCfmMdMhfIdPermission
            SYNTAX  Dot1agCfmIdPermission {
                        sendIdNone (1)
                        -- sendIdChassis (2),
                        -- sendIdManage (3),
                        -- sendIdChassisManage (4),
                        -- sendIdDefer (5)
                    }
            DESCRIPTION
                    "dot1agCfmMdMhfIdPermission only supports 'sendIdNone'."

        VARIATION   dot1agCfmMaNetFormat
            SYNTAX  INTEGER {
                              primaryVid        (1),
                              charString        (2),
                              unsignedInt16     (3),
                              rfc2865VpnId      (4),
                              iccBased         (32)
                    }
            DEFVAL  { unsignedInt16 }
            DESCRIPTION
                    "dot1agCfmMaNetFormat defaults to 'unsignedInt16' if not
                     specified. The value 'iccBased (32)' is supported for
                     Y.1731 MEPs. The dot1agCfmMaNetName must be between 8 and
                     13 characters (inclusive) long when dot1agCfmMaNetFormat is
                     set to 'iccBased (32)'."

        VARIATION   dot1agCfmMaNetCcmInterval
            SYNTAX  INTEGER {
                        -- intervalInvalid (0),
                        -- interval300Hz (1),
                        -- interval10ms (2),
                        -- interval100ms (3),
                        interval1s (4),
                        interval10s (5),
                        interval1min (6),
                        interval10min (7)
                    }
            DEFVAL  { interval10s }
            DESCRIPTION
                    "dot1agCfmMaNetCcmInterval defaults to 'interval10s' if not
                     specified, and does not support sub-second intervals."

        VARIATION   dot1agCfmMaCompMhfCreation
            SYNTAX  Dot1agCfmMhfCreation {
                        defMHFnone (1),
                        -- defMHFdefault (2),
                        defMHFexplicit (3)
                        -- defMHFdefer (4)
                    }
            DEFVAL  { defMHFnone }
            DESCRIPTION
                    "dot1agCfmMaCompMhfCreation defaults to 'defMHFnone' if not
                     specified."

        VARIATION   dot1agCfmMaCompIdPermission
            SYNTAX  Dot1agCfmIdPermission {
                        sendIdNone (1)
                        -- sendIdChassis (2),
                        -- sendIdManage (3),
                        -- sendIdChassisManage (4),
                        -- sendIdDefer (5)
                    }
            DEFVAL  { defMHFnone }
            DESCRIPTION
                    "dot1agCfmMaCompIdPermission defaults to, and only supports
                     the value 'defMHFnone'."

       VARIATION   dot1agCfmMepErrorCcmLastFailure
            SYNTAX  OCTET STRING (SIZE(0..1522))
            DESCRIPTION
                   "dot1agCfmMepErrorCcmLastFailure supports a size of
                    0 octets."

        VARIATION   dot1agCfmMepXconCcmLastFailure
            SYNTAX  OCTET STRING (SIZE(0..1522))
            DESCRIPTION
                   "dot1agCfmMepXconCcmLastFailure supports a size of 0 octets."

        VARIATION   dot1agCfmMepCcmLtmPriority
            DEFVAL  { 7 }
            DESCRIPTION
                    "dot1agCfmMepCcmLtmPriority defaults to 7, if not
                     specified."

        VARIATION   dot1agCfmMepLowPrDef
            DESCRIPTION
                    "dot1agCfmMepLowPrDef will default to allDef (1) for MEPs
                     on eth-tunnel or eth-ring paths, macRemErrXcon (2)
                     otherwise."

        VARIATION   dot1agCfmMepFngAlarmTime
            ACCESS  read-only
            DESCRIPTION
                    "dot1agCfmMepFngAlarmTime is implemented as read-only."

        VARIATION   dot1agCfmMepFngResetTime
            ACCESS  read-only
            DESCRIPTION
                    "dot1agCfmMepFngResetTime is implemented as read-only."

        VARIATION   dot1agCfmMepTransmitLbmStatus
            ACCESS  read-only
            DESCRIPTION
                    "dot1agCfmMepTransmitLbmStatus is implemented as read-only."

        VARIATION   dot1agCfmMepTransmitLtmEgressIdentifier
            ACCESS  read-only
            DESCRIPTION
                    "dot1agCfmMepTransmitLtmEgressIdentifier is implemented as
                     read-only."

        VARIATION   dot1agCfmMepTransmitLbmDestMepId
            DEFVAL  { 0 }
            DESCRIPTION
                    "dot1agCfmMepTransmitLbmDestMepId defaults to, and only
                     supports the value zero (0)."

        VARIATION   dot1agCfmMepTransmitLbmDestIsMepId
            DEFVAL  { false }
            DESCRIPTION
                    "dot1agCfmMepTransmitLbmDestIsMepId defaults to, and only
                     supports the value false."

        VARIATION   dot1agCfmMepTransmitLbmMessages
            SYNTAX  Integer32 (0..5)
            DEFVAL  { 0 }
            DESCRIPTION
                    "dot1agCfmMepTransmitLbmMessages supports a range from
                     0 to 5 messages and defaults to 0."

        VARIATION   dot1agCfmMepTransmitLtmTargetIsMepId
            DEFVAL  { false }
            DESCRIPTION
                    "dot1agCfmMepTransmitLtmTargetIsMepId defaults to, and only
                     supports the value false."

        VARIATION   dot1agCfmMepPrimaryVid
            SYNTAX  Unsigned32
            DESCRIPTION
                    "dot1agCfmMepPrimaryVid supports the entire Unsigned32 range
                     of values. This is to facilitate Q-in-Q encapsulation for
                     SAPs."

        VARIATION   dot1agCfmMepTransmitLbmVlanDropEnable
           ACCESS   read-only
           DESCRIPTION
                   "dot1agCfmMepTransmitLbmVlanDropEnable is implemented as
                    read-only and only supports the value of false."

        VARIATION   dot1agCfmMepDbChassisIdSubtype
           ACCESS   not-implemented
           DESCRIPTION
                   "dot1agCfmMepDbChassisIdSubtype is not implemented."

        VARIATION   dot1agCfmMepDbChassisId
           ACCESS   not-implemented
           DESCRIPTION
                   "dot1agCfmMepDbChassisId is not implemented."

        VARIATION   dot1agCfmMepDbManAddressDomain
           ACCESS   not-implemented
           DESCRIPTION
                   "dot1agCfmMepDbManAddressDomain is not implemented."

        VARIATION   dot1agCfmMepDbManAddress
           ACCESS   not-implemented
           DESCRIPTION
                   "dot1agCfmMepDbManAddress is not implemented."

    ::= { tmnxSROSV10v0 58 }  -- DOT1AG

--
--    Multicast Path Management CAPABILITIES
--
tmnxSROSMcastPathMgmtCapsV10v0 AGENT-CAPABILITIES
     PRODUCT-RELEASE "Alcatel-Lucent SROS"
     STATUS          current
     DESCRIPTION
         "Implementation of suport for multicast load balancing and for
          tunnel interfaces related to Point to Multipoint LSPs (P2MP)
          feature through Multicast Path Management feature on Alcatel-Lucent
          SROS release R10.0."

     SUPPORTS TIMETRA-MCAST-PATH-MGMT-MIB
        INCLUDES    {
            tmnxMcPathGlobalGroup,
            tmnxMcPathGlobalV6v1Group,
            tmnxMcPathPlcyV6v0Group,
            tmnxMcPathPlcyV6v1Group,
            tmnxMcPathBdlV6v0Group,
            tmnxMcPathBdlChlV6v0Group,
            tmnxMcPathChlSrcV6v0Group,
            tmnxMcPathOperChlV6v0Group,
            tmnxMcPathSwPlaneGroup,
            tmnxMcPathNotificationGroup,
            tmnxMcPathGlobalV7v0Group,
            tmnxMcPathVdoV7v0Group,
            tmnxMcPathTunnelIfV7v0Group,
            tmnxMcPathGlobalV8v0Group,
            tmnxMcPathGlobalExtV6v1Group,
            tmnxMcPathGlobalV9v0Group,
            tmnxMcPathRprtDestV9v0Group,
            tmnxMcPathVdoV9v0Group,
            tmnxMcPathGlobalV10v0Group
        }

        VARIATION   tmnxMcPathBdlChlStartAddrType
            SYNTAX  INTEGER {
                        -- unknown  (0),
                        ipv4        (1),
                        ipv6        (2)
                        -- ipv4z    (3),
                        -- ipv6z    (4),
                        -- dns      (16)
                    }
            DESCRIPTION
                    "tmnxMcPathBdlChlStartAddrType supports only InetAddressType
                    'ipv4' and 'ipv6'."

        VARIATION   tmnxMcPathBdlChlStartAddr
            SYNTAX  InetAddress (SIZE (4))
            DESCRIPTION
                    "tmnxMcPathBdlChlStartAddr supports only InetAddressType
                    'ipv4' and 'ipv6'."

        VARIATION   tmnxMcPathBdlChlEndAddrType
            SYNTAX  INTEGER {
                        -- unknown  (0),
                        ipv4        (1),
                        ipv6        (2)
                        -- ipv4z    (3),
                        -- ipv6z    (4),
                        -- dns      (16)
                    }
            DESCRIPTION
                    "tmnxMcPathBdlChlEndAddrType supports only InetAddressType
                    'ipv4' and 'ipv6'."

        VARIATION   tmnxMcPathBdlChlEndAddr
            SYNTAX  InetAddress (SIZE (4))
            DESCRIPTION
                    "tmnxMcPathBdlChlEndAddr supports only InetAddressType
                    'ipv4' and 'ipv6'."

        VARIATION   tmnxMcPathChlSrcSourceAddrType
            SYNTAX  INTEGER {
                        -- unknown  (0),
                        ipv4        (1),
                        ipv6        (2)
                        -- ipv4z    (3),
                        -- ipv6z    (4),
                        -- dns      (16)
                    }
            DESCRIPTION
                    "tmnxMcPathChlSrcSourceAddrType supports only
                     InetAddressType 'ipv4' and 'ipv6'."

        VARIATION   tmnxMcPathChlSrcSourceAddr
            SYNTAX  InetAddress (SIZE (4))
            DESCRIPTION
                    "tmnxMcPathChlSrcSourceAddr supports only InetAddressType
                     'ipv4' and 'ipv6'."

        VARIATION   tmnxMcPathBdlTunIfSdAddrType
            SYNTAX  INTEGER {
                        unknown  (0),
                        ipv4        (1)
                        -- ipv6      (2)
                        -- ipv4z    (3),
                        -- ipv6z    (4),
                        -- dns      (16)
                    }
            DESCRIPTION
                    "tmnxMcPathBdlTunIfSdAddrType supports only InetAddressType
                     'unknown' and 'ipv4'."

        VARIATION   tmnxMcPathBdlTunIfSdAddr
            SYNTAX  InetAddress (SIZE (0|4))
            DESCRIPTION
                    "tmnxMcPathBdlTunIfSdAddr supports only InetAddressType
                     'unknown' and 'ipv4'."

        VARIATION   tmnxMcPathBdlChlTunIfSdAddrType
            SYNTAX  INTEGER {
                        unknown  (0),
                        ipv4        (1)
                        -- ipv6     (2)
                        -- ipv4z    (3),
                        -- ipv6z    (4),
                        -- dns      (16)
                    }
            DESCRIPTION
                    "tmnxMcPathBdlChlTunIfSdAddrType supports only
                     InetAddressType 'unknown' and 'ipv4'."

        VARIATION   tmnxMcPathBdlChlTunIfSdAddr
            SYNTAX  InetAddress (SIZE (0|4))
            DESCRIPTION
                    "tmnxMcPathBdlChlTunIfSdAddr supports only InetAddressType
                     'unknown' and 'ipv4'."

         VARIATION   tmnxMcPathChlSrcTunIfSdAddrType
            SYNTAX  INTEGER {
                        unknown  (0),
                        ipv4        (1)
                        -- ipv6      (2)
                        -- ipv4z    (3),
                        -- ipv6z    (4),
                        -- dns      (16)
                    }
            DESCRIPTION
                    "tmnxMcPathChlSrcTunIfSdAddrType supports only
                     InetAddressType 'unknown' and 'ipv4'."

        VARIATION   tmnxMcPathChlSrcTunIfSdAddr
            SYNTAX  InetAddress (SIZE (0|4))
            DESCRIPTION
                    "tmnxMcPathChlSrcTunIfSdAddr supports only InetAddressType
                     'unknown' and 'ipv4'."

        VARIATION   tmnxMcPathBdlDefChlBwActivity
            SYNTAX  INTEGER {
                        -- none (0),    
                        use-admin-bw (1),
                        dynamic (2)
                    }
            DESCRIPTION
                    "tmnxMcPathBdlDefChlBwActivity supports only 'use-admin-bw'
                     and 'dynamic'."

    ::= { tmnxSROSV10v0 59 }  -- MCAST PATH MANAGEMENT

tmnxSprMcastPathMgmtCapsV10v0 AGENT-CAPABILITIES
     PRODUCT-RELEASE "Alcatel-Lucent SROS"
     STATUS          current
     DESCRIPTION
         "Implementation of specific multicast load balancing and
          tunnel interfaces related to Point to Multipoint LSPs (P2MP)
          capabilities through Multicast Path Management feature on
          SROS SPR release R10.0."

     SUPPORTS TIMETRA-MCAST-PATH-MGMT-MIB
        INCLUDES    {
            tmnxMcPathGlobalGroup,
            tmnxMcPathPlcyV6v0Group,
            tmnxMcPathBdlV6v0Group,
            tmnxMcPathBdlChlV6v0Group,
            tmnxMcPathChlSrcV6v0Group
        }

        VARIATION   tmnxMcPathBwPlcyTableLastChanged
            ACCESS  not-implemented
            DESCRIPTION
                    "tmnxMcPathBwPlcyTableLastChanged is not implemented."

    ::= { tmnxSROSMcastPathMgmtCapsV10v0 3 }  -- SPR MCAST PATH MANAGEMENT

--
--   Local User Database CAPABILITIES
--
tmnxSROSLocalUserDbCapsV10v0 AGENT-CAPABILITIES
     PRODUCT-RELEASE "Alcatel-Lucent SROS"
     STATUS          current
     DESCRIPTION
         "Implementation of the Local User Database feature on Alcatel-Lucent
          SROS release R10.0."

     SUPPORTS TIMETRA-LOCAL-USER-DB-MIB
        INCLUDES    {
            tmnxLocalUserDbV7v0Group,
            tmnxLocalUserDbPppoeV8v0Group,
            tmnxLocalUserDbPppoeV9v0Group,
            tmnxLocalUserDbDhcpV8v0Group,
            tmnxLocalUserDbDhcpV9v0Group,
            tmnxLocalUserDbHostGroup,
            tmnxLocalUserDbToolsV8v0Group,
            tmnxLocalUserDbRadiusFllbckGroup,
            tmnxLocalUserDbHostGroup,
            tmnxLudbPppHostGroup,
            tmnxLudbRadproxGroup
-- EXCLUDE  tmnxLocalUserDbFltrProfGroup   not supported in 9.0
        }

        VARIATION   tmnxLocUsrDbPppoeAddrType
            SYNTAX  INTEGER {
                        unknown     (0),
                        ipv4        (1)
                        -- ipv6     (2),
                        -- ipv4z    (3),
                        -- ipv6z    (4),
                        -- dns      (16)
                    }
            DESCRIPTION
                    "tmnxLocUsrDbPppoeAddrType supports only InetAddressType
                    'unknown (0)' and 'ipv4 (1)'."

        VARIATION   tmnxLocUsrDbPppoeAddress
            SYNTAX  InetAddress (SIZE (0|4))
            DESCRIPTION
                    "tmnxLocUsrDbPppoeAddress supports only InetAddressType
                    'unknown (0)' and 'ipv4 (1)'."

        VARIATION   tmnxLocUsrDbDhcpAddrType
            SYNTAX  INTEGER {
                        unknown     (0),
                        ipv4        (1)
                        -- ipv6     (2),
                        -- ipv4z    (3),
                        -- ipv6z    (4),
                        -- dns      (16)
                    }
            DESCRIPTION
                    "tmnxLocUsrDbDhcpAddrType supports only InetAddressType
                    'unknown (0)' and 'ipv4 (1)'."

        VARIATION   tmnxLocUsrDbDhcpAddress
            SYNTAX  InetAddress (SIZE (0|4))
            DESCRIPTION
                    "tmnxLocUsrDbDhcpAddress supports only InetAddressType
                    'unknown (0)' and 'ipv4 (1)'."

        VARIATION   tmnxLudbHostTableLastChange
            ACCESS  not-implemented
            DESCRIPTION
            "tmnxLudbHostTableLastChange is not implemented on
             Alcatel-Lucent SROS release R10.0."

         VARIATION   tmnxLudbHostTable
             ACCESS  not-implemented
             DESCRIPTION
             "tmnxLudbHostTable is not implemented on
              Alcatel-Lucent SROS release R10.0."

        VARIATION   tmnxLocUsrDbPppoeOptionType
            SYNTAX  INTEGER {
                        ipv4(1),
                        ascii(2),
                        hex(3)
                        -- ipv6(4)
                        -- domain(5)
                    }
            DESCRIPTION
                    "The value 'ipv6(4)' and 'domain(5)' is not supported."

        VARIATION   tmnxLocUsrDbDhcpOptionType
            SYNTAX  INTEGER {
                        ipv4(1),
                        ascii(2),
                        hex(3)
                        -- ipv6(4)
                        -- domain(5)
                    }
            DESCRIPTION
                    "The value 'ipv6(4)' and 'domain(5)' is not supported."

    ::= { tmnxSROSV10v0 60 }  -- LOCAL-USER DB

tmnx7710LocalUserDbCapsV10v0    AGENT-CAPABILITIES
    PRODUCT-RELEASE "Alcatel-Lucent SROS"
    STATUS          current
    DESCRIPTION     "Implementation of the Local User Database feature on
                     Alcatel-Lucent 7710 release R10.0."

    SUPPORTS        TIMETRA-LOCAL-USER-DB-MIB
        INCLUDES    {
            tmnxLocalUserDbPppoeV8v0Group
        }

        VARIATION   tmnxLocUsrDbPppoeL2tpTunnelGroup
            ACCESS  not-implemented
            DESCRIPTION
                "tmnxLocUsrDbPppoeL2tpTunnelGroup is not implemented on
                 Alcatel-Lucent 7710 systems."

        VARIATION   tmnxLocUsrDbPppoeL2tpSvcId
            ACCESS  not-implemented
            DESCRIPTION
                "tmnxLocUsrDbPppoeL2tpSvcId is not implemented on
                 Alcatel-Lucent 7710 systems."

    ::= { tmnxSROSLocalUserDbCapsV10v0 1 }  -- 7710 LOCAL-USER DB
tmnx7950LocalUserDbCapsV10v0    AGENT-CAPABILITIES
    PRODUCT-RELEASE "Alcatel-Lucent SROS"
    STATUS          current
    DESCRIPTION     "The Local User Database feature is not supported on
                     Alcatel-Lucent 7950 release R10.0."

--    SUPPORTS        TIMETRA-LOCAL-USER-DB-MIB
--        INCLUDES    { }
    ::= { tmnxSROSLocalUserDbCapsV10v0 2 }  -- 7950 LOCAL-USER DB


--
--   PIM Snooping CAPABILITIES
--
tmnxSROSPimSnoopingCapsV10v0 AGENT-CAPABILITIES
     PRODUCT-RELEASE "Alcatel-Lucent SROS"
     STATUS          current
     DESCRIPTION
         "Implementation of the PIM Snooping feature on Alcatel-Lucent
          SROS release R10.0."

     SUPPORTS TIMETRA-PIM-SNOOPING-MIB
        INCLUDES    {
            tmnxPimSnpgGlobalGroup,
            tmnxPimSnpgIfGroup,
            tmnxPimSnpgIfSecNbrV6v0Group,
            tmnxPimSnpgNotificationGroup
        }

    ::= { tmnxSROSV10v0 61 }  -- PIM-SNOOPING

--
--  SAP CAPABILITIES
--
tmnxSROSSapCapsV10v0    AGENT-CAPABILITIES
    PRODUCT-RELEASE "Alcatel-Lucent SROS"
    STATUS          current
    DESCRIPTION     "Implementation of SAP capabilities
                     for Alcatel-Lucent SROS release R10.0."

    SUPPORTS        TIMETRA-SAP-MIB
        INCLUDES    {
           tmnxSapArpHostGroup,
-- EXCLUDE tmnxSapAtmV6v0Group
-- EXCLUDE tmnxSapAtmV9v0Group
           tmnxSapBaseV6v0Group,
           tmnxSapDefHostV9v0Group,
           tmnxSapDhcpV8v0Group,
           tmnxSapEgrEncapGrpV9v0Group,
           tmnxSapEthCfmGroup,
           tmnxSapEthRingGroup,
           tmnxSapFPropBMacV8v0Group,
           tmnxSapFrGroupV8v0,                          -- ??? FR on 7450 in mixed-mode???
           tmnxSapGreGroup,
           tmnxSapHsmdaV10v0Group,
           tmnxSapHsmdaV9v0Group,
           tmnxSapIgmpTrkGroup,
           tmnxSapIgmpTrkV8v0Group,
           tmnxSapIpV6FilterV6v0Group,
           tmnxSapIpipeV8v0Group,
           tmnxSapL2ptV6v0Group,
           tmnxSapMrpV8v0Group,
           tmnxSapMsapV6v1Group,
           tmnxSapMsapV8v0Group,
           tmnxSapMsapV9v0Group,
           tmnxSapMstiV6v0Group,
           tmnxSapMvrpNotificationV8v0Group,
           tmnxSapMvrpV10v0Group,
           tmnxSapNotificationV8v0Group,
           tmnxSapNotificationV9v0Group,
           tmnxSapNotifyGroup,
           tmnxSapOverrideV8v0Group,
           tmnxSapOverrideV9v0Group,
           tmnxSapPbbGroup,
           tmnxSapPlcrV8v0Group,
           tmnxSapPlcrV9v0Group,
           tmnxSapPolicyV6v0Group,
           tmnxSapPortIdV6v0Group,
           tmnxSapQosV8v0Group,
           tmnxSapRadiusFallbackGroup,
           tmnxSapStaticHostV9v0Group,
           tmnxSapSubMgmtV9v0Group,
           tmnxSapTlsV7v0Group,
           tmnxSapTlsV8v0Group,
           tmnxSapV8v0Group,
           tmnxSapV9v0Group,
           tmnxSapV10v0Group,
           tmnxTlsMsapPppoeV6v0Group,
           tmnxSapSpbGroup,
-- EXCLUDE tmnxSapFilterProfileV9v0Group  - not supported.
           tmnxSapIpipeNotificationGroup,
           tmnxSapGreV10v0Group,
-- EXCLUDE tmnxSapNotificationV10v0Group,
-- EXCLUDE tmnxSapIpTnlGroup,
           tmnxSapStatsV10v0Group,
           tmnxSapMonitorIPGroup
        }

        VARIATION   sapCpmProtMonitorIP
            DESCRIPTION
                    "sapCpmProtMonitorIP is supported on 7750 SR-7, 7750 SR-12,
                     7450 ESS-6, 7450 ESS-7, and 7450 ESS-12 only."

        VARIATION   sapTlsStpBpduEncap
            SYNTAX  INTEGER {
                        dynamic (1)
                    }
            DESCRIPTION
                    "The only value that can be assigned to sapTlsStpBpduEncap
                    is 'dynamic (1)'.  Additional values may be supported in a
                    later release."

        VARIATION   sapCreated
            ACCESS  not-implemented
            DESCRIPTION
                    "sapCreated notification is not implemented.
                    Replaced with TIMETRA-SYSTEM-MIB.tmnxConfigModify
                    notification"

        VARIATION   sapDeleted
            ACCESS  not-implemented
            DESCRIPTION
                    "sapDeleted notification is not implemented.
                    Replaced with TIMETRA-SYSTEM-MIB.tmnxConfigModify
                    notification"

        VARIATION   bridgedTLS
            ACCESS  not-implemented
            DESCRIPTION
                    "bridgedTLS notification is not implemented."

        VARIATION   sapReceiveOwnBpdu
            ACCESS  not-implemented
            DESCRIPTION
                    "sapReceiveOwnBpdu notification is not implemented."

        VARIATION   sapFPropBMacAddrRowStatus
            SYNTAX  INTEGER {
                        active(1),
                        -- notInService(2),
                        -- notReady(3),
                        createAndGo(4),
                        -- createAndWait(5),
                        destroy(6)
                    }
            DESCRIPTION
                    "sapFPropBMacAddrRowStatus supports the values 'active(1)',
                     'createAndGo(4)' and 'destroy(6)' only.

                     At most four rows with the same <svcId, sapPortId,
                     sapEncapValue> index triple are allowed."

        VARIATION   sapTmplTlsStpBpduEncap
            SYNTAX  INTEGER {
                        dynamic (1)
                    }
            DESCRIPTION
                    "The only value that can be assigned to
                    sapTmplTlsStpBpduEncap is 'dynamic (1)'.
                    Additional values may be supported in a later release."

    ::= { tmnxSROSV10v0 62 }  -- SAP

tmnx7750SapCapsV10v0    AGENT-CAPABILITIES
    PRODUCT-RELEASE "Alcatel-Lucent SROS"
    STATUS          current
    DESCRIPTION     "Implementation of specific SAP capabilities
                     for Alcatel-Lucent SROS 7750 release R10.0."

    SUPPORTS        TIMETRA-SAP-MIB
        INCLUDES    {
           tmnxSapAtmV6v0Group,
           tmnxSapAtmV9v0Group,
           tmnxSapCemNotificationV6v0Group,
           tmnxSapCemV6v0Group,
           tmnxSapEthCfmMonitorGroup,
           tmnxSapBsxV7v0Group,
           tmnxSapBsxV9v0Group,
           tmnxSapBsxV10v0Group
        }

    ::= { tmnxSROSSapCapsV10v0 1 }  -- 7750 SAP

tmnx7450SapCapsV10v0    AGENT-CAPABILITIES
    PRODUCT-RELEASE "Alcatel-Lucent SROS"
    STATUS          current
    DESCRIPTION     "Implementation of specific SAP capabilities
                     for Alcatel-Lucent SROS 7450 release R10.0."

    SUPPORTS        TIMETRA-SAP-MIB
        INCLUDES    {
           tmnxSapAtmV6v0Group,
           tmnxSapAtmV9v0Group,
                        tmnxSapV8v0Group,
                        tmnxSapEthCfmMonitorGroup,
-- Circuit Emulation (CEM) not supported on 7450
-- EXCLUDE  tmnxSapCemNotificationV6v0Group,
-- EXCLUDE  tmnxSapCemV6v0Group
                        tmnxSapBsxV7v0Group,
                        tmnxSapBsxV9v0Group,
                        tmnxSapBsxV10v0Group
        }

        VARIATION   sapAntiSpoofing
            SYNTAX  INTEGER {
                        disabled            (0),
                        sourceIpAddr        (1),
                        sourceMacAddr       (2),
                        sourceIpAndMacAddr  (3)
                        -- nextHopIpAndMacAddr (4)
                    }
            DESCRIPTION
                "The value 'nextHopIpAndMacAddr (4)'
                 is not supported on 7450 systems."

    ::= { tmnxSROSSapCapsV10v0 2 }  -- 7450 SAP

tmnxSprSapCapsV10v0    AGENT-CAPABILITIES
    PRODUCT-RELEASE "Alcatel-Lucent SROS"
    STATUS          current
    DESCRIPTION     "Implementation of specific SAP capabilities
                     for Alcatel-Lucent SROS SPR release R10.0."

    SUPPORTS        TIMETRA-SAP-MIB
        INCLUDES    {
           tmnxSapAtmV6v0Group,
           tmnxSapAtmV9v0Group,
            tmnxSapV8v0Group
-- EXCLUDE  tmnxSapHsmdaV10v0Group      no Q-MDA on SPR
-- EXCLUDE  tmnxSapEthCfmMonitorGroup  no CPU Protection on SPR
-- EXCLUDE  tmnxSapBsxV7v0Group        no Application Assurance on SPR
-- EXCLUDE  tmnxSapBsxV9v0Group        no Application Assurance on SPR
-- EXCLUDE  tmnxSapBsxV10v0Group       no Application Assurance on SPR
        }

        VARIATION   sapAntiSpoofing
            SYNTAX  INTEGER {
                        disabled            (0),
                        sourceIpAddr        (1),
                        sourceMacAddr       (2),
                        sourceIpAndMacAddr  (3)
                        -- nextHopIpAndMacAddr (4)
                    }
            DESCRIPTION
                "The value 'nextHopIpAndMacAddr (4)'
                 is not supported on SROS SPR systems."

    ::= { tmnxSROSSapCapsV10v0 3 }  -- SPR SAP

tmnx7710SapCapsV10v0    AGENT-CAPABILITIES
    PRODUCT-RELEASE "Alcatel-Lucent SROS"
    STATUS          current
    DESCRIPTION
        "Implementation of specific SAP capabilities
         for Alcatel-Lucent SROS 7710 release R10.0."

    SUPPORTS        TIMETRA-SAP-MIB
        INCLUDES    {
            tmnxSapV8v0Group
-- EXCLUDE  tmnxSapPlcrV8v0Group
        }

        VARIATION   sapIngPolicerPolicy
            ACCESS  not-implemented
            DESCRIPTION
                "sapIngPolicerPolicy is not implemented on SROS
                 7710 systems."

        VARIATION   sapEgrPolicerPolicy
            ACCESS  not-implemented
            DESCRIPTION
                "sapEgrPolicerPolicy is not implemented on SROS
                 7710 systems."

    ::= { tmnxSROSSapCapsV10v0 4 }  -- 7710 SAP

tmnx7950SapCapsV10v0    AGENT-CAPABILITIES
    PRODUCT-RELEASE "Alcatel-Lucent SROS"
    STATUS          current
    DESCRIPTION
        "Implementation of specific SAP capabilities
         for Alcatel-Lucent SROS 7950 release R10.0."

    SUPPORTS        TIMETRA-SAP-MIB
        INCLUDES    {
            tmnxSapTlsV8v0Group
        }

        VARIATION   sapTlsRestProtSrcMacAction
            SYNTAX  INTEGER {
                       disabled     (1),
                    -- alarm-only   (2)
                       discardFrame (3)
                    }
            DESCRIPTION
                "sapTlsRestProtSrcMacAction does not support 'alarm-only' on
                 7950 systems."

    ::= { tmnxSROSSapCapsV10v0 5 }  -- 7950 SAP

--
--  SDP CAPABILITIES
--
tmnxSROSSdpCapsV10v0    AGENT-CAPABILITIES
    PRODUCT-RELEASE "Alcatel-Lucent SROS"
    STATUS          current
    DESCRIPTION     "Implementation of SDP capabilities
                     for Alcatel-Lucent SROS release R10.0."

    SUPPORTS        TIMETRA-SDP-MIB
        INCLUDES    {
-- EXCLUDE   tmnxSdpApipeV6v0Group
             tmnxSdpAutoBindV7v0Group,
             tmnxSdpAutoBindV8v0Group,
             tmnxSdpBgpVplsV8v0Group,
-- EXCLUDE   tmnxSdpBindBsxV9v0Group
-- EXCLUDE   tmnxSdpBindBsxV10v0Group
             tmnxSdpBindCpipeV6v0Group,
             tmnxSdpBindDhcpV6v0Group,
             tmnxSdpBindEthCfmGroup,
             tmnxSdpBindGenGroup,
             tmnxSdpBindIpipeV8v0Group,
             tmnxSdpBindMeshV6v0Group,
             tmnxSdpBindTlsL2ptV6v0Group,
             tmnxSdpBindTlsMrpV8v0Group,
             tmnxSdpBindTlsV6v0Group,
             tmnxSdpBindTlsV8v0Group,
             tmnxSdpBindV6v0Group,
             tmnxSdpBindV8v0Group,
             tmnxSdpBindV9v0Group,
             tmnxSdpEvalPwTempV7v0Group,
             tmnxSdpFCV6v0Group,
             tmnxSdpL2V6v0Group,
             tmnxSdpL2V7v0Group,
             tmnxSdpL2V8v0Group,
             tmnxSdpMixedLspModeV9v0Group,
             tmnxSdpNotifyObjsV8v0Group,
             tmnxSdpNotifyV6v0Group,
             tmnxSdpNotifyV8v0Group,
             tmnxSdpPbbGroup,
             tmnxSdpPwV8v0Group,
             tmnxSdpTlsBgpV6v0Group,
             tmnxSdpV6v0Group,
             tmnxSdpV8v0Group,
             tmnxSdpV9v0Group,
             tmnxSdpPwPortGroup,
             tmnxSdpSpbGroup,
             tmnxSdpNotifyV10v0Group,
             tmnxSdpV10v0Group,
             tmnxSdpBindIpipeNotifyGroup,
             tmnxSdpBindBlockOnPeerFaultGroup,
             tmnxSdpBindQGrpObjsV10v0Group 
        }

        VARIATION   sdpCreated
            ACCESS  not-implemented
            DESCRIPTION
                    "sdpCreated notification is not implemented.
                    Replaced with TIMETRA-SYSTEM-MIB.tmnxConfigModify
                    notification."

        VARIATION   sdpDeleted
            ACCESS  not-implemented
            DESCRIPTION
                    "sdpDeleted notification is not implemented.
                    Replaced with TIMETRA-SYSTEM-MIB.tmnxConfigModify
                    notification."

        VARIATION   sdpBindCreated
            ACCESS  not-implemented
            DESCRIPTION
                    "sdpBindCreated notification is not implemented.
                    Replaced with TIMETRA-SYSTEM-MIB.tmnxConfigModify
                    notification."

        VARIATION   sdpBindDeleted
            ACCESS  not-implemented
            DESCRIPTION
                    "sdpBindDeleted notification is not implemented.
                    Replaced with TIMETRA-SYSTEM-MIB.tmnxConfigModify
                    notification."

        VARIATION   sdpBindVcType
            SYNTAX  INTEGER {
                        undef         (1),
                        ether         (2),
                        -- vpls       (3),
                        vlan          (4),
                        mirror        (5),
                        -- atmSdu        (6),
                        -- atmCell       (7),
                        -- atmVcc        (8),
                        -- atmVpc        (9),
                        frDlci        (10),
                        ipipe         (11),
                        satopE1       (12),
                        satopT1       (13),
                        -- satopE3    (14),
                        -- satopT3    (15),
                        cesopsn       (16),
                        cesopsnCas    (17)
                    }
            DESCRIPTION
                    "The enumeration 'vpls (3)' is no longer supported.
                     The enumerations
                        - atmSdu   (6),
                        - atmCell  (7),
                        - atmVcc   (8),
                        - atmVpc   (9),
                        - satopE3 (14),
                        - satopT3 (15)
                        are not supported on the SROS, as they are not
                        implemented."

        VARIATION   sdpBindFPropBMacAddrRowStatus
            SYNTAX  INTEGER {
                        active(1),
                        -- notInService(2),
                        -- notReady(3),
                        createAndGo(4),
                        -- createAndWait(5),
                        destroy(6)
                    }
            DESCRIPTION
                    "sdpBindFPropBMacAddrRowStatus supports the values
                     'active(1)', 'createAndGo(4)' and 'destroy(6)' only.

                     At most four rows with the same <svcId, sdpBindId> index
                     pair are allowed."

        VARIATION   sdpBindIsaAaApplicationProfile
            DESCRIPTION
                   "The sdpBindIsaAaApplicationProfile object only
                    applies to spoke SDP bindings under epipe(1), tls(3),
                    vprn(4), and ies(5) services."

        VARIATION   pwTemplateMfibMdaRowStatus
            SYNTAX  INTEGER {
                        active      (1),
                        createAndGo (4),
                        destroy     (6)
                     }
            DESCRIPTION
                    "pwTemplateMfibMdaRowStatus supports only the values
                    'active (1)', 'createAndGo (4)' and 'destroy (6)'."

    ::= { tmnxSROSV10v0 63 }  -- SDP

tmnx7750SdpCapsV10v0    AGENT-CAPABILITIES
    PRODUCT-RELEASE "Alcatel-Lucent SROS"
    STATUS          current
    DESCRIPTION     "Implementation of specific SDP capabilities
                     for Alcatel-Lucent SROS 7750 release R10.0."

    SUPPORTS        TIMETRA-SDP-MIB
        INCLUDES    {
           tmnxSdpApipeV6v0Group,
             tmnxSdpBindCpipeV6v0Group,
             tmnxSdpBindCpmProtGroup,
             tmnxSdpBindBsxV9v0Group,
             tmnxSdpBindBsxV10v0Group
        }

        VARIATION   sdpBindVcType
            SYNTAX  INTEGER {
                        undef         (1),
                        ether         (2),
                        -- vpls       (3),
                        vlan          (4),
                        mirror        (5),
                        atmSdu        (6),
                        atmCell       (7),
                        atmVcc        (8),
                        atmVpc        (9),
                        frDlci        (10),
                        ipipe         (11),
                        satopE1       (12),
                        satopT1       (13),
                        -- satopE3    (14),
                        -- satopT3    (15),
                        cesopsn       (16),
                        cesopsnCas    (17)
                    }
            DESCRIPTION
                    "The enumeration 'vpls (3)' is no longer supported.
                     The enumerations
                        - satopE3 (14),
                        - satopT3 (15)
                        are not supported on the SROS, as they are not
                        implemented."

        VARIATION   sdpBindCpmProtPolicyId
            DESCRIPTION
                    "sdpBindCpmProtPolicyId is not implemented on 7750 SR-1
                     systems."

        VARIATION   sdpBindCpmProtMonitorMac
            DESCRIPTION
                    "sdpBindCpmProtMonitorMac is not implemented on 7750 SR-1
                     systems."

        VARIATION   sdpBindCpmProtEthCfmMonitorFlags
            DESCRIPTION
                    "sdpBindCpmProtEthCfmMonitorFlags is not implemented on 7750
                     SR-1 systems."

    ::= { tmnxSROSSdpCapsV10v0 1 }  -- 7750 SDP

tmnx7450SdpCapsV10v0    AGENT-CAPABILITIES
    PRODUCT-RELEASE "Alcatel-Lucent SROS"
    STATUS          current
    DESCRIPTION     "Implementation of specific SDP capabilities
                     for Alcatel-Lucent SROS 7450 release R10.0."

    SUPPORTS        TIMETRA-SDP-MIB
        INCLUDES    {
           tmnxSdpApipeV6v0Group,
                        tmnxSdpBindV6v0Group,
-- EXCLUDE  tmnxSdpBindCpipeV6v0Group           - no CPIPE on 7450
                        tmnxSdpBindCpmProtGroup,
                        tmnxSdpBindBsxV9v0Group,
                        tmnxSdpBindBsxV10v0Group
        }

        VARIATION   sdpBindVcType
            SYNTAX  INTEGER {
                        undef         (1),
                        ether         (2),
                        -- vpls       (3),
                        vlan          (4),
                        mirror        (5),
                        atmSdu        (6),
                        atmCell       (7),
                        atmVcc        (8),
                        atmVpc        (9),
                        frDlci        (10),
                        ipipe         (11)
                        -- satopE1    (12),
                        -- satopT1    (13),
                        -- satopE3    (14),
                        -- satopT3    (15),
                        -- cesopsn    (16),
                        -- cesopsnCas (17)
                    }
            DESCRIPTION
                    "The enumeration 'vpls (3)' is no longer supported.
                     The values
                        - 'satopE1    (12)',
                        - 'satopT1    (13)',
                        - 'satopE3    (14)',
                        - 'satopT3    (15)',
                        - 'cesopsn    (16)',
                        - 'cesopsnCas (17)'
                     are not supported on a 7450 system, because CEM is
                     not implemented."

        VARIATION   sdpBindCpmProtPolicyId
            DESCRIPTION
                    "sdpBindCpmProtPolicyId is not implemented on 7450 ESS-1
                     systems."

        VARIATION   sdpBindCpmProtMonitorMac
            DESCRIPTION
                    "sdpBindCpmProtMonitorMac is not implemented on 7450 ESS-1
                     systems."

        VARIATION   sdpBindCpmProtEthCfmMonitorFlags
            DESCRIPTION
                    "sdpBindCpmProtEthCfmMonitorFlags is not implemented on 7450
                     ESS-1 systems."

    ::= { tmnxSROSSdpCapsV10v0 2 }  -- 7450 SDP

tmnxSPRSdpCapsV10v0     AGENT-CAPABILITIES
    PRODUCT-RELEASE "Alcatel-Lucent SROS"
    STATUS          current
    DESCRIPTION     "Implementation of SDP capabilities
                     for Alcatel-Lucent SPR release R10.0."

    SUPPORTS        TIMETRA-SDP-MIB
        INCLUDES    {
           tmnxSdpApipeV6v0Group
        }

        VARIATION   sdpBindVcType
            SYNTAX  INTEGER {
                        undef         (1),
                        ether         (2),
                        -- vpls       (3),
                        vlan          (4),
                        mirror        (5),
                        atmSdu        (6),
                        atmCell       (7),
                        atmVcc        (8),
                        atmVpc        (9),
                        frDlci        (10),
                        ipipe         (11),
                        satopE1       (12),
                        satopT1       (13),
                        -- satopE3    (14),
                        -- satopT3    (15),
                        cesopsn       (16),
                        cesopsnCas    (17)
                    }
            DESCRIPTION
                    "The enumeration 'vpls (3)' is no longer supported.
                     The enumerations
                        - satopE3 (14),
                        - satopT3 (15)
                        are not supported on the SROS, as they are not
                        implemented."

    ::= { tmnxSROSSdpCapsV10v0 3 }  -- SPR SDP

--
--  BSX CAPABILITIES
--
tmnxSROSBsxCapsV10v0    AGENT-CAPABILITIES
    PRODUCT-RELEASE "Alcatel-Lucent SROS"
    STATUS          current
    DESCRIPTION     "Implementation of BSX capabilities
                     for Alcatel-Lucent SROS release R10.0."

--  SUPPORTS        TIMETRA-BSX-NG-MIB
--    INCLUDES    {
--    }

    ::= { tmnxSROSV10v0 64 }  -- BSX

tmnx7750BsxCapsV10v0    AGENT-CAPABILITIES
    PRODUCT-RELEASE "Alcatel-Lucent SROS"
    STATUS          current
    DESCRIPTION     "Implementation of BSX capabilities
                     for Alcatel-Lucent 7750 release R10.0."

    SUPPORTS        TIMETRA-BSX-NG-MIB
        INCLUDES    {
             tmnxBsxMdaGroupV7v0,
             tmnxBsxMdaGroupV8v0,
             tmnxBsxMdaGroupV10v0,
             tmnxBsxPolicyGroupV10v0,
             tmnxBsxStatsGroup,
             tmnxBsxStatsGroupV9v0,
             tmnxBsxNotifyObjsGroup,
             tmnxBsxNotifyObjsGroupV7v0,
             tmnxBsxNotifyObjsGroupV8v0,
             tmnxBsxNotificationGroup,
             tmnxBsxNotificationGroupV7v0,
             tmnxBsxNotificationGroupV8v0,
             tmnxBsxNotificationGroupV9v0,
             tmnxBsxNotificationGroupV10v0,
             tmnxBsxRadApNotificationGroup,
             tmnxBsxCflowdGroup,
             tmnxBsxCflowdGroupV9v0,
             tmnxBsxCflowdGroupV10v0,
             tmnxBsxOvrdGroup,
             tmnxBsxTransitGroup,
             tmnxBsxTransitGroupV10v0,
             tmnxBsxTransitSeenIpGroup,
             tmnxBsxMobileGatewayGroup,
             tmnxBsxHttpRedirErrGroup,
             tmnxBsxHttpRedirGroup,
             tmnxBsxStaticObjGroup,
             tmnxBsxRedundancyObjGroup,
-- EXCLUDE   tmnxBsxHttpEnrichObjGroup            - not enabled in 10.0
-- EXCLUDE   tmnxBsxHttpEnrichStatObjGroup        - not enabled in 10.0
             tmnxBsxRadiusAccountingObjGroup,
             tmnxBsxRadApObjGroup,
             tmnxBsxRadApStatObjGroup
        }

        VARIATION   tmnxBsxAqpCharOperator
            SYNTAX  TmnxBsxOperator {
                        -- none  (0),
                        eq       (1)
                        -- neq   (2),
                        -- lt    (3),
                        -- gt    (4),
                        -- range (5)
                    }
            DESCRIPTION
                    "tmnxBsxAqpCharOperator only supports TmnxBsxOperator value
                     of 'eq (1)'."

        VARIATION   tmnxBsxAqpCharRowStatus
            SYNTAX  RowStatus {
                        active      (1),
                        createAndGo (4),
                        destroy     (6)
                     }
            DESCRIPTION
                    "tmnxBsxAqpCharRowStatus supports only the values
                    'active (1)', 'createAndGo (4)' and 'destroy (6)'."

        VARIATION   tmnxBsxAqpSapSubscrOp
            SYNTAX  TmnxBsxOperator {
                        none     (0),
                        eq       (1),
                        neq      (2)
                        -- lt    (3),
                        -- gt    (4),
                        -- range (5)
                    }
            DESCRIPTION
                    "tmnxBsxAqpSapSubscrOp only supports TmnxBsxOperator values
                     of 'none (0)', 'eq (1)' and 'neq (2)."

        VARIATION   tmnxBsxAppFilterServerAddrType
            SYNTAX  INTEGER {
                        unknown     (0),
                        ipv4        (1)
                        -- ipv6     (2)
                        -- ipv4z    (3),
                        -- ipv6z    (4),
                        -- dns      (16)
                    }
            DESCRIPTION
                    "tmnxBsxAppFilterServerAddrType supports only
                     InetAddressType 'unknown (0)' and 'ipv4 (1)'."

        VARIATION   tmnxBsxAppFilterServerAddr
            SYNTAX  InetAddress (SIZE (0|4))
            DESCRIPTION
                    "tmnxBsxAppFilterServerAddr only supports InetAddressType
                    'unknown (0)' and 'ipv4 (1)'."

        VARIATION   tmnxBsxAppFilterServerAddrOp
            SYNTAX  TmnxBsxOperator {
                        none     (0),
                        eq       (1),
                        neq      (2)
                        -- lt    (3),
                        -- gt    (4),
                        -- range (5)
                    }
            DESCRIPTION
                    "tmnxBsxAppFilterServerAddrOp only supports TmnxBsxOperator
                     values of 'none (0)', 'eq (1)' and 'neq (2)."

        VARIATION   tmnxBsxAppFilterServerPortOp
            SYNTAX  TmnxBsxOperator {
                        none     (0),
                        eq       (1),
                        neq      (2),
                        lt       (3),
                        gt       (4)
                        -- range (5)
                    }
            DESCRIPTION
                    "tmnxBsxAppFilterServerPortOp only supports TmnxBsxOperator
                     values of 'none (0)', 'eq (1)', 'neq (2)', 'lt (3)' and
                     'gt (4)."

        VARIATION   tmnxBsxAqpSrcAddressType
            SYNTAX  INTEGER {
                        unknown     (0),
                        ipv4        (1)
                        -- ipv6     (2)
                        -- ipv4z    (3),
                        -- ipv6z    (4),
                        -- dns      (16)
                    }
            DESCRIPTION
                    "tmnxBsxAqpSrcAddressType supports only InetAddressType
                     'unknown (0)' and 'ipv4 (1)'."

        VARIATION   tmnxBsxAqpSrcAddress
            SYNTAX  InetAddress (SIZE (0|4))
            DESCRIPTION
                    "tmnxBsxAqpSrcAddress only supports InetAddressType
                    'unknown (0)' and 'ipv4 (1)'."

        VARIATION   tmnxBsxAqpSrcAddressOp
            SYNTAX  TmnxBsxOperator {
                        none     (0),
                        eq       (1),
                        neq      (2)
                        -- lt    (3),
                        -- gt    (4),
                        -- range (5)
                    }
            DESCRIPTION
                    "tmnxBsxAqpSrcAddressOp only supports TmnxBsxOperator values
                     of 'none (0)', 'eq (1)' and 'neq (2)."

        VARIATION   tmnxBsxAqpSrcPortOp
            SYNTAX  TmnxBsxOperator {
                        none     (0),
                        eq       (1),
                        neq      (2)
                        -- lt    (3),
                        -- gt    (4),
                        -- range (5)
                    }
            DESCRIPTION
                    "tmnxBsxAqpSrcPortOp only supports TmnxBsxOperator values
                     of 'none (0)', 'eq (1)' and 'neq (2)."

        VARIATION   tmnxBsxAqpDstAddressType
            SYNTAX  INTEGER {
                        unknown     (0),
                        ipv4        (1)
                        -- ipv6     (2)
                        -- ipv4z    (3),
                        -- ipv6z    (4),
                        -- dns      (16)
                    }
            DESCRIPTION
                    "tmnxBsxAqpDstAddressType supports only InetAddressType
                     'unknown (0)' and 'ipv4 (1)'."

        VARIATION   tmnxBsxAqpDstAddress
            SYNTAX  InetAddress (SIZE (0|4))
            DESCRIPTION
                    "tmnxBsxAqpDstAddress only supports InetAddressType
                    'unknown (0)' and 'ipv4 (1)'."

        VARIATION   tmnxBsxAqpDstAddressOp
            SYNTAX  TmnxBsxOperator {
                        none     (0),
                        eq       (1),
                        neq      (2)
                        -- lt    (3),
                        -- gt    (4),
                        -- range (5)
                    }
            DESCRIPTION
                    "tmnxBsxAqpDstAddressOp only supports TmnxBsxOperator values
                     of 'none (0)', 'eq (1)' and 'neq (2)."

        VARIATION   tmnxBsxAqpDstPortOp
            SYNTAX  TmnxBsxOperator {
                        none     (0),
                        eq       (1),
                        neq      (2)
                        -- lt    (3),
                        -- gt    (4),
                        -- range (5)
                    }
            DESCRIPTION
                    "tmnxBsxAqpDstPortOp only supports TmnxBsxOperator values
                     of 'none (0)', 'eq (1)' and 'neq (2)."

        VARIATION   tmnxBsxAppFilterExprIndex
            SYNTAX  Integer32 (1..4)
            DESCRIPTION
                    "tmnxBsxAppFilterExprIndex supports a range from 1 to 4
                     expressions."

        VARIATION   tmnxBsxAppFilterExprOperator
            SYNTAX  TmnxBsxOperator {
                        none     (0),
                        eq       (1),
                        neq      (2)
                        -- lt    (3),
                        -- gt    (4),
                        -- range (5)
                    }
            DESCRIPTION
                    "tmnxBsxAppFilterExprOperator only supports TmnxBsxOperator
                     values of 'none (0)', 'eq (1)' and 'neq (2)."

        VARIATION   tmnxBsxNotifyActionStatus
            SYNTAX  TmnxBsxActionStatus {
                        -- none  (0),
                        start (1),
                        stop  (2)
                    }
             DESCRIPTION
                    "tmnxBsxNotifyActionStatus only supports TmnxBsxActionStatus
                     values of 'start (1)' and 'stop (2)."

        VARIATION   tmnxBsxAaGrpPartRowStatus
            SYNTAX  RowStatus {
                        active      (1),
                        createAndGo (4),
                        destroy     (6)
                     }
            DESCRIPTION
                    "tmnxBsxAaGrpPartRowStatus supports only the values
                    'active (1)', 'createAndGo (4)' and 'destroy (6)'."

         VARIATION   tmnxBsxCustProtRowStatus
            SYNTAX  RowStatus {
                        active      (1),
                        createAndGo (4),
                        destroy     (6)
                     }
            DESCRIPTION
                    "tmnxBsxCustProtRowStatus supports only the values
                    'active (1)', 'createAndGo (4)' and 'destroy (6)'."

         VARIATION   tmnxBsxCustProtExprRowStatus
            SYNTAX  RowStatus {
                        active      (1),
                        createAndGo (4),
                        destroy     (6)
                     }
            DESCRIPTION
                    "tmnxBsxCustProtExprRowStatus supports only the values
                    'active (1)', 'createAndGo (4)' and 'destroy (6)'."

         VARIATION   tmnxBsxCustProtIpProtocolNum
            DESCRIPTION
                    "tmnxBsxCustProtIpProtocolNum supports only the values
                     not set (-1), tcp (6) and udp (17)."

         VARIATION   tmnxBsxCustProtExprOperator
            SYNTAX  TmnxBsxOperator {
                        -- none     (0),
                        eq          (1)
                        -- neq      (2)
                        -- lt       (3),
                        -- gt       (4),
                        -- range    (5)
                    }
            DESCRIPTION
                    "tmnxBsxCustProtExprOperator only supports TmnxBsxOperator
                     values of 'eq (1)'."

        VARIATION   tmnxBsxCflowdCollAddressType
            SYNTAX  INTEGER {
                        unknown     (0),
                        ipv4        (1)
                        -- ipv6     (2)
                        -- ipv4z    (3),
                        -- ipv6z    (4),
                        -- dns      (16)
                    }
            DESCRIPTION
                    "tmnxBsxCflowdCollAddressType supports only InetAddressType
                     'unknown (0)' and 'ipv4 (1)'."

        VARIATION   tmnxBsxCflowdCollAddress
            SYNTAX  InetAddress (SIZE (0|4))
            DESCRIPTION
                    "tmnxBsxCflowdCollAddress only supports InetAddressType
                    'unknown (0)' and 'ipv4 (1)'."

         VARIATION  tmnxBsxCflowdCollRowStatus
            SYNTAX  RowStatus {
                        active      (1),
                        createAndGo (4),
                        destroy     (6)
                     }
            DESCRIPTION
                    "tmnxBsxCflowdCollRowStatus supports only the values
                    'active (1)', 'createAndGo (4)' and 'destroy (6)'."

         VARIATION  tmnxBsxCflowdPerfExpRowStatus
            SYNTAX  RowStatus {
                        active      (1),
                        createAndGo (4),
                        destroy     (6)
                     }
            DESCRIPTION
                    "tmnxBsxCflowdPerfExpRowStatus supports only the values
                    'active (1)', 'createAndGo (4)' and 'destroy (6)'."

         VARIATION   tmnxBsxCustProtEntryId
            SYNTAX  TEntryId (1..10)
            DESCRIPTION
                    "tmnxBsxCustProtEntryId supports a range from 1 to 10
                     custom protocol entries."

         VARIATION   tmnxBsxCustProtExprIndex
            SYNTAX  Integer32 (1)
            DESCRIPTION
                    "tmnxBsxCustProtExprIndex only supports 1 custom protocol
                     expression."

         VARIATION  tmnxBsxTransitIpPolicyRowStatus
            SYNTAX  RowStatus {
                        active      (1),
                        createAndGo (4),
                        destroy     (6)
                     }
            DESCRIPTION
                    "tmnxBsxTransitIpPolicyRowStatus supports only the values
                     'active (1)', 'createAndGo (4)' and 'destroy (6)'."

         VARIATION  tmnxBsxTransIpPlcySubRowStatus
            SYNTAX  RowStatus {
                        active      (1),
                        createAndGo (4),
                        destroy     (6)
                     }
            DESCRIPTION
                    "tmnxBsxTransIpPlcySubRowStatus supports only the values
                     'active (1)', 'createAndGo (4)' and 'destroy (6)'."

        VARIATION   tmnxBsxTransitIpPolicyAddrType
            SYNTAX  INTEGER {
                        -- unknown     (0),
                        ipv4        (1),
                        ipv6        (2)
                        -- ipv4z    (3),
                        -- ipv6z    (4),
                        -- dns      (16)
                    }
            DESCRIPTION
                    "tmnxBsxTransitIpPolicyAddrType supports only
                     InetAddressTypes 'ipv4 (1)' and 'ipv6(2)'."

         VARIATION  tmnxBsxTransIpPlcyAddrRowStatus
            SYNTAX  RowStatus {
                        active      (1),
                        createAndGo (4),
                        destroy     (6)
                     }
            DESCRIPTION
                    "tmnxBsxTransIpPlcyAddrRowStatus supports only the values
                    'active (1)', 'createAndGo (4)' and 'destroy (6)'."

        VARIATION  tmnxBsxFlowSetupHighWatermark
            SYNTAX Integer32 (-1 | 1..200000)
            DESCRIPTION
                    "tmnxBsxFlowSetupHighWatermark supports the range from 1
                     to 200000 as well as the value -1 which ensures that this
                     high watermark threshold will not be exceeded."

        VARIATION   tmnxBsxFlowSetupLowWatermark
            SYNTAX  Integer32 (0..199999)
            DESCRIPTION
                    "tmnxBsxFlowSetupLowWatermark supports the range from 0
                     to 199999."

        VARIATION   tmnxBsxPacketRateHighWatermark
            SYNTAX  Integer32 (-1 | 1..14880952)
            DESCRIPTION
                    "tmnxBsxPacketRateHighWatermark supports the range from
                     1 to 14880952 as well as the value -1 which ensures that
                     this high watermark threshold will not be exceeded."

        VARIATION   tmnxBsxPacketRateLowWatermark
            SYNTAX  Integer32 (0..14880951)
            DESCRIPTION
                    "tmnxBsxPacketRateLowWatermark supports the range from
                     0 to 14880951."

        VARIATION   tmnxBsxBitRateHighWatermark
            SYNTAX  Integer32 (-1 | 1..10000)
            DESCRIPTION
                    "tmnxBsxBitRateHighWatermark supports the range from
                     1 to 10000 as well as the value -1 which ensures that this
                     high watermark threshold will not be exceeded."

        VARIATION   tmnxBsxBitRateLowWatermark
            SYNTAX  Integer32 (0..9999)
            DESCRIPTION
                    "tmnxBsxBitRateLowWatermark supports the range from
                     0 to 9999."

        VARIATION   tmnxBsxTransitIpSumParentSubType
            SYNTAX  TmnxBsxAaSubscriberType {
                     unknown   (0),
                     -- esm       (1),
                     sap       (2),
                     spokeSdp  (3)
                     -- transit   (4)
                 }
            DESCRIPTION
                    "tmnxBsxTransitIpSumParentSubType supports only the
                     values 'unknown(0)', 'sap(2)', and 'spokeSdp(3)'."

         VARIATION  tmnxBsxTransPrefPolicyRowStatus
            SYNTAX  RowStatus {
                        active      (1),
                        createAndGo (4),
                        destroy     (6)
                     }
            DESCRIPTION
                    "tmnxBsxTransPrefPolicyRowStatus supports only the values
                    'active (1)', 'createAndGo (4)' and 'destroy (6)'."

         VARIATION  tmnxBsxTransPrefSubRowStatus
            SYNTAX  RowStatus {
                        active      (1),
                        createAndGo (4),
                        destroy     (6)
                     }
            DESCRIPTION
                    "tmnxBsxTransPrefSubRowStatus supports only the values
                    'active (1)', 'createAndGo (4)' and 'destroy (6)'."

         VARIATION  tmnxBsxTransPrefEntryRowStatus
            SYNTAX  RowStatus {
                        active      (1),
                        createAndGo (4),
                        destroy     (6)
                     }
            DESCRIPTION
                    "tmnxBsxTransPrefEntryRowStatus supports only the values
                    'active (1)', 'createAndGo (4)' and 'destroy (6)'."

        VARIATION   tmnxBsxTransPrefEntrySubAddrType
            SYNTAX  INTEGER {
                        unknown     (0),
                        ipv4        (1)
                        -- ipv6     (2)
                        -- ipv4z    (3),
                        -- ipv6z    (4),
                        -- dns      (16)
                    }
            DESCRIPTION
                    "tmnxBsxTransPrefEntrySubAddrType supports only
                     InetAddressTypes 'unknown(0)' and 'ipv4 (1)'."

        VARIATION   tmnxBsxTransPrefEntryNetAddrType
            SYNTAX  INTEGER {
                        unknown     (0),
                        ipv4        (1)
                        -- ipv6     (2)
                        -- ipv4z    (3),
                        -- ipv6z    (4),
                        -- dns      (16)
                    }
            DESCRIPTION
                    "tmnxBsxTransPrefEntryNetAddrType supports only
                     InetAddressTypes 'unknown(0)' and 'ipv4 (1)'."

        VARIATION   tmnxBsxTransPrefSumSubAddrType
            SYNTAX  INTEGER {
                        unknown     (0),
                        ipv4        (1)
                        -- ipv6     (2)
                        -- ipv4z    (3),
                        -- ipv6z    (4),
                        -- dns      (16)
                    }
            DESCRIPTION
                    "tmnxBsxTransPrefSumSubAddrType supports only
                     InetAddressTypes 'unknown(0)' and 'ipv4 (1)'."

        VARIATION   tmnxBsxTransPrefSumNetAddrType
            SYNTAX  INTEGER {
                        unknown     (0),
                        ipv4        (1)
                        -- ipv6     (2)
                        -- ipv4z    (3),
                        -- ipv6z    (4),
                        -- dns      (16)
                    }
            DESCRIPTION
                    "tmnxBsxTransPrefSumNetAddrType supports only
                     InetAddressTypes 'unknown(0)' and 'ipv4 (1)'."

        VARIATION   tmnxBsxIsaAaGrpTransPrefV4NmEntr
            SYNTAX  Unsigned32 (0..16383)
            DESCRIPTION
                    "tmnxBsxIsaAaGrpTransPrefV4NmEntr supports the range
                     from 0 to 16383."

         VARIATION  tmnxBsxHttpRedirErrRowStatus
            SYNTAX  RowStatus {
                        active      (1),
                        createAndGo (4),
                        destroy     (6)
                     }
            DESCRIPTION
                    "tmnxBsxHttpRedirErrRowStatus supports only the values
                    'active (1)', 'createAndGo (4)' and 'destroy (6)'."

         VARIATION  tmnxBsxHttpRedirErrCodeRowStatus
            SYNTAX  RowStatus {
                        active      (1),
                        createAndGo (4),
                        destroy     (6)
                     }
            DESCRIPTION
                    "tmnxBsxHttpRedirErrCodeRowStatus supports only the values
                    'active (1)', 'createAndGo (4)' and 'destroy (6)'."

         VARIATION  tmnxBsxAarpInstRowStatus
            SYNTAX  RowStatus {
                        active      (1),
                        createAndGo (4),
                        destroy     (6)
                     }
            DESCRIPTION
                    "tmnxBsxAarpInstRowStatus supports only the values
                    'active (1)', 'createAndGo (4)' and 'destroy (6)'."

        VARIATION   tmnxBsxAarpInstPeerIpType
            SYNTAX  INTEGER {
                        unknown     (0),
                        ipv4        (1)
                        --  ipv6    (2),
                        -- ipv4z    (3),
                        -- ipv6z    (4),
                        -- dns      (16)
                    }
            DESCRIPTION
                    "tmnxBsxAarpInstPeerIpType supports only
                     InetAddressTypes 'unknown(0)', 'ipv4(1)',
                     and 'ipv6(2)'."

        VARIATION   tmnxBsxAarpInstPeerEPSapEncType
            SYNTAX  INTEGER {
                    unknown (0),
                    nullEncap (1),  
                    -- qEncap (2),
                    -- mplsEncap (3),
                    -- bcpNullEncap (4),
                    bcpDot1qEncap (5),
                    -- ipcpEncap (6),
                    -- frEncap (7),
                    -- pppAutoEncap (8),
                    -- atmEncap (9),
                    qinqEncap (10)
                    -- wanMirrorEncap (11),
                    -- ciscoHDLCEncap (12),
                    -- cemEncap (13)
                }
            DESCRIPTION
                    "tmnxBsxAarpInstPeerEPSapEncType supports only
                     TmnxPortEncapType 'unknown(0)', 'nullEncap(1)', 
                     'bcpDot1qEncap(5)', and 'qinqEncap(10)'."

        VARIATION   tmnxBsxTransitIpPolicyIPv6PfxLen
            SYNTAX  InetAddressPrefixLength (32..64)
            DESCRIPTION
                    "tmnxBsxTransitIpPolicyIPv6PfxLen supports only
                     the range from 32 to 64."

        VARIATION   tmnxBsxStatAaSubSdyRowStatus
            SYNTAX  RowStatus {
                        active      (1),
                        createAndGo (4),
                        destroy     (6)
                    }
            DESCRIPTION
                    "tmnxBsxStatAaSubSdyRowStatus supports only the values
                     'active (1)', 'createAndGo (4)' and 'destroy (6)'.

                     Rows can not be created where the tmnxBsxStatAaType
                     has a value of 'chargingGroup (4)'."

        VARIATION   tmnxBsxStatAaSubCfgRowStatus
            SYNTAX  RowStatus {
                        active      (1),
                        createAndGo (4),
                        destroy     (6)
                    }
            DESCRIPTION
                    "tmnxBsxStatAaSubCfgRowStatus supports only the values
                     'active (1)', 'createAndGo (4)' and 'destroy (6)'."

        VARIATION   tmnxBsxStatAaSubCfgExportMethod
            DESCRIPTION
                    "tmnxBsxStatAaSubCfgExportMethod must only have the
                     'accountingPolicy (0)' bit set when tmnxBsxStatAaType has a
                     value of 'app-group (3)'.
                     
                     tmnxBsxStatAaSubCfgExportMethod must only have the
                     'radiusAccountingPolicy (1)' bit set when tmnxBsxStatAaType
                     has a value of 'charging-group (3)'. "

        VARIATION   tmnxBsxChargeGrpRowStatus
            SYNTAX  RowStatus {
                        active      (1),
                        createAndGo (4),
                        destroy     (6)
                    }
            DESCRIPTION
                    "tmnxBsxChargeGrpRowStatus supports only the values
                     'active (1)', 'createAndGo (4)' and 'destroy (6)'."

        VARIATION   tmnxBsxRadApRowStatus
            SYNTAX  RowStatus {
                        active      (1),
                        createAndGo (4),
                        destroy     (6)
                    }
            DESCRIPTION
                    "tmnxBsxRadApRowStatus supports only the values
                     'active (1)', 'createAndGo (4)' and 'destroy (6)'."

        VARIATION   tmnxBsxRadApServerSrcAddrType
            SYNTAX  INTEGER {
                        unknown     (0),
                        ipv4        (1)
                        -- ipv6     (2)
                        -- ipv4z    (3),
                        -- ipv6z    (4),
                        -- dns      (16)
                    }
            DESCRIPTION
                    "tmnxBsxRadApServerSrcAddrType supports only
                     InetAddressType values 'unknown (0)' and 'ipv4 (1)'."

        VARIATION   tmnxBsxRadApServerAlgorithm
            SYNTAX  TmnxSubRadServAlgorithm {
                        direct     (1),
                        roundRobin (2)
                    }
            DESCRIPTION
                    "tmnxBsxRadApServerAlgorithm supports only the values
                     'direct (1)' and 'roundRobin (2)'."

        VARIATION   tmnxBsxRadApServRowStatus
            SYNTAX  RowStatus {
                        active      (1),
                        createAndGo (4),
                        destroy     (6)
                    }
            DESCRIPTION
                    "tmnxBsxRadApServRowStatus supports only the values
                     'active (1)', 'createAndGo (4)' and 'destroy (6)'."

        VARIATION   tmnxBsxRadApServAddrType
            SYNTAX  INTEGER {
                        unknown     (0),
                        ipv4        (1)
                        -- ipv6     (2)
                        -- ipv4z    (3),
                        -- ipv6z    (4),
                        -- dns      (16)
                    }
            DESCRIPTION
                    "tmnxBsxRadApServAddrType supports only
                     InetAddressType values 'unknown (0)' and 'ipv4 (1)'."

    ::= { tmnxSROSBsxCapsV10v0 1 }  -- 7750 BSX

tmnx7450BsxCapsV10v0    AGENT-CAPABILITIES
    PRODUCT-RELEASE "Alcatel-Lucent SROS"
    STATUS          current
    DESCRIPTION     "Implementation of BSX capabilities
                     for Alcatel-Lucent 7450 release R10.0."

    SUPPORTS        TIMETRA-BSX-NG-MIB
        INCLUDES    {
             tmnxBsxMdaGroupV7v0,
             tmnxBsxMdaGroupV8v0,
             tmnxBsxMdaGroupV10v0,
             tmnxBsxPolicyGroupV10v0,
             tmnxBsxStatsGroup,
             tmnxBsxStatsGroupV9v0,
             tmnxBsxNotifyObjsGroup,
             tmnxBsxNotifyObjsGroupV7v0,
             tmnxBsxNotifyObjsGroupV8v0,
             tmnxBsxNotificationGroup,
             tmnxBsxNotificationGroupV7v0,
             tmnxBsxNotificationGroupV8v0,
             tmnxBsxNotificationGroupV9v0,
             tmnxBsxNotificationGroupV10v0,
             tmnxBsxRadApNotificationGroup,
             tmnxBsxCflowdGroup,
             tmnxBsxCflowdGroupV9v0,
             tmnxBsxCflowdGroupV10v0,
             tmnxBsxOvrdGroup,
             tmnxBsxTransitGroup,
             tmnxBsxTransitGroupV10v0,
             tmnxBsxTransitSeenIpGroup,
             tmnxBsxMobileGatewayGroup,
             tmnxBsxHttpRedirErrGroup,
             tmnxBsxHttpRedirGroup,
             tmnxBsxStaticObjGroup,
             tmnxBsxRedundancyObjGroup,
             tmnxBsxRadiusAccountingObjGroup,
             tmnxBsxRadApObjGroup,
             tmnxBsxRadApStatObjGroup
        }

        VARIATION   tmnxBsxAqpCharOperator
            SYNTAX  TmnxBsxOperator {
                        -- none  (0),
                        eq       (1)
                        -- neq   (2),
                        -- lt    (3),
                        -- gt    (4),
                        -- range (5)
                    }
            DESCRIPTION
                    "tmnxBsxAqpCharOperator only supports TmnxBsxOperator value
                     of 'eq (1)'."

        VARIATION   tmnxBsxAqpCharRowStatus
            SYNTAX  RowStatus {
                        active      (1),
                        createAndGo (4),
                        destroy     (6)
                     }
            DESCRIPTION
                    "tmnxBsxAqpCharRowStatus supports only the values
                    'active (1)', 'createAndGo (4)' and 'destroy (6)'."

        VARIATION   tmnxBsxAqpSapSubscrOp
            SYNTAX  TmnxBsxOperator {
                        none     (0),
                        eq       (1),
                        neq      (2)
                        -- lt    (3),
                        -- gt    (4),
                        -- range (5)
                    }
            DESCRIPTION
                    "tmnxBsxAqpSapSubscrOp only supports TmnxBsxOperator values
                     of 'none (0)', 'eq (1)' and 'neq (2)."

        VARIATION   tmnxBsxAppFilterServerAddrType
            SYNTAX  INTEGER {
                        unknown     (0),
                        ipv4        (1)
                        -- ipv6     (2)
                        -- ipv4z    (3),
                        -- ipv6z    (4),
                        -- dns      (16)
                    }
            DESCRIPTION
                    "tmnxBsxAppFilterServerAddrType supports only
                     InetAddressType 'unknown (0)' and 'ipv4 (1)'."

        VARIATION   tmnxBsxAppFilterServerAddr
            SYNTAX  InetAddress (SIZE (0|4))
            DESCRIPTION
                    "tmnxBsxAppFilterServerAddr only supports InetAddressType
                    'unknown (0)' and 'ipv4 (1)'."

        VARIATION   tmnxBsxAppFilterServerAddrOp
            SYNTAX  TmnxBsxOperator {
                        none     (0),
                        eq       (1),
                        neq      (2)
                        -- lt    (3),
                        -- gt    (4),
                        -- range (5)
                    }
            DESCRIPTION
                    "tmnxBsxAppFilterServerAddrOp only supports TmnxBsxOperator
                     values of 'none (0)', 'eq (1)' and 'neq (2)."

        VARIATION   tmnxBsxAppFilterServerPortOp
            SYNTAX  TmnxBsxOperator {
                        none     (0),
                        eq       (1),
                        neq      (2),
                        lt       (3),
                        gt       (4)
                        -- range (5)
                    }
            DESCRIPTION
                    "tmnxBsxAppFilterServerPortOp only supports TmnxBsxOperator
                     values of 'none (0)', 'eq (1)', 'neq (2)', 'lt (3)' and
                     'gt (4)."

        VARIATION   tmnxBsxAqpSrcAddressType
            SYNTAX  INTEGER {
                        unknown     (0),
                        ipv4        (1)
                        -- ipv6     (2)
                        -- ipv4z    (3),
                        -- ipv6z    (4),
                        -- dns      (16)
                    }
            DESCRIPTION
                    "tmnxBsxAqpSrcAddressType supports only InetAddressType
                     'unknown (0)' and 'ipv4 (1)'."

        VARIATION   tmnxBsxAqpSrcAddress
            SYNTAX  InetAddress (SIZE (0|4))
            DESCRIPTION
                    "tmnxBsxAqpSrcAddress only supports InetAddressType
                    'unknown (0)' and 'ipv4 (1)'."

        VARIATION   tmnxBsxAqpSrcAddressOp
            SYNTAX  TmnxBsxOperator {
                        none     (0),
                        eq       (1),
                        neq      (2)
                        -- lt    (3),
                        -- gt    (4),
                        -- range (5)
                    }
            DESCRIPTION
                    "tmnxBsxAqpSrcAddressOp only supports TmnxBsxOperator values
                     of 'none (0)', 'eq (1)' and 'neq (2)."

        VARIATION   tmnxBsxAqpSrcPortOp
            SYNTAX  TmnxBsxOperator {
                        none     (0),
                        eq       (1),
                        neq      (2)
                        -- lt    (3),
                        -- gt    (4),
                        -- range (5)
                    }
            DESCRIPTION
                    "tmnxBsxAqpSrcPortOp only supports TmnxBsxOperator values
                     of 'none (0)', 'eq (1)' and 'neq (2)."

        VARIATION   tmnxBsxAqpDstAddressType
            SYNTAX  INTEGER {
                        unknown     (0),
                        ipv4        (1)
                        -- ipv6     (2)
                        -- ipv4z    (3),
                        -- ipv6z    (4),
                        -- dns      (16)
                    }
            DESCRIPTION
                    "tmnxBsxAqpDstAddressType supports only InetAddressType
                     'unknown (0)' and 'ipv4 (1)'."

        VARIATION   tmnxBsxAqpDstAddress
            SYNTAX  InetAddress (SIZE (0|4))
            DESCRIPTION
                    "tmnxBsxAqpDstAddress only supports InetAddressType
                    'unknown (0)' and 'ipv4 (1)'."

        VARIATION   tmnxBsxAqpDstAddressOp
            SYNTAX  TmnxBsxOperator {
                        none     (0),
                        eq       (1),
                        neq      (2)
                        -- lt    (3),
                        -- gt    (4),
                        -- range (5)
                    }
            DESCRIPTION
                    "tmnxBsxAqpDstAddressOp only supports TmnxBsxOperator values
                     of 'none (0)', 'eq (1)' and 'neq (2)."

        VARIATION   tmnxBsxAqpDstPortOp
            SYNTAX  TmnxBsxOperator {
                        none     (0),
                        eq       (1),
                        neq      (2)
                        -- lt    (3),
                        -- gt    (4),
                        -- range (5)
                    }
            DESCRIPTION
                    "tmnxBsxAqpDstPortOp only supports TmnxBsxOperator values
                     of 'none (0)', 'eq (1)' and 'neq (2)."

        VARIATION   tmnxBsxAppFilterExprIndex
            SYNTAX  Integer32 (1..4)
            DESCRIPTION
                    "tmnxBsxAppFilterExprIndex supports a range from 1 to 4
                     expressions."

        VARIATION   tmnxBsxAppFilterExprOperator
            SYNTAX  TmnxBsxOperator {
                        none     (0),
                        eq       (1),
                        neq      (2)
                        -- lt    (3),
                        -- gt    (4),
                        -- range (5)
                    }
            DESCRIPTION
                    "tmnxBsxAppFilterExprOperator only supports TmnxBsxOperator
                     values of 'none (0)', 'eq (1)' and 'neq (2)."

        VARIATION   tmnxBsxNotifyActionStatus
            SYNTAX  TmnxBsxActionStatus {
                        -- none  (0),
                        start (1),
                        stop  (2)
                    }
             DESCRIPTION
                    "tmnxBsxNotifyActionStatus only supports TmnxBsxActionStatus
                     values of 'start (1)' and 'stop (2)."

        VARIATION   tmnxBsxAaGrpPartRowStatus
            SYNTAX  RowStatus {
                        active      (1),
                        createAndGo (4),
                        destroy     (6)
                     }
            DESCRIPTION
                    "tmnxBsxAaGrpPartRowStatus supports only the values
                    'active (1)', 'createAndGo (4)' and 'destroy (6)'."

         VARIATION   tmnxBsxCustProtRowStatus
            SYNTAX  RowStatus {
                        active      (1),
                        createAndGo (4),
                        destroy     (6)
                     }
            DESCRIPTION
                    "tmnxBsxCustProtRowStatus supports only the values
                    'active (1)', 'createAndGo (4)' and 'destroy (6)'."

         VARIATION   tmnxBsxCustProtExprRowStatus
            SYNTAX  RowStatus {
                        active      (1),
                        createAndGo (4),
                        destroy     (6)
                     }
            DESCRIPTION
                    "tmnxBsxCustProtExprRowStatus supports only the values
                    'active (1)', 'createAndGo (4)' and 'destroy (6)'."

         VARIATION   tmnxBsxCustProtIpProtocolNum
            DESCRIPTION
                    "tmnxBsxCustProtIpProtocolNum supports only the values
                     not set (-1), tcp (6) and udp (17)."

         VARIATION   tmnxBsxCustProtExprOperator
            SYNTAX  TmnxBsxOperator {
                        -- none     (0),
                        eq          (1)
                        -- neq      (2)
                        -- lt       (3),
                        -- gt       (4),
                        -- range    (5)
                    }
            DESCRIPTION
                    "tmnxBsxCustProtExprOperator only supports TmnxBsxOperator
                     values of 'eq (1)'."

        VARIATION   tmnxBsxCflowdCollAddressType
            SYNTAX  INTEGER {
                        unknown     (0),
                        ipv4        (1)
                        -- ipv6     (2)
                        -- ipv4z    (3),
                        -- ipv6z    (4),
                        -- dns      (16)
                    }
            DESCRIPTION
                    "tmnxBsxCflowdCollAddressType supports only InetAddressType
                     'unknown (0)' and 'ipv4 (1)'."

        VARIATION   tmnxBsxCflowdCollAddress
            SYNTAX  InetAddress (SIZE (0|4))
            DESCRIPTION
                    "tmnxBsxCflowdCollAddress only supports InetAddressType
                    'unknown (0)' and 'ipv4 (1)'."

         VARIATION  tmnxBsxCflowdCollRowStatus
            SYNTAX  RowStatus {
                        active      (1),
                        createAndGo (4),
                        destroy     (6)
                     }
            DESCRIPTION
                    "tmnxBsxCflowdCollRowStatus supports only the values
                    'active (1)', 'createAndGo (4)' and 'destroy (6)'."

         VARIATION  tmnxBsxCflowdPerfExpRowStatus
            SYNTAX  RowStatus {
                        active      (1),
                        createAndGo (4),
                        destroy     (6)
                     }
            DESCRIPTION
                    "tmnxBsxCflowdPerfExpRowStatus supports only the values
                    'active (1)', 'createAndGo (4)' and 'destroy (6)'."

         VARIATION   tmnxBsxCustProtEntryId
            SYNTAX  TEntryId (1..10)
            DESCRIPTION
                    "tmnxBsxCustProtEntryId supports a range from 1 to 10
                     custom protocol entries."

         VARIATION   tmnxBsxCustProtExprIndex
            SYNTAX  Integer32 (1)
            DESCRIPTION
                    "tmnxBsxCustProtExprIndex only supports 1 custom protocol
                     expression."

         VARIATION  tmnxBsxTransitIpPolicyRowStatus
            SYNTAX  RowStatus {
                        active      (1),
                        createAndGo (4),
                        destroy     (6)
                     }
            DESCRIPTION
                    "tmnxBsxTransitIpPolicyRowStatus supports only the values
                     'active (1)', 'createAndGo (4)' and 'destroy (6)'."

         VARIATION  tmnxBsxTransIpPlcySubRowStatus
            SYNTAX  RowStatus {
                        active      (1),
                        createAndGo (4),
                        destroy     (6)
                     }
            DESCRIPTION
                    "tmnxBsxTransIpPlcySubRowStatus supports only the values
                     'active (1)', 'createAndGo (4)' and 'destroy (6)'."

        VARIATION   tmnxBsxTransitIpPolicyAddrType
            SYNTAX  INTEGER {
                        -- unknown     (0),
                        ipv4        (1),
                        ipv6        (2)
                        -- ipv4z    (3),
                        -- ipv6z    (4),
                        -- dns      (16)
                    }
            DESCRIPTION
                    "tmnxBsxTransitIpPolicyAddrType supports only
                     InetAddressTypes 'ipv4 (1)' and 'ipv6(2)'."

         VARIATION  tmnxBsxTransIpPlcyAddrRowStatus
            SYNTAX  RowStatus {
                        active      (1),
                        createAndGo (4),
                        destroy     (6)
                     }
            DESCRIPTION
                    "tmnxBsxTransIpPlcyAddrRowStatus supports only the values
                    'active (1)', 'createAndGo (4)' and 'destroy (6)'."

        VARIATION  tmnxBsxFlowSetupHighWatermark
            SYNTAX Integer32 (-1 | 1..200000)
            DESCRIPTION
                    "tmnxBsxFlowSetupHighWatermark supports the range from 1
                     to 200000 as well as the value -1 which ensures that this
                     high watermark threshold will not be exceeded."

        VARIATION   tmnxBsxFlowSetupLowWatermark
            SYNTAX  Integer32 (0..199999)
            DESCRIPTION
                    "tmnxBsxFlowSetupLowWatermark supports the range from 0
                     to 199999."

        VARIATION   tmnxBsxPacketRateHighWatermark
            SYNTAX  Integer32 (-1 | 1..14880952)
            DESCRIPTION
                    "tmnxBsxPacketRateHighWatermark supports the range from
                     1 to 14880952 as well as the value -1 which ensures that
                     this high watermark threshold will not be exceeded."

        VARIATION   tmnxBsxPacketRateLowWatermark
            SYNTAX  Integer32 (0..14880951)
            DESCRIPTION
                    "tmnxBsxPacketRateLowWatermark supports the range from
                     0 to 14880951."

        VARIATION   tmnxBsxBitRateHighWatermark
            SYNTAX  Integer32 (-1 | 1..10000)
            DESCRIPTION
                    "tmnxBsxBitRateHighWatermark supports the range from
                     1 to 10000 as well as the value -1 which ensures that this
                     high watermark threshold will not be exceeded."

        VARIATION   tmnxBsxBitRateLowWatermark
            SYNTAX  Integer32 (0..9999)
            DESCRIPTION
                    "tmnxBsxBitRateLowWatermark supports the range from
                     0 to 9999."

        VARIATION   tmnxBsxTransitIpSumParentSubType
            SYNTAX  TmnxBsxAaSubscriberType {
                     unknown   (0),
                     -- esm       (1),
                     sap       (2),
                     spokeSdp  (3)
                     -- transit   (4)
                 }
            DESCRIPTION
                    "tmnxBsxTransitIpSumParentSubType supports only the
                     values 'unknown(0)', 'sap(2)', and 'spokeSdp(3)'."

         VARIATION  tmnxBsxTransPrefPolicyRowStatus
            SYNTAX  RowStatus {
                        active      (1),
                        createAndGo (4),
                        destroy     (6)
                     }
            DESCRIPTION
                    "tmnxBsxTransPrefPolicyRowStatus supports only the values
                    'active (1)', 'createAndGo (4)' and 'destroy (6)'."

         VARIATION  tmnxBsxTransPrefSubRowStatus
            SYNTAX  RowStatus {
                        active      (1),
                        createAndGo (4),
                        destroy     (6)
                     }
            DESCRIPTION
                    "tmnxBsxTransPrefSubRowStatus supports only the values
                    'active (1)', 'createAndGo (4)' and 'destroy (6)'."

         VARIATION  tmnxBsxTransPrefEntryRowStatus
            SYNTAX  RowStatus {
                        active      (1),
                        createAndGo (4),
                        destroy     (6)
                     }
            DESCRIPTION
                    "tmnxBsxTransPrefEntryRowStatus supports only the values
                    'active (1)', 'createAndGo (4)' and 'destroy (6)'."

        VARIATION   tmnxBsxTransPrefEntrySubAddrType
            SYNTAX  INTEGER {
                        unknown     (0),
                        ipv4        (1)
                        -- ipv6     (2)
                        -- ipv4z    (3),
                        -- ipv6z    (4),
                        -- dns      (16)
                    }
            DESCRIPTION
                    "tmnxBsxTransPrefEntrySubAddrType supports only
                     InetAddressTypes 'unknown(0)' and 'ipv4 (1)'."

        VARIATION   tmnxBsxTransPrefEntryNetAddrType
            SYNTAX  INTEGER {
                        unknown     (0),
                        ipv4        (1)
                        -- ipv6     (2)
                        -- ipv4z    (3),
                        -- ipv6z    (4),
                        -- dns      (16)
                    }
            DESCRIPTION
                    "tmnxBsxTransPrefEntryNetAddrType supports only
                     InetAddressTypes 'unknown(0)' and 'ipv4 (1)'."

        VARIATION   tmnxBsxTransPrefSumSubAddrType
            SYNTAX  INTEGER {
                        unknown     (0),
                        ipv4        (1)
                        -- ipv6     (2)
                        -- ipv4z    (3),
                        -- ipv6z    (4),
                        -- dns      (16)
                    }
            DESCRIPTION
                    "tmnxBsxTransPrefSumSubAddrType supports only
                     InetAddressTypes 'unknown(0)' and 'ipv4 (1)'."

        VARIATION   tmnxBsxTransPrefSumNetAddrType
            SYNTAX  INTEGER {
                        unknown     (0),
                        ipv4        (1)
                        -- ipv6     (2)
                        -- ipv4z    (3),
                        -- ipv6z    (4),
                        -- dns      (16)
                    }
            DESCRIPTION
                    "tmnxBsxTransPrefSumNetAddrType supports only
                     InetAddressTypes 'unknown(0)' and 'ipv4 (1)'."

        VARIATION   tmnxBsxIsaAaGrpTransPrefV4NmEntr
            SYNTAX  Unsigned32 (0..16383)
            DESCRIPTION
                    "tmnxBsxIsaAaGrpTransPrefV4NmEntr supports the range
                     from 0 to 16383."

         VARIATION  tmnxBsxHttpRedirErrRowStatus
            SYNTAX  RowStatus {
                        active      (1),
                        createAndGo (4),
                        destroy     (6)
                     }
            DESCRIPTION
                    "tmnxBsxHttpRedirErrRowStatus supports only the values
                    'active (1)', 'createAndGo (4)' and 'destroy (6)'."

         VARIATION  tmnxBsxHttpRedirErrCodeRowStatus
            SYNTAX  RowStatus {
                        active      (1),
                        createAndGo (4),
                        destroy     (6)
                     }
            DESCRIPTION
                    "tmnxBsxHttpRedirErrCodeRowStatus supports only the values
                    'active (1)', 'createAndGo (4)' and 'destroy (6)'."

         VARIATION  tmnxBsxAarpInstRowStatus
            SYNTAX  RowStatus {
                        active      (1),
                        createAndGo (4),
                        destroy     (6)
                     }
            DESCRIPTION
                    "tmnxBsxAarpInstRowStatus supports only the values
                    'active (1)', 'createAndGo (4)' and 'destroy (6)'."

        VARIATION   tmnxBsxAarpInstPeerIpType
            SYNTAX  INTEGER {
                        unknown     (0),
                        ipv4        (1)
                        --  ipv6    (2),
                        -- ipv4z    (3),
                        -- ipv6z    (4),
                        -- dns      (16)
                    }
            DESCRIPTION
                    "tmnxBsxAarpInstPeerIpType supports only
                     InetAddressTypes 'unknown(0)', 'ipv4(1)',
                     and 'ipv6(2)'."

        VARIATION   tmnxBsxAarpInstPeerEPSapEncType
            SYNTAX  INTEGER {
                    unknown (0),
                    nullEncap (1),  
                    -- qEncap (2),
                    -- mplsEncap (3),
                    -- bcpNullEncap (4),
                    bcpDot1qEncap (5),
                    -- ipcpEncap (6),
                    -- frEncap (7),
                    -- pppAutoEncap (8),
                    -- atmEncap (9),
                    qinqEncap (10)
                    -- wanMirrorEncap (11),
                    -- ciscoHDLCEncap (12),
                    -- cemEncap (13)
                }
            DESCRIPTION
                    "tmnxBsxAarpInstPeerEPSapEncType supports only
                     TmnxPortEncapType 'unknown (0)', 'nullEncap(1)', 
                     'bcpDot1qEncap(5)', and 'qinqEncap(10)'."

        VARIATION   tmnxBsxTransitIpPolicyIPv6PfxLen
            SYNTAX  InetAddressPrefixLength (32..64)
            DESCRIPTION
                    "tmnxBsxTransitIpPolicyIPv6PfxLen supports only
                     the range from 32 to 64."

        VARIATION   tmnxBsxHttpRedirRowStatus
            SYNTAX  RowStatus {
                        active      (1),
                        createAndGo (4),
                        destroy     (6)
                    }
            DESCRIPTION
                    "tmnxBsxHttpRedirRowStatus supports only the values
                     'active (1)', 'createAndGo (4)' and 'destroy (6)'."

        VARIATION   tmnxBsxHttpEnrichRowStatus
            SYNTAX  RowStatus {
                        active      (1),
                        createAndGo (4),
                        destroy     (6)
                    }
            DESCRIPTION
                    "tmnxBsxHttpEnrichRowStatus supports only the values
                     'active (1)', 'createAndGo (4)' and 'destroy (6)'."

        VARIATION   tmnxBsxHttpEnrichFieldRowStatus
            SYNTAX  RowStatus {
                        active      (1),
                        createAndGo (4),
                        destroy     (6)
                    }
            DESCRIPTION
                    "tmnxBsxHttpEnrichFieldRowStatus supports only the values
                     'active (1)', 'createAndGo (4)' and 'destroy (6)'."

        VARIATION   tmnxBsxStatAaSubSdyRowStatus
            SYNTAX  RowStatus {
                        active      (1),
                        createAndGo (4),
                        destroy     (6)
                    }
            DESCRIPTION
                    "tmnxBsxStatAaSubSdyRowStatus supports only the values
                     'active (1)', 'createAndGo (4)' and 'destroy (6)'.

                     Rows can not be created where the tmnxBsxStatAaType
                     has a value of 'chargingGroup (4)'."

        VARIATION   tmnxBsxStatAaSubCfgRowStatus
            SYNTAX  RowStatus {
                        active      (1),
                        createAndGo (4),
                        destroy     (6)
                    }
            DESCRIPTION
                    "tmnxBsxStatAaSubCfgRowStatus supports only the values
                     'active (1)', 'createAndGo (4)' and 'destroy (6)'."

        VARIATION   tmnxBsxStatAaSubCfgExportMethod
            DESCRIPTION
                    "tmnxBsxStatAaSubCfgExportMethod must only have the
                     'accountingPolicy (0)' bit set when tmnxBsxStatAaType has a
                     value of 'app-group (3)'.
                     
                     tmnxBsxStatAaSubCfgExportMethod must only have the
                     'radiusAccountingPolicy (1)' bit set when tmnxBsxStatAaType
                     has a value of 'charging-group (3)'. "

        VARIATION   tmnxBsxChargeGrpRowStatus
            SYNTAX  RowStatus {
                        active      (1),
                        createAndGo (4),
                        destroy     (6)
                    }
            DESCRIPTION
                    "tmnxBsxChargeGrpRowStatus supports only the values
                     'active (1)', 'createAndGo (4)' and 'destroy (6)'."

        VARIATION   tmnxBsxRadApRowStatus
            SYNTAX  RowStatus {
                        active      (1),
                        createAndGo (4),
                        destroy     (6)
                    }
            DESCRIPTION
                    "tmnxBsxRadApRowStatus supports only the values
                     'active (1)', 'createAndGo (4)' and 'destroy (6)'."

        VARIATION   tmnxBsxRadApServerSrcAddrType
            SYNTAX  INTEGER {
                        unknown     (0),
                        ipv4        (1)
                        -- ipv6     (2)
                        -- ipv4z    (3),
                        -- ipv6z    (4),
                        -- dns      (16)
                    }
            DESCRIPTION
                    "tmnxBsxRadApServerSrcAddrType supports only
                     InetAddressType values 'unknown (0)' and 'ipv4 (1)'."

        VARIATION   tmnxBsxRadApServerAlgorithm
            SYNTAX  TmnxSubRadServAlgorithm {
                        direct     (1),
                        roundRobin (2)
                    }
            DESCRIPTION
                    "tmnxBsxRadApServerAlgorithm supports only the values
                     'direct (1)' and 'roundRobin (2)'."

        VARIATION   tmnxBsxRadApServRowStatus
            SYNTAX  RowStatus {
                        active      (1),
                        createAndGo (4),
                        destroy     (6)
                    }
            DESCRIPTION
                    "tmnxBsxRadApServRowStatus supports only the values
                     'active (1)', 'createAndGo (4)' and 'destroy (6)'."

        VARIATION   tmnxBsxRadApServAddrType
            SYNTAX  INTEGER {
                        unknown     (0),
                        ipv4        (1)
                        -- ipv6     (2)
                        -- ipv4z    (3),
                        -- ipv6z    (4),
                        -- dns      (16)
                    }
            DESCRIPTION
                    "tmnxBsxRadApServAddrType supports only
                     InetAddressType values 'unknown (0)' and 'ipv4 (1)'."

    ::= { tmnxSROSBsxCapsV10v0 2 }  -- 7450 BSX

tmnx7750cBsxCapsV10v0    AGENT-CAPABILITIES
    PRODUCT-RELEASE "Alcatel-Lucent SROS"
    STATUS          current
    DESCRIPTION     "Implementation of specific BSX capabilities
                     for Alcatel-Lucent SROS 7750 SR-c release R10.0."
    SUPPORTS        TIMETRA-BSX-NG-MIB
        INCLUDES    {
             tmnxBsxMdaGroupV10v0
        }

        VARIATION   tmnxBsxIsaAaGrpTransPrefV4NmEntr
            SYNTAX  Unsigned32 (0..4095)
            DESCRIPTION
                    "tmnxBsxIsaAaGrpTransPrefV4NmEntr supports the range
                     from 0 to 4095."

    ::= { tmnxSROSBsxCapsV10v0 3 }  -- 7750 SR-c BSX

--
--  LLDP CAPABILITIES
--
tmnxSROSLLDPCapsV10v0    AGENT-CAPABILITIES
    PRODUCT-RELEASE "Alcatel-Lucent SROS"
    STATUS          current
    DESCRIPTION     "Implementation of LLDP capabilities
                     for Alcatel-Lucent SROS release R10.0."

    SUPPORTS        TIMETRA-LLDP-MIB
        INCLUDES    {
            tmnxLldpConfigGroup,
            tmnxLldpStatsRxGroup,
            tmnxLldpStatsTxGroup,
            tmnxLldpLocSysGroup,
            tmnxLldpRemSysGroup,
            tmnxLldpRemManAddrGroup
        }

    SUPPORTS        LLDP-MIB
        INCLUDES    {
-- EXCLUDE  lldpConfigGroup,
            lldpConfigRxGroup,
            lldpConfigTxGroup,
            lldpStatsRxGroup,
-- EXCLUDE  lldpStatsTxGroup,
            lldpLocSysGroup,
-- EXCLUDE  lldpRemSysGroup,
            lldpNotificationsGroup
        }

        VARIATION   lldpPortConfigNotificationEnable
            ACCESS  not-implemented
            DESCRIPTION
                    "lldpPortConfigNotificationEnable has been replaced by
                     TIMETRA-LLDP-MIB::tmnxLldpPortCfgNotifyEnable."

        VARIATION   lldpTxDelay
            ACCESS  not-implemented
            DESCRIPTION
                    "lldpTxDelay is not implemented."

        VARIATION   lldpPortConfigTLVsTxEnable
            ACCESS  not-implemented
            DESCRIPTION
                    "lldpPortConfigTLVsTxEnable has been replaced by
                     TIMETRA-LLDP-MIB::tmnxLldpPortCfgTLVsTxEnable."

        VARIATION   lldpConfigManAddrPortsTxEnable
            ACCESS  not-implemented
            DESCRIPTION
                    "lldpConfigManAddrPortsTxEnable has been replaced by
                     TIMETRA-LLDP-MIB::tmnxLldpPortCfgManAddrTxEnabled."

        VARIATION   lldpStatsRxPortFramesDiscardedTotal
            ACCESS  not-implemented
            DESCRIPTION
                    "lldpStatsRxPortFramesDiscardedTotal has been replaced by
                     TIMETRA-LLDP-MIB::tmnxLldpStatsRxPortFrameDiscard."

        VARIATION   lldpStatsRxPortFramesErrors
            ACCESS  not-implemented
            DESCRIPTION
                    "lldpStatsRxPortFramesErrors has been replaced by
                     TIMETRA-LLDP-MIB::tmnxLldpStatsRxPortFrameErrs."

        VARIATION   lldpStatsRxPortFramesTotal
            ACCESS  not-implemented
            DESCRIPTION
                    "lldpStatsRxPortFramesTotal has been replaced by
                     TIMETRA-LLDP-MIB::tmnxLldpStatsRxPortFrames."

        VARIATION   lldpStatsRxPortTLVsDiscardedTotal
            ACCESS  not-implemented
            DESCRIPTION
                    "lldpStatsRxPortTLVsDiscardedTotal has been replaced by
                     TIMETRA-LLDP-MIB::tmnxLldpStatsRxPortTLVDiscard."

        VARIATION   lldpStatsRxPortTLVsUnrecognizedTotal
            ACCESS  not-implemented
            DESCRIPTION
                    "lldpStatsRxPortTLVsUnrecognizedTotal has been replaced
                     with TIMETRA-LLDP-MIB::tmnxLldpStatsRxPortTLVUnknown."

        VARIATION   lldpStatsRxPortAgeoutsTotal
            ACCESS  not-implemented
            DESCRIPTION
                    "lldpStatsRxPortAgeoutsTotal has been replaced by
                     TIMETRA-LLDP-MIB::tmnxLldpStatsRxPortAgeouts."

        VARIATION   lldpLocPortIdSubtype
            ACCESS  not-implemented
            DESCRIPTION
                    "lldpLocPortIdSubtype has been replaced by
                     TIMETRA-LLDP-MIB::tmnxLldpLocPortIdSubtype."

        VARIATION   lldpLocPortId
            ACCESS  not-implemented
            DESCRIPTION
                    "lldpLocPortId has been replaced by
                     TIMETRA-LLDP-MIB::tmnxLldpLocPortId."

        VARIATION   lldpLocPortDesc
            ACCESS  not-implemented
            DESCRIPTION
                    "lldpLocPortDesc has been replaced by
                     TIMETRA-LLDP-MIB::tmnxLldpLocPortDesc."

    ::= { tmnxSROSV10v0 65 }  -- LLDP

--
--  L2TP CAPABILITIES
--
tmnxSROSL2tpCapsV10v0 AGENT-CAPABILITIES
    PRODUCT-RELEASE "Alcatel-Lucent SROS"
    STATUS current
    DESCRIPTION
        "Implementation of the L2TP (Layer Two Tunneling Protocol) feature
         on Alcatel-Lucent SROS release R10.0."

    SUPPORTS TIMETRA-L2TP-MIB
        INCLUDES    {
            tmnxL2tpCfgV8v0Group,
            tmnxL2tpTgCfgGroup,
            tmnxL2tpTuCfgGroup,
            tmnxL2tpStatV8v0Group,
            tmnxL2tpTgStatGroup,
            tmnxL2tpTuStatGroup,
            tmnxL2tpPeerStatV8v0Group,
            tmnxL2tpSeStatGroup,
            tmnxL2tpTgOpGroup,
            tmnxL2tpTuOpGroup,
            tmnxL2tpPeerOpGroup,
            tmnxL2tpSeOpGroup,
-- EXCLUDE  tmnxL2tpLnsIsaGroup             not supported on SPR
-- EXCLUDE  tmnxL2tpLnsIsaStatGroup         not supported on SPR
            tmnxL2tpLnsTgGroup,
            tmnxL2tpLnsTgV9v0Group,
            tmnxL2tpLnsTuGroup,
            tmnxL2tpLnsTuV9v0Group,
            tmnxL2tpLnsSeV9v0Group,
-- EXCLUDE  tmnxL2tpLnsIfV9v0Group          not supported on SPR
            tmnxL2tpNotifyObjsGroup,
            tmnxL2tpNotifyObjsV9v0Group,
            tmnxL2tpNotifyGroup,
            tmnxL2tpNotifyV9v0Group,
            tmnxL2tpNotifyV10v0Group,
            tmnxL2tpMlpppGroup,
            tmnxL2tpTgV10v0Group,
            tmnxL2tpTuV10v0Group,
            tmnxL2tpAccountingGroup
-- EXCLUDE  tmnxL2tpFilterProfileV9v0Group  not supported in release 9.0
        }

        VARIATION   tmnxL2tpAdminState
            SYNTAX  INTEGER {
                        -- noop         (1),
                        inService       (2),
                        outOfService    (3)
                    }
            DESCRIPTION
                    "The only allowed values for this object are 'inService (2)'
                    and 'outOfService (3)'."

        VARIATION   tmnxL2tpTgCfgAdminState
            SYNTAX  INTEGER {
                        -- noop         (1),
                        inService       (2),
                        outOfService    (3)
                    }
            DESCRIPTION
                    "The only allowed values for this object are 'inService (2)'
                    and 'outOfService (3)'."

        VARIATION   tmnxL2tpTuCfgAdminState
            SYNTAX  INTEGER {
                        -- noop         (1),
                        inService       (2),
                        outOfService    (3)
                    }
            DESCRIPTION
                    "The only allowed values for this object are 'inService (2)'
                    and 'outOfService (3)'."

        VARIATION   tmnxL2tpTgCfgRowStatus
            SYNTAX  INTEGER {
                        active      (1),
                        createAndGo (4),
                        destroy     (6)
                     }
            DESCRIPTION
                    "The only allowed values for this object are
                    'active (1)', 'createAndGo (4)' and 'destroy (6)'."

        VARIATION   tmnxL2tpTuCfgRowStatus
            SYNTAX  INTEGER {
                        active      (1),
                        createAndGo (4),
                        destroy     (6)
                     }
            DESCRIPTION
                    "The only allowed values for this object are
                    'active (1)', 'createAndGo (4)' and 'destroy (6)'."

        VARIATION   tmnxL2tpTgCfgAddrType
            SYNTAX  INTEGER {
                        unknown(0),
                        ipv4(1)
                    }
            DESCRIPTION
                    "The only allowed values for this object are 'unknown(0)'
                     and 'ipv4(1)'."

        VARIATION   tmnxL2tpTgCfgAddr
            SYNTAX  InetAddress (SIZE(0|4))
            DESCRIPTION
                    "The only values allowed for this object are ''H and
                     IPv4 addresses."

        VARIATION   tmnxL2tpTuCfgPeerAddrType
            SYNTAX  INTEGER {
                        unknown(0),
                        ipv4(1)
                    }
            DESCRIPTION
                    "The only allowed values for this object are 'unknown(0)'
                     and 'ipv4(1)'."

        VARIATION   tmnxL2tpTuCfgPeerAddr
            SYNTAX  InetAddress (SIZE(0|4))
            DESCRIPTION
                    "The only values allowed for this object are ''H and
                     IPv4 addresses."

        VARIATION   tmnxL2tpTuCfgAddrType
            SYNTAX  INTEGER {
                        unknown(0),
                        ipv4(1)
                    }
            DESCRIPTION
                    "The only allowed values for this object are 'unknown(0)'
                     and 'ipv4(1)'.

                     In case of a LAC tunnel, the only allowed value for this
                     object is 'unknown (0)'; the value used instead is
                     the actual value of the object vRiaInetAddressType
                     of the entry corresponding to the system interface."

        VARIATION   tmnxL2tpTuCfgAddr
            SYNTAX  InetAddress (SIZE(0|4))
            DESCRIPTION
                    "The only values allowed for this object are ''H and
                     IPv4 addresses.

                     In case of a LAC tunnel, the only allowed value
                     for this object is ''H; the value used instead
                     is the value of the object vRiaInetAddress
                     of the entry corresponding to the system interface."

        VARIATION   tmnxL2tpTuCfgSessionLimit
            SYNTAX  TmnxL2tpTunnelSessionLimit (1..65535)
            DESCRIPTION
                    "The number of sessions allowed for a tunnel is currently
                     limited to 65535.

                     The reason is that currently only L2TP version 2 is
                     supported, and version 2 uses a 16 bit number to identify
                     a session."

        VARIATION   tmnxL2tpTgMlpppAdminState
            SYNTAX  INTEGER {
                        -- noop         (1),
                        inService       (2),
                        outOfService    (3)
                    }
            DESCRIPTION
                    "The only allowed values for this object are 'inService (2)'
                    and 'outOfService (3)'."

        VARIATION   tmnxL2tpTuMlpppAdminState
            SYNTAX  INTEGER {
                        -- noop         (1),
                        inService       (2),
                        outOfService    (3)
                    }
            DESCRIPTION
                    "The only allowed values for this object are 'inService (2)'
                    and 'outOfService (3)'."

        VARIATION   tmnxL2tpApRowStatus
            SYNTAX  INTEGER {
                        active      (1),
                        createAndGo (4),
                        destroy     (6)
                     }
            DESCRIPTION
                    "The only allowed values for this object are
                    'active (1)', 'createAndGo (4)' and 'destroy (6)'."
                    

        VARIATION   tmnxL2tpApServerSrcAddrType
            SYNTAX  InetAddressType (0|1)
            DESCRIPTION
                    "The only values supported are 'unknown' (0) and 'ipv4' (1)."

        VARIATION   tmnxL2tpApServerSrcAddr
            SYNTAX      InetAddress (SIZE(0|4))
            DESCRIPTION
                    "Only empty or IPv4 addresses are allowed."

        VARIATION   tmnxL2tpApServRowStatus
            SYNTAX  INTEGER {
                        active      (1),
                        createAndGo (4),
                        destroy     (6)
                     }
            DESCRIPTION
                    "The only allowed values for this object are
                    'active (1)', 'createAndGo (4)' and 'destroy (6)'."
                    
        VARIATION   tmnxL2tpApServAddrType
            SYNTAX  InetAddressType (1)
            DESCRIPTION
                    "The only value supported is 'ipv4' (1)."

        VARIATION   tmnxL2tpApServAddr
            SYNTAX      InetAddress (SIZE(4))
            DESCRIPTION
                    "Only IPv4 addresses are allowed."

    ::= { tmnxSROSV10v0 66 } -- L2TP

tmnx7750L2tpCapsV10v0 AGENT-CAPABILITIES
    PRODUCT-RELEASE "Alcatel-Lucent SROS"
    STATUS current
    DESCRIPTION
        "Implementation of the L2TP (Layer Two Tunneling Protocol) feature
         on Alcatel-Lucent 7750 release R10.0."

    SUPPORTS TIMETRA-L2TP-MIB
        INCLUDES    {
            tmnxL2tpLnsIsaGroup,
            tmnxL2tpLnsIsaV10v0Group,
            tmnxL2tpLnsIsaStatGroup,
            tmnxL2tpLnsIfV9v0Group
        }

        VARIATION   tmnxL2tpLnsIfDefSubIdent
            SYNTAX  INTEGER {
                     -- useSapId  (1),
                        useString (2)
                    }
            DESCRIPTION
                "The only allowed value for this object is 'useString (2)'."

    ::= { tmnxSROSL2tpCapsV10v0 1 }  -- L2TP 7750

tmnx7450L2tpCapsV10v0 AGENT-CAPABILITIES
    PRODUCT-RELEASE "Alcatel-Lucent SROS"
    STATUS current
    DESCRIPTION
        "Implementation of the L2TP (Layer Two Tunneling Protocol) feature
         on Alcatel-Lucent 7450 release R10.0."

    SUPPORTS TIMETRA-L2TP-MIB
        INCLUDES    {
            tmnxL2tpLnsIsaGroup,
            tmnxL2tpLnsIsaV10v0Group,
            tmnxL2tpLnsIsaStatGroup,
            tmnxL2tpLnsIfV9v0Group
        }

        VARIATION   tmnxL2tpLnsIfDefSubIdent
            SYNTAX  INTEGER {
                     -- useSapId  (1),
                        useString (2)
                    }
            DESCRIPTION
                "The only allowed value for this object is 'useString (2)'."

    ::= { tmnxSROSL2tpCapsV10v0 2 }  -- L2TP 7450

tmnx7710L2tpCapsV10v0    AGENT-CAPABILITIES
    PRODUCT-RELEASE "Alcatel-Lucent SROS"
    STATUS          current
    DESCRIPTION
        "Implementation of the L2TP (Layer Two Tunneling Protocol) feature
         on Alcatel-Lucent 7710 release R10.0."

--    SUPPORTS        TIMETRA-L2TP-MIB
--        INCLUDES    {
--        }

--          L2TP is not supported on SROS 7710

    ::= { tmnxSROSL2tpCapsV10v0 3 }  -- L2TP 7710

tmnx7950L2tpCapsV10v0    AGENT-CAPABILITIES
    PRODUCT-RELEASE "Alcatel-Lucent SROS"
    STATUS          current
    DESCRIPTION
        "The L2TP (Layer Two Tunneling Protocol) feature is not supported
         on Alcatel-Lucent 7950 release R10.0."

--    SUPPORTS        TIMETRA-L2TP-MIB
--        INCLUDES    { }
    ::= { tmnxSROSL2tpCapsV10v0 4 }  -- L2TP 7950

--
--  OTU CAPABILITIES
--
tmnxSROSOTUCapsV10v0              AGENT-CAPABILITIES
    PRODUCT-RELEASE "Alcatel-Lucent SROS"
    STATUS current
    DESCRIPTION
        "Implementation of the OTU (Optical Transport Unit) feature
         on Alcatel-Lucent SROS release R10.0."

    SUPPORTS TIMETRA-OTU-MIB
        INCLUDES    {
            tmnxOtuIfBaseConfigGroupV8v0,
            tmnxOtuIfSMGroup,
            tmnxOtuIfSMGroupV8v0,
            tmnxOtuIfPMGroupV8v0,
            tmnxOtuIfPSIGroupV8v0,
            tmnxOtuStatsGroup,
            tmnxOtuStatsGroupV8v0,
            tmnxOtuNotificationGroup
        }

    ::= { tmnxSROSV10v0 67 }  -- OTU

--
-- ETH-TUNNEL CAPABILITIES
--
tmnxSROSEthTunnelCapsV10v0        AGENT-CAPABILITIES
    PRODUCT-RELEASE "Alcatel-Lucent SROS"
    STATUS current
    DESCRIPTION
        "Implementation of the Ethernet Tunnel feature
         on Alcatel-Lucent SROS release R10.0."

    SUPPORTS TIMETRA-ETH-TUNNEL-MIB
        INCLUDES    {
            tmnxEthTunnelTimeStampGroup,
            tmnxEthTunnelTimeStampV8v0Group,
            tmnxEthTunnelBaseConfigGroup,
            tmnxEthTunnelBaseConfigV8v0Group,
            tmnxEthTunnelBaseOperGroup,
            tmnxEthTunnelBaseMemberGroup,
            tmnxEthTunnelBaseAPSGroup,
            tmnxEthTunnelBaseAPSV8v0Group,
            tmnxEthTunnelLEGroup,
            tmnxEthTunnelSAPMemberGroup,
            tmnxEthTunnelAPSNotifyGroup
        }

        VARIATION tmnxEthTunnelIndex
            SYNTAX  Unsigned32 (1..1024)
            DESCRIPTION
                "The tmnxEthTunnelIndex is restricted to the values 1 to 1024.
                 If the tmnxChassisAdminMode is set to a value less than
                 'modeD (4)' the tmnxEthTunnelIndex is restricted to a maximum
                 value of 128."

        VARIATION tmnxEthTunnelRowStatus
            SYNTAX  INTEGER {
                        active      (1),
                        createAndGo (4),
                        destroy     (6)
                     }
            DESCRIPTION
                "The only allowed values for this object are
                'active (1)', 'createAndGo (4)' and 'destroy (6)'."

        VARIATION tmnxEthTunnelMemberIndex
            SYNTAX  Unsigned32 (1..16)
            DESCRIPTION
                "The tmnxEthTunnelMemberIndex is restricted to the
                 values 1 to 16. If the tmnxChassisAdminMode is set to a value
                 less than 'modeD (4)' the tmnxEthTunnelMemberIndex is
                 restricted to a maximum value of 8."

        VARIATION tmnxEthTunnelMemberRowStatus
            SYNTAX  INTEGER {
                        active      (1),
                        createAndGo (4),
                        destroy     (6)
                     }
            DESCRIPTION
                "The only allowed values for this object are
                'active (1)', 'createAndGo (4)' and 'destroy (6)'."

        VARIATION tmnxEthTunnelLEMbrThreshold
            SYNTAX  Unsigned32 (0..15)
            DESCRIPTION
                "The tmnxEthTunnelLEMbrThreshold is restricted to the
                 values 0 to one less than the maximum value of
                 tmnxEthTunnelMemberIndex. "

    ::= { tmnxSROSV10v0 68 }  -- ETH-TUNNEL

tmnxSprEthTunnelCapsV10v0        AGENT-CAPABILITIES
    PRODUCT-RELEASE "Alcatel-Lucent SROS"
    STATUS current
    DESCRIPTION
        "Implementation of specific Ethernet Tunnel capabilities
         on Alcatel-Lucent SROS SPR release R10.0."

--    SUPPORTS TIMETRA-ETH-TUNNEL-MIB
--        INCLUDES    {
--        }

-- Ethernet Tunnel is not supported on SROS SPR systems.

    ::= { tmnxSROSEthTunnelCapsV10v0 3 }  -- SPR ETH-TUNNEL

--
--  NAT CAPABILITIES
--
tmnxSROSNatCapsV10v0 AGENT-CAPABILITIES
    PRODUCT-RELEASE "Alcatel-Lucent SROS"
    STATUS current
    DESCRIPTION
        "Implementation of the NAT (Network Address Translation) feature
         on Alcatel-Lucent SROS release R10.0."

    SUPPORTS TIMETRA-NAT-MIB
        INCLUDES    {
            tmnxNatIsaV10v0Group,
            tmnxNatIsaStatGroup,
            tmnxNatIsaStatV10v0Group,
            tmnxNatPlcyGroup,
            tmnxNatPlcyV9v0Group,
            tmnxNatPlcyV10v0Group,
            tmnxNatPlcyStatGroup,
            tmnxNatVrtrGroup,
            tmnxNatVrtrV9v0Group,
            tmnxNatRedGroup,
            tmnxNatPlGroup,
            tmnxNatPlV9v0Group,
            tmnxNatDestGroup,
            tmnxNatL2AwGroup,
            tmnxNatLsnGroup,
            tmnxNatLsnV9v0Group,
            tmnxNatFwdGroup,
            tmnxNatDestNatGroup,
            tmnxNatAccGroup,
            tmnxNatWlanGwGroup,
            tmnxNat64Group,
            tmnxNatLsnSubIdentGroup,
            tmnxNatPcpGroup,
            tmnxNatNotifyGroup,
            tmnxNatNotifyV9v0Group,
            tmnxNatNotifyV10v0Group
        }

        VARIATION   tmnxNatIsaGrpAdminState
            SYNTAX  INTEGER {
                        -- noop         (1),
                        inService       (2),
                        outOfService    (3)
                    }
            DESCRIPTION
                    "The only allowed values for this object are 'inService (2)'
                    and 'outOfService (3)'."

        VARIATION   tmnxNatPlAdminState
            SYNTAX  INTEGER {
                        -- noop         (1),
                        inService       (2),
                        outOfService    (3)
                    }
            DESCRIPTION
                    "The only allowed values for this object are 'inService (2)'
                    and 'outOfService (3)'."

        VARIATION   tmnxNatIsaGrpRowStatus
            SYNTAX  INTEGER {
                        active      (1),
                        createAndGo (4),
                        destroy     (6)
                    }
            DESCRIPTION
                    "The only allowed values for this object are
                    'active (1)', 'createAndGo (4)' and 'destroy (6)'."

        VARIATION   tmnxNatIsaMdaRowStatus
            SYNTAX  INTEGER {
                        active      (1),
                        createAndGo (4),
                        destroy     (6)
                    }
            DESCRIPTION
                    "The only allowed values for this object are
                    'active (1)', 'createAndGo (4)' and 'destroy (6)'."

        VARIATION   tmnxNatPlcyRowStatus
            SYNTAX  INTEGER {
                        active      (1),
                        createAndGo (4),
                        destroy     (6)
                    }
            DESCRIPTION
                    "The only allowed values for this object are
                    'active (1)', 'createAndGo (4)' and 'destroy (6)'."

        VARIATION   tmnxNatPlRowStatus
            SYNTAX  INTEGER {
                        active      (1),
                        createAndGo (4),
                        destroy     (6)
                    }
            DESCRIPTION
                    "The only allowed values for this object are
                    'active (1)', 'createAndGo (4)' and 'destroy (6)'."

        VARIATION   tmnxNatPlRangeRowStatus
            SYNTAX  INTEGER {
                        active      (1),
                        createAndGo (4),
                        destroy     (6)
                    }
            DESCRIPTION
                    "The only allowed values for this object are
                    'active (1)', 'createAndGo (4)' and 'destroy (6)'."

        VARIATION   tmnxNatDestRowStatus
            SYNTAX  INTEGER {
                        active      (1),
                        createAndGo (4),
                        destroy     (6)
                    }
            DESCRIPTION
                    "The only allowed values for this object are
                    'active (1)', 'createAndGo (4)' and 'destroy (6)'."

        VARIATION   tmnxNatL2AwAddrRowStatus
            SYNTAX  INTEGER {
                        active      (1),
                        createAndGo (4),
                        destroy     (6)
                    }
            DESCRIPTION
                    "The only allowed values for this object are
                    'active (1)', 'createAndGo (4)' and 'destroy (6)'."

        VARIATION   tmnxNatPlcyFiltering
            SYNTAX  INTEGER {
                       endpointIndependent     (0),
                       addressAndPortDependent (2)
                    }
            DESCRIPTION
                    "The only allowed values for this object are
                    'endpointIndependent (0)' and
                    'addressAndPortDependent (2)'."

        VARIATION   tmnxNatPlPortResvAllowPrivileged
            SYNTAX  INTEGER {
                     -- true (1),
                        false(2)
                    }
            DESCRIPTION
                    "The only allowed value for this object is 'false (2)'."

        VARIATION   tmnxNatFwdActionAddrType
            SYNTAX  InetAddressType (0|1|2)
            DESCRIPTION
                    "The only values supported are 'unknown', 'ipv4' and 'ipv6' ."

        VARIATION   tmnxNatFwdActionAddr
            SYNTAX      InetAddress (SIZE(0|4|16))
            DESCRIPTION
                    "Only empty, IPv4 or IPv6 addresses are allowed."

        VARIATION   tmnxNatFwdActionProtocol
            SYNTAX  Unsigned32 (6|17)
            DESCRIPTION
                    "The only values supported are six (TCP) and seventeen (UDP)."

        VARIATION   tmnxNatVrtrInRedPeerAddrType
            SYNTAX  InetAddressType (0|1)
            DESCRIPTION
                    "The only values supported are 'unknown' (0) and 'ipv4' (1)."

        VARIATION   tmnxNatVrtrInRedPeerAddr
            SYNTAX      InetAddress (SIZE(0|4))
            DESCRIPTION
                    "Only empty or IPv4 addresses are allowed."

        VARIATION   tmnxNatVrtrInRedSteerRtType
            SYNTAX  InetAddressType (0|1)
            DESCRIPTION
                    "The only values supported are 'unknown' (0) and 'ipv4' (1)."

        VARIATION   tmnxNatVrtrInRedSteerRt
            SYNTAX      InetAddress (SIZE(0|4))
            DESCRIPTION
                    "Only empty or IPv4 addresses are allowed."

        VARIATION   tmnxNatPlLsnRedExpPrefixType
            SYNTAX  InetAddressType (0|1)
            DESCRIPTION
                    "The only values supported are 'unknown' (0) and 'ipv4' (1)."

        VARIATION   tmnxNatPlLsnRedExpPrefix
            SYNTAX      InetAddress (SIZE(0|4))
            DESCRIPTION
                    "Only empty or IPv4 addresses are allowed."

        VARIATION   tmnxNatPlLsnRedMonPrefixType
            SYNTAX  InetAddressType (0|1)
            DESCRIPTION
                    "The only values supported are 'unknown' (0) and 'ipv4' (1)."

        VARIATION   tmnxNatPlLsnRedMonPrefix
            SYNTAX      InetAddress (SIZE(0|4))
            DESCRIPTION
                    "Only empty or IPv4 addresses are allowed."

        VARIATION   tmnxNatPlcyDestNatAddrType
            SYNTAX  InetAddressType (0)
            DESCRIPTION
                    "The only value supported is 'unknown' (0).
                     Destination NAT is not supported."

        VARIATION   tmnxNatPlcyDestNatAddr
            SYNTAX      InetAddress (SIZE(0))
            DESCRIPTION
                    "Only empty addresses are allowed.
                     Destination NAT is not supported."

        VARIATION   tmnxNatApRowStatus
            SYNTAX  INTEGER {
                        active      (1),
                        createAndGo (4),
                        destroy     (6)
                     }
            DESCRIPTION
                    "The only allowed values for this object are
                        'active (1)', 'createAndGo (4)' and 'destroy (6)'."

        VARIATION   tmnxNatApServersSrcAddrType
            SYNTAX  INTEGER {
                        unknown     (0),
                        ipv4        (1)
                    }
            DESCRIPTION
                    "tmnxNatApServersSrcAddrType supports only InetAddressType
                     values 'unknown (0)' and 'ipv4 (1)'."

        VARIATION   tmnxNatApServRowStatus
            SYNTAX  INTEGER {
                        active      (1),
                        createAndGo (4),
                        destroy     (6)
                     }
            DESCRIPTION
                    "The only allowed values for this object are
                     'active (1)', 'createAndGo (4)' and 'destroy (6)'."
        
        VARIATION   tmnxNatApServAddrType
            SYNTAX  INTEGER {
                        ipv4        (1)
                    }
            DESCRIPTION
                    "tmnxNatApServAddrType supports only InetAddressType
                     the value 'ipv4 (1)'."

        VARIATION   tmnxNat64RowStatus
            SYNTAX  INTEGER {
                        active      (1),
                        createAndGo (4),
                        destroy     (6)
                    }
            DESCRIPTION
                    "The only allowed values for this object are
                    'active (1)', 'createAndGo (4)' and 'destroy (6)'."

        VARIATION   tmnxNat64InAdminState
            SYNTAX  INTEGER {
                        -- noop         (1),
                        inService       (2),
                        outOfService    (3)
                    }
            DESCRIPTION
                    "The only allowed values for this object are 'inService (2)'
                    and 'outOfService (3)'."

        VARIATION   tmnxNatSubIdAdminState
            SYNTAX  INTEGER {
                        -- noop         (1),
                        inService       (2),
                        outOfService    (3)
                    }
            DESCRIPTION
                    "The only allowed values for this object are 'inService (2)'
                    and 'outOfService (3)'."
                    
        VARIATION   tmnxNatPcpPlcyRowStatus
            SYNTAX  INTEGER {
                        active      (1),
                        createAndGo (4),
                        destroy     (6)
                    }
            DESCRIPTION
                    "The only allowed values for this object are
                    'active (1)', 'createAndGo (4)' and 'destroy (6)'."

        VARIATION   tmnxNatPcpSrvRowStatus
            SYNTAX  INTEGER {
                        active      (1),
                        createAndGo (4),
                        destroy     (6)
                    }
            DESCRIPTION
                    "The only allowed values for this object are
                    'active (1)', 'createAndGo (4)' and 'destroy (6)'."

                                       
    ::= { tmnxSROSV10v0 69 }  -- NAT

tmnx7450NatCapsV10v0 AGENT-CAPABILITIES
    PRODUCT-RELEASE "Alcatel-Lucent SROS"
    STATUS current
    DESCRIPTION
        "Implementation of specific NAT (Network Address Translation)
         capabilities on Alcatel-Lucent SROS 7450 release R10.0."

--    SUPPORTS TIMETRA-NAT-MIB
--        INCLUDES    {
--        }

-- NAT is not implemented on the SROS 7450.

    ::= { tmnxSROSNatCapsV10v0 2 }  -- 7450 NAT

tmnxSprNatCapsV10v0 AGENT-CAPABILITIES
    PRODUCT-RELEASE "Alcatel-Lucent SROS"
    STATUS current
    DESCRIPTION
        "Implementation of specific NAT (Network Address Translation)
         capabilities on Alcatel-Lucent SROS SPR release R10.0."

--    SUPPORTS TIMETRA-NAT-MIB
--        INCLUDES    {
--        }

-- NAT is not implemented on the SPR.

    ::= { tmnxSROSNatCapsV10v0 3 }  -- SPR NAT

tmnx7950NatCapsV10v0 AGENT-CAPABILITIES
    PRODUCT-RELEASE "Alcatel-Lucent SROS"
    STATUS current
    DESCRIPTION
        "NAT (Network Address Translation)
         is not supported on Alcatel-Lucent SROS 7950 release R10.0."

--    SUPPORTS TIMETRA-NAT-MIB
--        INCLUDES    {
--        }


    ::= { tmnxSROSNatCapsV10v0 4 }  -- 7950 NAT

--
--    Video CAPABILITIES
--
tmnxSROSVideoCapsV10v0 AGENT-CAPABILITIES
     PRODUCT-RELEASE "Alcatel-Lucent SROS"
     STATUS          current
     DESCRIPTION
         "Implementation of the video features on
          Alcatel-Lucent-Lucent SROS release R10.0."

     SUPPORTS TIMETRA-VIDEO-MIB
        INCLUDES    {
            tmnxVdoGlobalV7v0Group,
            tmnxVdoIfV7v0Group,
            tmnxVdoGrpV7v0Group,
            tmnxVdoGrpSrcV7v0Group,
            tmnxVdoAdiV7v0Group,
            tmnxVdoStatsV7v0Group,
            tmnxVdoNotificationsV7v0Group,
            tmnxVdoGrpV8v0Group,
            tmnxVdoIfV8v0Group,
            tmnxVdoNotificationsV8v0Group,
            tmnxVdoStatsV9v0Group
        }

        VARIATION   tmnxVdoIfRowStatus
            SYNTAX  INTEGER {
                        active      (1),
                        createAndGo (4),
                        destroy     (6)
                    }
            DESCRIPTION
                    "The only allowed values for this object are
                    'active (1)', 'createAndGo (4)' and 'destroy (6)'."

        VARIATION   tmnxVdoIfAddrRowStatus
            SYNTAX  INTEGER {
                        active      (1),
                        createAndGo (4),
                        destroy     (6)
                    }
            DESCRIPTION
                    "The only allowed values for this object are
                    'active (1)', 'createAndGo (4)' and 'destroy (6)'."


        VARIATION   tmnxVdoGrpRowStatus
            SYNTAX  INTEGER {
                        active      (1),
                        createAndGo (4),
                        destroy     (6)
                    }
            DESCRIPTION
                    "The only allowed values for this object are
                    'active (1)', 'createAndGo (4)' and 'destroy (6)'."

        VARIATION   tmnxVdoGrpMdaRowStatus
            SYNTAX  INTEGER {
                        active      (1),
                        createAndGo (4),
                        destroy     (6)
                    }
            DESCRIPTION
                    "The only allowed values for this object are
                    'active (1)', 'createAndGo (4)' and 'destroy (6)'."

        VARIATION   tmnxVdoAdiChlRowStatus
            SYNTAX  INTEGER {
                        active      (1),
                        createAndGo (4),
                        destroy     (6)
                    }
            DESCRIPTION
                    "The only allowed values for this object are
                    'active (1)', 'createAndGo (4)' and 'destroy (6)'."

        VARIATION   tmnxVdoAdiZoneChlRowStatus
            SYNTAX  INTEGER {
                        active      (1),
                        createAndGo (4),
                        destroy     (6)
                    }
            DESCRIPTION
                    "The only allowed values for this object are
                    'active (1)', 'createAndGo (4)' and 'destroy (6)'."

        VARIATION   tmnxVdoIfScte30AdSrvrRowStatus
            SYNTAX  INTEGER {
                        active      (1),
                        createAndGo (4),
                        destroy     (6)
                    }
            DESCRIPTION
                    "The only allowed values for this object are
                    'active (1)', 'createAndGo (4)' and 'destroy (6)'."

        VARIATION   tmnxVdoIfAdminState
            SYNTAX  INTEGER {
                        inService       (2),
                        outOfService    (3)
                    }
            DESCRIPTION
                    "The only allowed values for this object are
                     'inService (2)' and 'outOfService (3)'."

        VARIATION   tmnxVdoGrpAdminState
            SYNTAX  INTEGER {
                        inService       (2),
                        outOfService    (3)
                    }
            DESCRIPTION
                    "The only allowed values for this object are
                     'inService (2)' and 'outOfService (3)'."

        VARIATION   tmnxVdoGrpMdaAdminState
            SYNTAX  INTEGER {
                        inService       (2),
                        outOfService    (3)
                    }
            DESCRIPTION
                    "The only supported values for this object are
                     'inService (2)' and 'outOfService (3)'."

        VARIATION   tmnxVdoGrpSrcRTClientAdminState
            SYNTAX  INTEGER {
                        inService       (2),
                        outOfService    (3)
                    }
            DESCRIPTION
                "The only supported values for this object are
                 'inService (2)' and 'outOfService (3)'."

        VARIATION   tmnxVdoGrpSrcRTSrvrAdminState
            SYNTAX  INTEGER {
                        inService       (2),
                        outOfService    (3)
                    }
            DESCRIPTION
                "The only supported values for this object are
                 'inService (2)' and 'outOfService (3)'."

        VARIATION   tmnxVdoGrpSrcFCCSrvrAdminState
            SYNTAX  INTEGER {
                        inService       (2),
                        outOfService    (3)
                    }
            DESCRIPTION
                "The only supported values for this object are
                 'inService (2)' and 'outOfService (3)'."

        VARIATION   tmnxVdoGrpSrcADIAdminState
            SYNTAX  INTEGER {
                        inService       (2),
                        outOfService    (3)
                    }
            DESCRIPTION
                "The only supported values for this object are
                 'inService (2)' and 'outOfService (3)'."

        VARIATION   tmnxVdoIfOperState
            SYNTAX  INTEGER {
                        inService       (2),
                        outOfService    (3)
                    }
            DESCRIPTION
                "The only supported values for this object are
                 'inService (2)' and 'outOfService (3)'."

        VARIATION   tmnxVdoGrpOperState
            SYNTAX  INTEGER {
                        inService       (2),
                        outOfService    (3)
                    }
            DESCRIPTION
                "The only supported values for this object are
                 'inService (2)' and 'outOfService (3)'."

        VARIATION   tmnxVdoGrpMdaOperState
            SYNTAX  INTEGER {
                        inService       (2),
                        outOfService    (3)
                    }
            DESCRIPTION
                "The only supported values for this object are
                 'inService (2)' and 'outOfService (3)'."

        VARIATION   tmnxVdoIfRTClientAddrType
            SYNTAX  INTEGER {
                        unknown     (0),
                        ipv4        (1)
                    }
            DESCRIPTION
                    "tmnxVdoIfRTClientAddrType only supports the values
                    'unknown' and 'ipv4' as defined by the InetAddressType
                    textual convention."

        VARIATION   tmnxVdoIfRTClientAddr
            SYNTAX  InetAddress (SIZE (0|4))
            DESCRIPTION
                    "tmnxVdoIfRTClientAddr only supports the InetAddressType
                     values 'unknown' and 'ipv4'."

        VARIATION   tmnxVdoIfGatewayAddrType
            SYNTAX  INTEGER {
                        unknown     (0),
                        ipv4        (1)
                    }
            DESCRIPTION
                    "tmnxVdoIfGatewayAddrType only supports the values
                    'unknown' and 'ipv4' as defined by the InetAddressType
                    textual convention."

        VARIATION   tmnxVdoIfGatewayAddr
            SYNTAX  InetAddress (SIZE (0|4))
            DESCRIPTION
                    "tmnxVdoIfGatewayAddr only supports the InetAddressType
                     values 'unknown' and 'ipv4'."

        VARIATION   tmnxVdoIfScte30ControlAddrType
            SYNTAX  INTEGER {
                        unknown     (0),
                        ipv4        (1)
                    }
            DESCRIPTION
                    "tmnxVdoIfScte30ControlAddrType only supports the values
                    'unknown' and 'ipv4' as defined by the InetAddressType
                    textual convention."

        VARIATION   tmnxVdoIfScte30ControlAddr
            SYNTAX  InetAddress (SIZE (0|4))
            DESCRIPTION
                    "tmnxVdoIfScte30ControlAddr only supports the
                     InetAddressType values 'unknown' and 'ipv4'."

        VARIATION   tmnxVdoIfScte30DataAddrType
            SYNTAX  INTEGER {
                        unknown     (0),
                        ipv4        (1)
                    }
            DESCRIPTION
                    "tmnxVdoIfScte30DataAddrType only supports the values
                    'unknown' and 'ipv4' as defined by the InetAddressType
                    textual convention."

        VARIATION   tmnxVdoIfScte30DataAddr
            SYNTAX  InetAddress (SIZE (0|4))
            DESCRIPTION
                    "tmnxVdoIfScte30DataAddr only supports the InetAddressType
                     values 'unknown' and 'ipv4'."

        VARIATION   tmnxVdoIfAddrIpAddrType
            SYNTAX  INTEGER {
                        ipv4        (1)
                    }
            DESCRIPTION
                    "tmnxVdoIfAddrIpAddrType only supports the value 'ipv4' as
                     defined by the InetAddressType textual convention."

        VARIATION   tmnxVdoIfAddrIpAddress
            SYNTAX  InetAddress (SIZE (4))
            DESCRIPTION
                    "tmnxVdoIfAddrIpAddress only supports the InetAddressType
                     value 'ipv4'."

        VARIATION   tmnxVdoAdiChlGrpAddrType
            SYNTAX  INTEGER {
                        ipv4        (1)
                    }
            DESCRIPTION
                    "tmnxVdoAdiChlGrpAddrType only supports the value 'ipv4' as
                     defined by the InetAddressType textual convention."

        VARIATION   tmnxVdoAdiChlGrpAddress
            SYNTAX  InetAddress (SIZE (4))
            DESCRIPTION
                    "tmnxVdoAdiChlGrpAddress only supports the InetAddressType
                     value 'ipv4'."

        VARIATION   tmnxVdoAdiChlSrcAddrType
            SYNTAX  INTEGER {
                        ipv4        (1)
                    }
            DESCRIPTION
                    "tmnxVdoAdiChlSrcAddrType only supports the value 'ipv4' as
                     defined by the InetAddressType textual convention."

        VARIATION   tmnxVdoAdiChlSrcAddress
            SYNTAX  InetAddress (SIZE (4))
            DESCRIPTION
                    "tmnxVdoAdiChlSrcAddress only supports the InetAddressType
                     value 'ipv4'."

        VARIATION   tmnxVdoAdiZoneChlGrpAddrType
            SYNTAX  INTEGER {
                        ipv4        (1)
                    }
            DESCRIPTION
                    "tmnxVdoAdiZoneChlGrpAddrType only supports the value
                     'ipv4' as defined by the InetAddressType textual
                     convention."

        VARIATION   tmnxVdoAdiZoneChlGrpAddress
            SYNTAX  InetAddress (SIZE (4))
            DESCRIPTION
                    "tmnxVdoAdiZoneChlGrpAddress only supports the
                     InetAddressType value 'ipv4'."

        VARIATION   tmnxVdoAdiZoneChlSrcAddrType
            SYNTAX  INTEGER {
                        ipv4        (1)
                    }
            DESCRIPTION
                    "tmnxVdoAdiZoneChlSrcAddrType only supports the value
                     'ipv4' as defined by the InetAddressType textual
                     convention."

        VARIATION   tmnxVdoAdiZoneChlSrcAddress
            SYNTAX  InetAddress (SIZE (4))
            DESCRIPTION
                    "tmnxVdoAdiZoneChlSrcAddress only supports the
                     InetAddressType value 'ipv4'."

        VARIATION   tmnxVdoGrpSrcGrpAddrType
            SYNTAX  INTEGER {
                        ipv4        (1)
                    }
            DESCRIPTION
                    "tmnxVdoGrpSrcGrpAddrType only supports the value 'ipv4' as
                     defined by the InetAddressType textual convention."

        VARIATION   tmnxVdoGrpSrcGroupAddress
            SYNTAX  InetAddress (SIZE (4))
            DESCRIPTION
                    "tmnxVdoGrpSrcGroupAddress only supports the InetAddressType
                     value 'ipv4'."

        VARIATION   tmnxVdoGrpSrcSrcAddrType
            SYNTAX  INTEGER {
                        ipv4        (1)
                    }
            DESCRIPTION
                    "tmnxVdoGrpSrcSrcAddrType only supports the value
                     'ipv4' as defined by the InetAddressType textual
                     convention."

        VARIATION   tmnxVdoGrpSrcSourceAddress
            SYNTAX  InetAddress (SIZE (4))
            DESCRIPTION
                    "tmnxVdoGrpSrcSourceAddress only supports the
                     InetAddressType value 'ipv4'."

        VARIATION   tmnxVdoGrpSrcRTClntRTSvrAddrType
            SYNTAX  INTEGER {
                        ipv4        (1)
                    }
            DESCRIPTION
                    "tmnxVdoGrpSrcRTClntRTSvrAddrType only supports the value
                     'ipv4' as defined by the InetAddressType textual
                     convention."

        VARIATION   tmnxVdoGrpSrcRTClntRTSvrAddr
            SYNTAX  InetAddress (SIZE (4))
            DESCRIPTION
                    "tmnxVdoGrpSrcRTClntRTSvrAddr only supports the
                     InetAddressType value 'ipv4'."

        VARIATION   tmnxVdoSessionSourceAddrType
            SYNTAX  INTEGER {
                        ipv4        (1)
                    }
            DESCRIPTION
                    "tmnxVdoSessionSourceAddrType only supports the value
                     'ipv4' as defined by the InetAddressType textual
                     convention."

        VARIATION   tmnxVdoSessionSourceAddr
            SYNTAX  InetAddress (SIZE (4))
            DESCRIPTION
                    "tmnxVdoSessionSourceAddr only supports the
                     InetAddressType value 'ipv4'."

        VARIATION   tmnxVdoSessionDestAddrType
            SYNTAX  INTEGER {
                        ipv4        (1)
                    }
            DESCRIPTION
                    "tmnxVdoSessionDestAddrType only supports the value
                     'ipv4' as defined by the InetAddressType textual
                     convention."

        VARIATION   tmnxVdoSessionDestAddr
            SYNTAX  InetAddress (SIZE (4))
            DESCRIPTION
                    "tmnxVdoSessionDestAddr only supports the
                     InetAddressType value 'ipv4'."

        VARIATION   tmnxVdoIfScte30AdSrvrAddrType
            SYNTAX  INTEGER {
                        ipv4        (1)
                    }
            DESCRIPTION
                    "tmnxVdoIfScte30AdSrvrAddrType only supports the value
                     'ipv4' as defined by the InetAddressType textual
                     convention."

        VARIATION   tmnxVdoIfScte30AdSrvrAddr
            SYNTAX  InetAddress (SIZE (4))
            DESCRIPTION
                    "tmnxVdoIfScte30AdSrvrAddr only supports the
                     InetAddressType value 'ipv4'."

        VARIATION   tmnxVdoSGAdiServerAddrType
            SYNTAX  INTEGER {
                        ipv4        (1)
                    }
            DESCRIPTION
                    "tmnxVdoSGAdiServerAddrType only supports the value
                     'ipv4' as defined by the InetAddressType textual
                     convention."

        VARIATION   tmnxVdoSGAdiServerAddr
            SYNTAX  InetAddress (SIZE (4))
            DESCRIPTION
                    "tmnxVdoSGAdiServerAddr only supports the
                     InetAddressType value 'ipv4'."

        VARIATION   tmnxVdoSGSpliceAdServerAddrType
            SYNTAX  INTEGER {
                        ipv4        (1)
                    }
            DESCRIPTION
                    "tmnxVdoSGSpliceAdServerAddrType only supports the value
                     'ipv4' as defined by the InetAddressType textual
                     convention."

        VARIATION   tmnxVdoSGSpliceAdServerAddr
            SYNTAX  InetAddress (SIZE (4))
            DESCRIPTION
                    "tmnxVdoSGSpliceAdServerAddr only supports the
                     InetAddressType value 'ipv4'."

    ::= { tmnxSROSV10v0 70 }  -- VIDEO

tmnxSprVideoCapsV10v0 AGENT-CAPABILITIES
     PRODUCT-RELEASE "Alcatel-Lucent SROS"
     STATUS          current
     DESCRIPTION
         "Implementation of specific video feature capabilities on
          Alcatel-Lucent-Lucent SROS SPR release R10.0."

--     SUPPORTS TIMETRA-VIDEO-MIB
--        INCLUDES    {
--        }

-- VIDEO is not supported on SROS SPR systems

    ::= { tmnxSROSVideoCapsV10v0 3 }  -- SPR VIDEO

--
--    Ethernet LMI CAPABILITIES
--
tmnxSROSElmiCapsV10v0 AGENT-CAPABILITIES
     PRODUCT-RELEASE "Alcatel-Lucent SROS"
     STATUS          current
     DESCRIPTION
         "Implementation of the E-LMI features on
          Alcatel-Lucent-Lucent SROS release R10.0."

     SUPPORTS TIMETRA-ELMI-MIB
        INCLUDES    {
            tmnxElmiEvcConfigGroup,
            tmnxElmiEventGroup,
            tmnxElmiIfConfigGroup,
            tmnxElmiStatsGroup,
            tmnxElmiTimeStampGroup
        }

     VARIATION   tmnxElmiIfCfgUniIdentifier
         ACCESS  read-only
         DESCRIPTION
                 "tmnxElmiIfCfgUniIdentifier is implemented as read-only."

     VARIATION   tmnxElmiEvcCfgIdentifier
         ACCESS  read-only
         DESCRIPTION
                 "tmnxElmiEvcCfgIdentifier is implemented as read-only."

     VARIATION   tmnxElmiIfCfgMode
         SYNTAX  INTEGER {
                    none (0),
                    uniN (1)
                 --   uniC (2)
                 }
         DESCRIPTION
                 "tmnxElmiIfCfgMode supports the values 'none (0)' and
                  'uniN (1)' only."

    ::= { tmnxSROSV10v0 71 }  -- ELMI

--
--  IPsec Static SA CAPABILITIES
--
tmnxSROSIPsecStaticSACapsV10v0    AGENT-CAPABILITIES
    PRODUCT-RELEASE "Alcatel-Lucent SROS"
    STATUS          current
    DESCRIPTION     "Implementation of IPsec Static SA tunneling, encryption and
                     other related features capabilities for Alcatel-Lucent
                     SROS release R10.0"
    SUPPORTS        TIMETRA-IPSEC-STATIC-SA-MIB
        INCLUDES    {
            tmnxIPsecStaticSAGroup
        }

    ::= { tmnxSROSV10v0 72 }  -- IPSEC Static SA

--
--  IF GROUP HANDLER CAPABILITIES
--
tmnxSROSIFGrpHandlerCapsV10v0     AGENT-CAPABILITIES
    PRODUCT-RELEASE "Alcatel-Lucent SROS"
    STATUS          current
    DESCRIPTION     "Implementation of Interface Group Handler capabilities
                     for Alcatel-Lucent SROS release R10.0"
    SUPPORTS        TIMETRA-IF-GROUP-HANDLER-MIB
        INCLUDES    {
            tmnxIfGroupHandlerTimeStampGroup,
            tmnxIfGroupHandlerConfigGroup,
            tmnxIfGroupHandlerMemberGroup,
            tmnxIfGroupHandlerProtocolGroup,
            tmnxIfGroupHdlrNotificationGroup
        }

    ::= { tmnxSROSV10v0 73 }  -- IF GROUP HANDLER

--
--  Ethernet Ring CAPABILITIES
--
tmnxSROSEthRingCapsV10v0          AGENT-CAPABILITIES
    PRODUCT-RELEASE "Alcatel-Lucent SROS"
    STATUS          current
    DESCRIPTION     "Implementation of Ethernet Ring capabilities for
                     Alcatel-Lucent SROS release R10.0"
    SUPPORTS        TIMETRA-ETH-RING-MIB
        INCLUDES    {
            tmnxEthRingApsNotifyGroup,
            tmnxEthRingBaseConfigGroup,
            tmnxEthRingBaseConfigV9v0Group,
            tmnxEthRingBasePathGroup,
            tmnxEthRingCommandV9v0Group,
            tmnxEthRingOperNotifyGroup,
            tmnxEthRingSAPPathGroup,
            tmnxEthRingSubRingV9v0Group,
            tmnxEthRingTimeStampGroup
        }
    ::= { tmnxSROSV10v0 74 }  -- Ethernet Rings

tmnxSprEthRingCapsV10v0           AGENT-CAPABILITIES
    PRODUCT-RELEASE "Alcatel-Lucent SPR SROS"
    STATUS          current
    DESCRIPTION     "Implementation of Ethernet Ring capabilities for
                     Alcatel-Lucent SROS SPR release R10.0"
--  SUPPORTS        TIMETRA-ETH-RING-MIB
--      INCLUDES    {
--      }
--        NOTE:  Eth-Ring is not implemented on SPR platforms.
    ::= { tmnxSROSEthRingCapsV10v0 1 }  -- Ethernet Rings

--
--  DIAMETER CAPABILITIES
--
tmnxSROSDiameterCapsV10v0         AGENT-CAPABILITIES
    PRODUCT-RELEASE "Alcatel-Lucent SROS"
    STATUS          current
    DESCRIPTION     "Implementation of DIAMETER capabilities
                     for Alcatel-Lucent SROS release R10.0"

    SUPPORTS        TIMETRA-DIAMETER-MIB
        INCLUDES    {
            tmnxDiameterBaseV8v0Group,
            tmnxDiameterDccaGroup,
            tmnxDiameterNotifyV10v0Group,
            tmnxDiameterDccaGxGroup,
            tmnxDiameterDccaV10v0Group
        }

        VARIATION tmnxDiamPlcyDccaAvpImsiOrg
            SYNTAX  INTEGER {
                        subscriberId (1),
                        circuitId    (2),
                        imsi         (3)
                     }
            DESCRIPTION
                    "tmnxDiamPlcyDccaAvpImsiOrg supports only the values
                    'subscriberId(1)', 'circuitId(2)' and 'imsi(3)'."

    ::= { tmnxSROSV10v0 75 }  -- DIAMETER

--
--  CONN PROF CAPABILITIES
--
tmnxSROSConnProfCapsV10v0         AGENT-CAPABILITIES
    PRODUCT-RELEASE "Alcatel-Lucent SROS"
    STATUS          current
    DESCRIPTION     "Implementation of connection profile capabilities
                     for Alcatel-Lucent SROS release R10.0."

--  SUPPORTS        TIMETRA-CONN-PROF-MIB
--      INCLUDES    {
--      }

    ::= { tmnxSROSV10v0 76 }  -- CONN PROF

tmnx7750ConnProfCapsV10v0    AGENT-CAPABILITIES
    PRODUCT-RELEASE "Alcatel-Lucent SROS"
    STATUS          current
    DESCRIPTION     "Implementation of connection profile capabilities
                     for Alcatel-Lucent SROS 7750 release R10.0.
                     TIMETRA-CONN-PROF-MIB is not supported on 7750 SR-1
                     systems."

    SUPPORTS        TIMETRA-CONN-PROF-MIB
        INCLUDES    {
            tmnxConnProfTimeStampGroup,
            tmnxConnProfGroup,
            tmnxConnProfAtmMemberGroup
        }

        VARIATION   tmnxConnProfRowStatus
            SYNTAX  INTEGER {
                        active      (1),
                        createAndGo (4),
                        destroy     (6)
                     }
            DESCRIPTION
                    "The tmnxConnProfRowStatus supports only the values
                    'active(1)', 'createAndGo(4)' and 'destroy(6)'."

        VARIATION   tmnxConnProfAtmMemberRowStatus
            SYNTAX  INTEGER {
                        active      (1),
                        createAndGo (4),
                        destroy     (6)
                     }
            DESCRIPTION
                    "The tmnxConnProfAtmMemberRowStatus supports only the
                     values 'active(1)', 'createAndGo(4)' and 'destroy(6)'."

    ::= { tmnxSROSConnProfCapsV10v0 1 }  -- 7750 CONN PROF

tmnx7450ConnProfCapsV10v0    AGENT-CAPABILITIES
    PRODUCT-RELEASE "Alcatel-Lucent SROS"
    STATUS          current
    DESCRIPTION     "Implementation of connection profile capabilities
                     for Alcatel-Lucent SROS 7450 release R10.0.
                     TIMETRA-CONN-PROF-MIB is not supported on 7450 ESS-1,
                     ESS-6 or ESS-6V systems."

    SUPPORTS        TIMETRA-CONN-PROF-MIB
        INCLUDES    {
            tmnxConnProfTimeStampGroup,
            tmnxConnProfGroup,
            tmnxConnProfAtmMemberGroup
        }

        VARIATION   tmnxConnProfRowStatus
            SYNTAX  INTEGER {
                        active      (1),
                        createAndGo (4),
                        destroy     (6)
                     }
            DESCRIPTION
                    "The tmnxConnProfRowStatus supports only the values
                    'active(1)', 'createAndGo(4)' and 'destroy(6)'."

        VARIATION   tmnxConnProfAtmMemberRowStatus
            SYNTAX  INTEGER {
                        active      (1),
                        createAndGo (4),
                        destroy     (6)
                     }
            DESCRIPTION
                    "The tmnxConnProfAtmMemberRowStatus supports only the
                     values 'active(1)', 'createAndGo(4)' and 'destroy(6)'."

    ::= { tmnxSROSConnProfCapsV10v0 2 }  -- 7450 CONN PROF

--
--  TWAMP CAPABILITIES
--
tmnxSROSTwampCapsV10v0            AGENT-CAPABILITIES
    PRODUCT-RELEASE "Alcatel-Lucent SROS"
    STATUS          current
    DESCRIPTION     "Implementation of Two-Way Active Measurement Protocol
                     (TWAMP) capabilities for Alcatel-Lucent SROS release R10.0."

    SUPPORTS        TIMETRA-TWAMP-MIB
        INCLUDES    {
            tmnxTwampSrvV9v0Group,
            tmnxTwampSrvNotifyV9v0Group,
            tmnxTwampSrvNotifyObjsV9v0Group
        }

        VARIATION   tmnxTwampSrvPrefixEntry
            DESCRIPTION
                    "tmnxTwampSrvPrefixEntry is not supported on 7450 ESS-1 or
                     7750 SR-1 systems."

        VARIATION   tmnxTwampSrvPrefixTblLastChg
            DESCRIPTION
                    "tmnxTwampSrvPrefixTblLastChg is not supported on 7450 ESS-1
                     or 7750 SR-1 systems."

        VARIATION   tmnxTwampSrvAdminState
            DESCRIPTION
                    "tmnxTwampSrvAdminState is not supported on 7450 ESS-1 or
                     7750 SR-1 systems."

        VARIATION   tmnxTwampSrvInactTimeout
            DESCRIPTION
                    "tmnxTwampSrvInactTimeout is not supported on 7450 ESS-1 or
                     7750 SR-1 systems."

        VARIATION   tmnxTwampSrvMaxConnections
            DESCRIPTION
                    "tmnxTwampSrvMaxConnections is not supported on 7450 ESS-1
                     or 7750 SR-1 systems."

        VARIATION   tmnxTwampSrvMaxSessions
            DESCRIPTION
                    "tmnxTwampSrvMaxSessions is not supported on 7450 ESS-1 or
                     7750 SR-1 systems."

        VARIATION   tmnxTwampSrvOperState
            DESCRIPTION
                    "tmnxTwampSrvOperState is not supported on 7450 ESS-1 or
                     7750 SR-1 systems."

        VARIATION   tmnxTwampSrvUpTime
            DESCRIPTION
                    "tmnxTwampSrvUpTime is not supported on 7450 ESS-1 or 7750
                     SR-1 systems."

        VARIATION   tmnxTwampSrvConnectionCount
            DESCRIPTION
                    "tmnxTwampSrvConnectionCount is not supported on 7450 ESS-1
                     or 7750 SR-1 systems."

        VARIATION   tmnxTwampSrvConnectionsRejected
            DESCRIPTION
                    "tmnxTwampSrvConnectionsRejected is not supported on 7450
                     ESS-1 or 7750 SR-1 systems."

        VARIATION   tmnxTwampSrvSessionCount
            DESCRIPTION
                    "tmnxTwampSrvSessionCount is not supported on 7450 ESS-1 or
                     7750 SR-1 systems."

        VARIATION   tmnxTwampSrvTestSessCompleted
            DESCRIPTION
                    "tmnxTwampSrvTestSessCompleted is not supported on 7450
                     ESS-1 or 7750 SR-1 systems."

        VARIATION   tmnxTwampSrvTestSessRejected
            DESCRIPTION
                    "tmnxTwampSrvTestSessRejected is not supported on 7450 ESS-1
                     or 7750 SR-1 systems."

        VARIATION   tmnxTwampSrvTestSessAborted
            DESCRIPTION
                    "tmnxTwampSrvTestSessAborted is not supported on 7450 ESS-1
                     or 7750 SR-1 systems."

        VARIATION   tmnxTwampSrvTestPacketsRx
            DESCRIPTION
                    "tmnxTwampSrvTestPacketsRx is not supported on 7450 ESS-1 or
                     7750 SR-1 systems."

        VARIATION   tmnxTwampSrvTestPacketsTx
            DESCRIPTION
                    "tmnxTwampSrvTestPacketsTx is not supported on 7450 ESS-1 or
                     7750 SR-1 systems."

        VARIATION   tmnxTwampSrvPrefixAddrType
            SYNTAX  InetAddressType {
                        ipv4(1)
                    }
            DESCRIPTION
                    "tmnxTwampSrvPrefixAddrType supports the value 'ipv4(1)'
                     only."

        VARIATION   tmnxTwampSrvPrefixLen
            SYNTAX  InetAddressPrefixLength (0..32)
            DESCRIPTION
                    "tmnxTwampSrvPrefixLen supports the IPv4 address prefix
                     length range only."

        VARIATION   tmnxTwampSrvPrefixRowStatus
            SYNTAX  RowStatus {
                        active      (1),
                        createAndGo (4),
                        destroy     (6)
                    }
            DESCRIPTION
                    "tmnxTwampSrvPrefixRowStatus supports the values
                    'active (1)', 'createAndGo (4)' and 'destroy (6)' only."

    ::= { tmnxSROSV10v0 77 }  -- TWAMP

--
--  TIMETRA IPFIX CAPABILITIES
--
tmnxSROSIpfixCapsV10v0 AGENT-CAPABILITIES
    PRODUCT-RELEASE "Alcatel-Lucent SROS"
    STATUS current
    DESCRIPTION
        "Implementation of the IP Flow Information Export (IPFIX) Protocol
         for the Exchange of IP Traffic Flow Information feature
         on Alcatel-Lucent SROS release R10.0."

    SUPPORTS TIMETRA-IPFIX-MIB
        INCLUDES    {
            tmnxIpfixExportGroup
        }

        VARIATION   tmnxIpfixExpPlcyRowStatus
            SYNTAX  INTEGER {
                        active      (1),
                        createAndGo (4),
                        destroy     (6)
                    }
            DESCRIPTION
                    "The only allowed values for this object are
                    'active (1)', 'createAndGo (4)' and 'destroy (6)'."

        VARIATION   tmnxIpfixExpPlcyColRowStatus
            SYNTAX  INTEGER {
                        active      (1),
                        createAndGo (4),
                        destroy     (6)
                    }
            DESCRIPTION
                    "The only allowed values for this object are
                    'active (1)', 'createAndGo (4)' and 'destroy (6)'."

        VARIATION   tmnxIpfixExpPlcyColAdminState
            SYNTAX  INTEGER {
                        -- noop         (1),
                        inService       (2),
                        outOfService    (3)
                    }
            DESCRIPTION
                    "The only allowed values for this object are 'inService (2)'
                    and 'outOfService (3)'."

    ::= { tmnxSROSV10v0 78 }  -- IPFIX

--
--  TIMETRA RADIUS CAPABILITIES
--
tmnxSROSRadProxCapsV10v0 AGENT-CAPABILITIES
    PRODUCT-RELEASE "Alcatel-Lucent SROS"
    STATUS current
    DESCRIPTION
        "Implementation of Radius on 
         Alcatel-Lucent SROS release R10.0."

    SUPPORTS TIMETRA-RADIUS-MIB
        INCLUDES    {
               tmnxRadProxSrvGroup,
               tmnxRadServGroup,
               tmnxRadScriptPlcyGroup,
               tmnxRadRouteDownlGroup,
               tmnxRadiusNotifyGroup
        }
        VARIATION   tmnxRadProxSrvRowStatus
            SYNTAX  INTEGER {
                        active      (1),
                        createAndGo (4),
                        destroy     (6)
                     }
            DESCRIPTION
                    "The only allowed values for this object are
                        'active (1)', 'createAndGo (4)' and 'destroy (6)'."

        VARIATION   tmnxRadProxSrvAdminState
            SYNTAX  INTEGER {
                        outOfService      (2),
                        inService         (3)
                     }
            DESCRIPTION
                    "The only allowed values for this object are
                        'outOfService' and 'inService'."

        VARIATION   tmnxRadProxSrvCacheTrackAcct
    SYNTAX      BITS {
--                  start         (0),
                    stop          (1),
                    interimUpdate (2),
                    accountingOn  (3),
                    accountingOff (4)
                }
            DESCRIPTION
                    "The only bits that are supported are 'stop',
                     'interimUpdate', 'accountingOn' and 'accountingOff'."

        VARIATION   tmnxRadProxSrvIfRowStatus
            SYNTAX  INTEGER {
                        active      (1),
                        createAndGo (4),
                        destroy     (6)
                     }
            DESCRIPTION
                    "The only allowed values for this object are
                        'active (1)', 'createAndGo (4)' and 'destroy (6)'."

        VARIATION   tmnxRadProxUsrToRspRowStatus
            SYNTAX  INTEGER {
                        active      (1),
                        createAndGo (4),
                        destroy     (6)
                     }
            DESCRIPTION
                    "The only allowed values for this object are
                        'active (1)', 'createAndGo (4)' and 'destroy (6)'."

        VARIATION   tmnxRadServRowStatus
            SYNTAX  INTEGER {
                        active      (1),
                        createAndGo (4),
                        destroy     (6)
                     }
            DESCRIPTION
                    "The only allowed values for this object are
                        'active (1)', 'createAndGo (4)' and 'destroy (6)'."

        VARIATION   tmnxRadSrvPlcyRowStatus
            SYNTAX  INTEGER {
                        active      (1),
                        createAndGo (4),
                        destroy     (6)
                     }
            DESCRIPTION
                    "The only allowed values for this object are
                        'active (1)', 'createAndGo (4)' and 'destroy (6)'."

        VARIATION   tmnxRadSrvPlcySrvRowStatus
            SYNTAX  INTEGER {
                        active      (1),
                        createAndGo (4),
                        destroy     (6)
                     }
            DESCRIPTION
                    "The only allowed values for this object are
                        'active (1)', 'createAndGo (4)' and 'destroy (6)'."

        VARIATION   tmnxRadScriptPlcyRowStatus
            SYNTAX  INTEGER {
                        active      (1),
                        createAndGo (4),
                        destroy     (6)
                     }
            DESCRIPTION
                    "The only allowed values for this object are
                        'active (1)', 'createAndGo (4)' and 'destroy (6)'."

        VARIATION   tmnxRadScriptPlcyRowStatus
            SYNTAX  INTEGER {
                        active      (1),
                        createAndGo (4),
                        destroy     (6)
                     }
            DESCRIPTION
                    "The only allowed values for this object are
                        'active (1)', 'createAndGo (4)' and 'destroy (6)'."

        VARIATION   tmnxRadRouteDownlRowStatus
            SYNTAX  INTEGER {
                        active      (1),
                        createAndGo (4),
                        destroy     (6)
                     }  
            DESCRIPTION
                    "The only allowed values for this object are
                        'active (1)', 'createAndGo (4)' and 'destroy (6)'."

    ::= { tmnxSROSV10v0 79 }  -- Radius Proxy

--
--  TIMETRA Web Portal Protocol CAPABILITIES
--
tmnxSROSWppCapsV10v0 AGENT-CAPABILITIES
    PRODUCT-RELEASE "Alcatel-Lucent SROS"
    STATUS current
    DESCRIPTION
        "Implementation of Web Portal Protocol
         on Alcatel-Lucent SROS release R10.0."

    SUPPORTS TIMETRA-WEB-PORTAL-PROTOCOL-MIB
        INCLUDES    {
                tmnxWppGroup,
                tmnxWppNotifyGroup
        }

        VARIATION   tmnxWppRowStatus
            SYNTAX  INTEGER {
                        active      (1),
                        createAndGo (4),
                        destroy     (6)
                     }
            DESCRIPTION
                    "The only allowed values for this object are
                        'active (1)', 'createAndGo (4)' and 'destroy (6)'."

        VARIATION   tmnxWppAdminState
            SYNTAX  INTEGER {
                        outOfService      (2),
                        inService (3)
                     }
            DESCRIPTION
                    "The only allowed values for this object are
                        'outOfService' and 'inService'."

        VARIATION   tmnxWppPortalRowStatus
            SYNTAX  INTEGER {
                        active      (1),
                        createAndGo (4),
                        destroy     (6)
                     }
            DESCRIPTION
                    "The only allowed values for this object are
                        'active (1)', 'createAndGo (4)' and 'destroy (6)'."

        VARIATION   tmnxWppPortalAddrType
            SYNTAX  INTEGER {
                        ipv4        (1)
                    }
            DESCRIPTION
                    "tmnxWppPortalAddrType supports only InetAddressType
                     value 'ipv4 (1)'."

        VARIATION   tmnxWppPortalAdminState
            SYNTAX  INTEGER {
                        outOfService      (2),
                        inService (3)
                     }
            DESCRIPTION
                    "The only allowed values for this object are
                        'outOfService' and 'inService'."

         VARIATION   tmnxWppIfAdminState
             SYNTAX  INTEGER {
                         outOfService      (2),
                         inService (3)
                      }
             DESCRIPTION
                     "The only allowed values for this object are
                         'outOfService' and 'inService'."

    ::= { tmnxSROSV10v0 80 }  -- Web Portal Protocol
tmnx7950WppCapsV10v0 AGENT-CAPABILITIES
    PRODUCT-RELEASE "Alcatel-Lucent SROS"
    STATUS current
    DESCRIPTION
        "Web Portal Protocol is not supported
         on Alcatel-Lucent SROS release R10.0."

--    SUPPORTS TIMETRA-WEB-PORTAL-PROTOCOL-MIB
--        INCLUDES    { }
    ::= { tmnxSROSWppCapsV10v0 1 }  -- 7950 Web Portal Protocol


--
--  Precision Timing Protocol (PTP1588) CAPABILITIES
--
tmnxSROSPTPCapsV10v0 AGENT-CAPABILITIES
    PRODUCT-RELEASE "Alcatel-Lucent SROS"
    STATUS current
    DESCRIPTION
        "Implementation of Precision Timing Protocol (PTP1588)
         on Alcatel-Lucent SROS release R10.0."

--  SUPPORTS TIMETRA-PTP-MIB
--    INCLUDES    {
--    }

    ::= { tmnxSROSV10v0 81 }  -- Precision Timing Protocol

tmnx7750PTPCapsV10v0 AGENT-CAPABILITIES
    PRODUCT-RELEASE "Alcatel-Lucent SROS"
    STATUS current
    DESCRIPTION
        "Implementation of Precision Timing Protocol (PTP1588)
         on Alcatel-Lucent 7750 release R10.0.  PTP1588 is only accessible on
         a system with an active CPM3/SFM3."

    SUPPORTS TIMETRA-PTP-MIB
        INCLUDES    {
            tmnxPtpTimeStampGroup,
            tmnxPtpLocalConfigGroup,
            tmnxPtpLocalOperGroup,
            tmnxPtpMasterClockGroup,
            tmnxPtpPeerBaseConfigGroup,
            tmnxPtpPeerMasterStatusGroup,
            tmnxPtpPacketStatsGroup,
            tmnxPtpClockRecoveryGroup,
            tmnxPtpPeerUnicastStatusGroup,
            tmnxPtpNotificationsGroup,
-- EXCLUDE  tmnxPtpVRtrIfTimeStampGroup,
-- EXCLUDE  tmnxPtpVRtrIfConfigGroup,
            tmnxPtpTimeInfoGroup
-- EXCLUDE  tmnxPtpPeerOperGroup,
-- EXCLUDE  tmnxPtpPacketStatsV10v0Group
        }

        VARIATION   tmnxPtpPeerLocalPriority
            SYNTAX  TmnxPtpPriority (1..255)
            DESCRIPTION
                    "tmnxPtpPeerLocalPriority supports the range from 1 to 255."

    ::= { tmnxSROSPTPCapsV10v0 1 }  -- 7750 Precision Timing Protocol

tmnx7450PTPCapsV10v0 AGENT-CAPABILITIES
    PRODUCT-RELEASE "Alcatel-Lucent SROS"
    STATUS current
    DESCRIPTION
        "Implementation of Precision Timing Protocol (PTP1588)
         on Alcatel-Lucent 7750 release R10.0.  PTP1588 is only accessible on
         a system with an active CPM3/SFM3."

    SUPPORTS TIMETRA-PTP-MIB
        INCLUDES    {
            tmnxPtpTimeStampGroup,
            tmnxPtpLocalConfigGroup,
            tmnxPtpLocalOperGroup,
            tmnxPtpMasterClockGroup,
            tmnxPtpPeerBaseConfigGroup,
            tmnxPtpPeerMasterStatusGroup,
            tmnxPtpPacketStatsGroup,
            tmnxPtpClockRecoveryGroup,
            tmnxPtpPeerUnicastStatusGroup,
            tmnxPtpNotificationsGroup,
            tmnxPtpTimeInfoGroup
        }

        VARIATION   tmnxPtpPeerLocalPriority
            SYNTAX  TmnxPtpPriority (1..255)
            DESCRIPTION
                    "tmnxPtpPeerLocalPriority supports the range from 1 to 255."

    ::= { tmnxSROSPTPCapsV10v0 2 }  -- 7450 Precision Timing Protocol

tmnx7750c4PTPCapsV10v0 AGENT-CAPABILITIES
    PRODUCT-RELEASE "Alcatel-Lucent SROS"
    STATUS current
    DESCRIPTION
        "Implementation of Precision Timing Protocol (PTP1588)
         on Alcatel-Lucent 7750-c4 release R10.0."

    SUPPORTS TIMETRA-PTP-MIB
        INCLUDES    {
            tmnxPtpTimeStampGroup,
            tmnxPtpLocalConfigGroup,
            tmnxPtpLocalOperGroup,
            tmnxPtpMasterClockGroup,
            tmnxPtpPeerBaseConfigGroup,
            tmnxPtpPeerMasterStatusGroup,
            tmnxPtpPacketStatsGroup,
            tmnxPtpClockRecoveryGroup,
            tmnxPtpPeerUnicastStatusGroup,
            tmnxPtpNotificationsGroup,
            tmnxPtpTimeInfoGroup
        }

        VARIATION   tmnxPtpPeerLocalPriority
            SYNTAX  TmnxPtpPriority (1..255)
            DESCRIPTION
                    "tmnxPtpPeerLocalPriority supports the range from 1 to 255."

    ::= { tmnxSROSPTPCapsV10v0 3 }  -- 7750-c4 Precision Timing Protocol

--
--  TIMETRA WLAN Gateway CAPABILITIES
--
--
-- WLAN Gateway is only supported on 7750
-- 

tmnxSROSWlanGwCapsV10v0 AGENT-CAPABILITIES
    PRODUCT-RELEASE "Alcatel-Lucent SROS"
    STATUS current
    DESCRIPTION
        "Implementation of the Wireless Local Area Network Gateway function
         on Alcatel-Lucent SROS release R10.0."
    ::= { tmnxSROSV10v0 82 }  -- WLAN Gateway

tmnx7750WlanGwCapsV10v0 AGENT-CAPABILITIES
    PRODUCT-RELEASE "Alcatel-Lucent SROS"
    STATUS current
    DESCRIPTION
        "Implementation of the Wireless Local Area Network Gateway function
         on Alcatel-Lucent SROS release R10.0."

    SUPPORTS TIMETRA-WLAN-GW-MIB
        INCLUDES    {
            tmnxWlanGwIsaGroup,
            tmnxWlanGwSoftGreGroup,
            tmnxWlanGwObjGroup,
            tmnxWlanGwNotifyGroup,
            tmnxWlanGwMgwGroup
        }

        VARIATION   tmnxWlanGwGrpRowStatus
            SYNTAX  INTEGER {
                        active      (1),
                        createAndGo (4),
                        destroy     (6)
                    }
            DESCRIPTION
                    "The only allowed values for this object are
                    'active (1)', 'createAndGo (4)' and 'destroy (6)'."

        VARIATION   tmnxWlanGwIomRowStatus
            SYNTAX  INTEGER {
                        active      (1),
                        createAndGo (4),
                        destroy     (6)
                    }
            DESCRIPTION
                    "The only allowed values for this object are
                    'active (1)', 'createAndGo (4)' and 'destroy (6)'."

        VARIATION   tmnxWlanGwGrpAdminState
            SYNTAX  INTEGER {
                        -- noop         (1),
                        inService       (2),
                        outOfService    (3)
                    }
            DESCRIPTION
                    "The only allowed values for this object are 'inService (2)'
                    and 'outOfService (3)'."

        VARIATION   tmnxWlanGwSoftGreIfAdminState
            SYNTAX  INTEGER {
                        -- noop         (1),
                        inService       (2),
                        outOfService    (3)
                    }
            DESCRIPTION
                    "The only allowed values for this object are 'inService (2)'
                    and 'outOfService (3)'."

        VARIATION   tmnxWlanGwSoftGreIfGwAddrType
            SYNTAX  INTEGER {
                        unknown     (0),
                        ipv4        (1)
                    }
            DESCRIPTION
                    "The only values allowed for this object are 'unknown' and 'ipv4'."

    ::= { tmnxSROSWlanGwCapsV10v0 1 }  -- WLAN Gateway 7750

END
