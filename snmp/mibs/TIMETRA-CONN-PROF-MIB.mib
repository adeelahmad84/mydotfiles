TIMETRA-CONN-PROF-MIB DEFINITIONS ::= BEGIN

IMPORTS
        MODULE-IDENTITY, OBJECT-TYPE,
        NOTIFICATION-TYPE,
        Integer32, Unsigned32                 FROM SNMPv2-SMI

        MODULE-COMPLIANCE, OBJECT-GROUP,
        NOTIFICATION-GROUP                    FROM SNMPv2-CONF

        TEXTUAL-CONVENTION, RowStatus,
        TimeStamp                             FROM SNMPv2-TC

        TmnxEncapVal, TItemDescription        FROM TIMETRA-TC-MIB

        timetraSRMIBModules, tmnxSRObjs,
        tmnxSRNotifyPrefix, tmnxSRConfs       FROM TIMETRA-GLOBAL-MIB
        ;

timetraConnProfMIBModule   MODULE-IDENTITY
        LAST-UPDATED "201102010000Z"
        ORGANIZATION "Alcatel-Lucent"
        CONTACT-INFO
            "Alcatel-Lucent SROS Support
             Web: http://support.alcatel-lucent.com"
        DESCRIPTION
        "This document is the SNMP MIB module to manage connection profiles
        associated with VLL services of the Alcatel-Lucent SROS system.

        Copyright (c) 2011-2014 Alcatel-Lucent. All rights reserved. Reproduction
        of this document is authorized on the condition that the
        foregoing copyright notice is included.

        This SNMP MIB module (Specification) embodies Alcatel-Lucent's
        proprietary intellectual property. Alcatel-Lucent retains all title
        and ownership in the Specification, including any revisions.

        Alcatel-Lucent grants all interested parties a non-exclusive license
        to use and distribute an unmodified copy of this Specification
        in connection with management of Alcatel-Lucent products, and without
        fee, provided this copyright notice and license appear on all
        copies.

        This Specification is supplied `as is', and Alcatel-Lucent makes no
        warranty, either express or implied, as to the use, operation,
        condition, or performance of the Specification."

--
--  Revision History
--
        REVISION                 "201102010000Z"
        DESCRIPTION              "Rev 1.0                1 Feb 2011 00:00
                                  Initial Release of the TIMETRA-CONN-PROF-MIB
                                  in SROS 9.0."

        ::= { timetraSRMIBModules 75 }

tmnxConnProfObjs             OBJECT IDENTIFIER ::= { tmnxSRObjs             75 }
tmnxConnProfNtfyPrefix       OBJECT IDENTIFIER ::= { tmnxSRNotifyPrefix     75 }
tmnxConnProfConformance      OBJECT IDENTIFIER ::= { tmnxSRConfs            75 }

-- Object Groups in the Alcatel-Lucent Connection Profile MIB Module
tmnxConnProfConfigTimeStamps OBJECT IDENTIFIER ::= { tmnxConnProfObjs        1 }
tmnxConnProfConfigObjs       OBJECT IDENTIFIER ::= { tmnxConnProfObjs        2 }

-- Notification Groups in the Alcatel-Lucent Connection Profile MIB Module
tmnxConnProfNotifications    OBJECT IDENTIFIER ::= { tmnxConnProfNtfyPrefix  0 }

-- Compliance Groups in the Alcatel-Lucent Connection Profile MIB Module
tmnxConnProfCompliances      OBJECT IDENTIFIER ::= { tmnxConnProfConformance 1 }
tmnxConnProfGroups           OBJECT IDENTIFIER ::= { tmnxConnProfConformance 2 }

--%%%%%%%%%%%%%%%%%%%%%%%%%%%%%%%%%%%%%%%%%%%%%%%%%%%%%%%%%%%%%%%%%%%%%%%%%%%
--
--  TIMETRA-CONN-PROF-MIB Textual Conventions
--
TmnxConnProfId                   ::= TEXTUAL-CONVENTION
    STATUS      current
    DESCRIPTION
        "A number used to identify a connection profile. The value 0 is used as
         the null ID."
    SYNTAX      Unsigned32 (0|1..8000)

--%%%%%%%%%%%%%%%%%%%%%%%%%%%%%%%%%%%%%%%%%%%%%%%%%%%%%%%%%%%%%%%%%%%%%%%%%%%
--
--  TIMETRA-CONN-PROF-MIB Configuration Objects
--

--
--  Connection Profile objects
--

tmnxConnProfTblLastChanged       OBJECT-TYPE
    SYNTAX      TimeStamp
    MAX-ACCESS  read-only
    STATUS      current
    DESCRIPTION
        "The value of tmnxConnProfTblLastChanged indicates the time, since
         system startup, when the tmnxConnProfTable last changed state."
    ::= { tmnxConnProfConfigTimeStamps 1 }

tmnxConnProfTable                OBJECT-TYPE
    SYNTAX      SEQUENCE OF TmnxConnProfEntry
    MAX-ACCESS  not-accessible
    STATUS      current
    DESCRIPTION
        "The tmnxConnProfTable contains an entry for each connection
         profile."
    ::= { tmnxConnProfConfigObjs 1 }

tmnxConnProfEntry                OBJECT-TYPE
    SYNTAX      TmnxConnProfEntry
    MAX-ACCESS  not-accessible
    STATUS      current
    DESCRIPTION
        "Each tmnxConnProfEntry contains connection profile specific
         configuration."
    INDEX {     tmnxConnProfId
          }
    ::= { tmnxConnProfTable 1 }

TmnxConnProfEntry                ::= SEQUENCE {
    tmnxConnProfId                   TmnxConnProfId,
    tmnxConnProfRowStatus            RowStatus,
    tmnxConnProfLastChanged          TimeStamp,
    tmnxConnProfDescription          TItemDescription
}

tmnxConnProfId                   OBJECT-TYPE
    SYNTAX      TmnxConnProfId
    MAX-ACCESS  not-accessible
    STATUS      current
    DESCRIPTION
        "The value of tmnxConnProfId specifies the index to a specific
         connection profile. tmnxConnProfId is system unique."
    ::= { tmnxConnProfEntry 1 }

tmnxConnProfRowStatus            OBJECT-TYPE
    SYNTAX      RowStatus
    MAX-ACCESS  read-create
    STATUS      current
    DESCRIPTION
        "The value of tmnxConnProfRowStatus specifies the row status. It allows
         entries to be created and deleted in the tmnxConnProfTable.

         Rows are created by specifying the value of 'createAndGo(4)' and
         deleted by specifying the value of 'destroy(6)'.

         To delete an entry, all references to the connection profile in
         existing SAPs and in tmnxConnProfAtmMemberTable must be deleted."
    ::= { tmnxConnProfEntry 2 }

tmnxConnProfLastChanged          OBJECT-TYPE
    SYNTAX      TimeStamp
    MAX-ACCESS  read-only
    STATUS      current
    DESCRIPTION
        "The value of tmnxConnProfLastChanged indicates the time, since system
         startup, that the connection profile was created or modified."
    ::= { tmnxConnProfEntry 3 }

tmnxConnProfDescription          OBJECT-TYPE
    SYNTAX      TItemDescription
    MAX-ACCESS  read-create
    STATUS      current
    DESCRIPTION
        "The value of tmnxConnProfDescription specifies the description of this
         connection profile."
    DEFVAL { "" }
    ::= { tmnxConnProfEntry 4 }

--
--  Connection Profile ATM Member objects
--

tmnxConnProfAtmMemberTblLastChgd OBJECT-TYPE
    SYNTAX      TimeStamp
    MAX-ACCESS  read-only
    STATUS      current
    DESCRIPTION
        "The value of tmnxConnProfAtmMemberTblLastChgd indicates the time,
         since system startup, when the tmnxConnProfAtmMemberTable last changed
         state."
    ::= { tmnxConnProfConfigTimeStamps 2 }

tmnxConnProfAtmMemberTable       OBJECT-TYPE
    SYNTAX      SEQUENCE OF TmnxConnProfAtmMemberEntry
    MAX-ACCESS  not-accessible
    STATUS      current
    DESCRIPTION
        "The tmnxConnProfAtmMemberTable contains an entry for each ATM
         connection profile member.

         Each ATM connection profile member is a VPI/VCI value to be assigned
         to an ATM SAP of an APIPE VLL service with
         TIMETRA-SERV-MIB:svcVllType set to a value of 'atmCell(7)'.

         Up to a maximum of 16 ATM connection profile members can be added to
         a connection profile."
    ::= { tmnxConnProfConfigObjs 2 }

tmnxConnProfAtmMemberEntry       OBJECT-TYPE
    SYNTAX      TmnxConnProfAtmMemberEntry
    MAX-ACCESS  not-accessible
    STATUS      current
    DESCRIPTION
        "Each tmnxConnProfAtmMemberEntry contains ATM connection profile member
         specific configuration."
    INDEX  {    tmnxConnProfId,
                tmnxConnProfAtmMemberEncapValue
           }
    ::= { tmnxConnProfAtmMemberTable 1 }

TmnxConnProfAtmMemberEntry       ::= SEQUENCE {
    tmnxConnProfAtmMemberEncapValue  TmnxEncapVal,
    tmnxConnProfAtmMemberRowStatus   RowStatus
}

tmnxConnProfAtmMemberEncapValue  OBJECT-TYPE
    SYNTAX      TmnxEncapVal
    MAX-ACCESS  not-accessible
    STATUS      current
    DESCRIPTION
        "The value of tmnxConnProfAtmMemberEncapValue specifies, along with
         tmnxConnProfId, the index to a specific ATM connection profile member.
         The TmnxEncapVal supported is ATM VC, for which the top 3 bits are
         000."
    ::= { tmnxConnProfAtmMemberEntry 1 }

tmnxConnProfAtmMemberRowStatus   OBJECT-TYPE
    SYNTAX      RowStatus
    MAX-ACCESS  read-create
    STATUS      current
    DESCRIPTION
        "The value of tmnxConnProfAtmMemberRowStatus specifies the row status.
         It allows entries to be created and deleted in the
         tmnxConnProfAtmMemberTable.

         Rows are created by specifying the value of 'createAndGo(4)' and
         deleted by specifying the value of 'destroy(6)'."
    ::= { tmnxConnProfAtmMemberEntry 2 }

--%%%%%%%%%%%%%%%%%%%%%%%%%%%%%%%%%%%%%%%%%%%%%%%%%%%%%%%%%%%%%%%%%%%%%%%%%%%
--
--  TIMETRA-CONN-PROF-MIB Notification Objects
--

--%%%%%%%%%%%%%%%%%%%%%%%%%%%%%%%%%%%%%%%%%%%%%%%%%%%%%%%%%%%%%%%%%%%%%%%%%%%
--
--  TIMETRA-CONN-PROF-MIB Compliance Statements
--
tmnxConnProfV9v0Compliance       MODULE-COMPLIANCE
    STATUS      current
    DESCRIPTION
        "The compliance statement for management of connection profiles
         on Alcatel-Lucent SROS series systems for release 9.0."
    MODULE -- this module
        MANDATORY-GROUPS {
            tmnxConnProfTimeStampGroup,
            tmnxConnProfGroup,
            tmnxConnProfAtmMemberGroup
        }
    ::= { tmnxConnProfCompliances 1 }

--%%%%%%%%%%%%%%%%%%%%%%%%%%%%%%%%%%%%%%%%%%%%%%%%%%%%%%%%%%%%%%%%%%%%%%%%%%%
--
--  TIMETRA-CONN-PROF-MIB Group Statements
--
tmnxConnV9v0Groups OBJECT IDENTIFIER ::= { tmnxConnProfGroups 1 }

tmnxConnProfTimeStampGroup       OBJECT-GROUP
    OBJECTS {
        tmnxConnProfTblLastChanged,
        tmnxConnProfAtmMemberTblLastChgd
    }
    STATUS      current
    DESCRIPTION
        "The group of objects maintaining table/row statistics for connection
         profile tables on Alcatel-Lucent SROS series systems."
    ::= { tmnxConnV9v0Groups 1 }

tmnxConnProfGroup                OBJECT-GROUP
    OBJECTS {
        tmnxConnProfRowStatus,
        tmnxConnProfLastChanged,
        tmnxConnProfDescription
    }
    STATUS      current
    DESCRIPTION
        "The group of objects supporting management of connection
         profiles on Alcatel-Lucent SROS series systems."
    ::= { tmnxConnV9v0Groups 2 }

tmnxConnProfAtmMemberGroup       OBJECT-GROUP
    OBJECTS {
        tmnxConnProfAtmMemberRowStatus
    }
    STATUS      current
    DESCRIPTION
        "The group of objects supporting management of ATM connection
         profile members on Alcatel-Lucent SROS series systems."
    ::= { tmnxConnV9v0Groups 3 }
END
