TIMETRA-DYNAMIC-SERVICES-MIB DEFINITIONS ::= BEGIN

IMPORTS
    MODULE-IDENTITY,
    OBJECT-TYPE,
    Unsigned32,
    Counter32
                                                                FROM SNMPv2-SMI


    RowStatus, 
    TimeStamp,
    DateAndTime,
    DisplayString,
    TruthValue,
    RowPointer
                                                                 FROM SNMPv2-TC


    OBJECT-GROUP, MODULE-COMPLIANCE
                                                               FROM SNMPv2-CONF

    timetraSRMIBModules, 
    tmnxSRObjs, 
    tmnxSRConfs, 
    tmnxSRNotifyPrefix
                                                        FROM TIMETRA-GLOBAL-MIB

    TNamedItem,
    TNamedItemOrEmpty,
    TItemDescription,
    TmnxServId,
    TmnxSubAcctSessionId,
    TmnxEnabledDisabled,
    TmnxPortID,
    TmnxEncapVal
                                                            FROM TIMETRA-TC-MIB

    sapPortId, 
    sapEncapValue    
                                                           FROM TIMETRA-SAP-MIB

    ;
timetraDynSrvMIBModule    MODULE-IDENTITY
    LAST-UPDATED    "201305311200Z"
    ORGANIZATION    "Alcatel-Lucent"
    CONTACT-INFO
    "Alcatel-Lucent 7xxx Support
    Web: http://www.alcatel-lucent.com/wps/portal/Support"
    DESCRIPTION
    "This document is the SNMP MIB module to manage and provision
    Dynamic Services for the Alcatel-Lucent 7xxx device.

    Copyright 2012-2014 Alcatel-Lucent. All rights reserved.
    Reproduction of this document is authorized on the condition that
    the foregoing copyright notice is included.

    This SNMP MIB module (Specification) embodies Alcatel-Lucent's
    proprietary intellectual property. Alcatel-Lucent retains all title and
    ownership in the Specification, including any revisions.

    Alcatel-Lucent grants all interested parties a non-exclusive
    license to use and distribute an unmodified copy of this
    Specification in connection with management of Alcatel products,
    and without fee, provided this copyright notice and license appear
    on all copies.

    This Specification is supplied 'as is', and Alcatel-Lucent
    makes no warranty, either express or implied, as to the use,
    operation, condition, or performance of the Specification."

--
--  Revision History
--

    REVISION        "201305311200Z"
    DESCRIPTION     "Rev 11.0                31 May 2013 12:00
                     11.0 release of the TIMETRA-DYNAMIC-SERVICES-PROTOCOL-MIB.mib."

    ::= { timetraSRMIBModules 84 }

-- ----------------------------------------------------------------------------
--  Alcatel-Lucent 7xxx series Dynamic Services MIB structure
-- ----------------------------------------------------------------------------
tmnxDynSvc                     OBJECT IDENTIFIER ::= { tmnxSRObjs 84 }
    tmnxDynSvcObjs             OBJECT IDENTIFIER ::= { tmnxDynSvc 1 }
    tmnxDynSvcNotificationObjs OBJECT IDENTIFIER ::= { tmnxDynSvc 2 }

tmnxDynSvcConformance         OBJECT IDENTIFIER ::= { tmnxSRConfs 84 }
    tmnxDynSvcCompliances     OBJECT IDENTIFIER ::= { tmnxDynSvcConformance 1 }
    tmnxDynSvcGroups          OBJECT IDENTIFIER ::= { tmnxDynSvcConformance 2 }

tmnxDynSvcNotifyPrefix        OBJECT IDENTIFIER ::= { tmnxSRNotifyPrefix 84 }
    tmnxDynSvcNotifications   OBJECT IDENTIFIER ::= { tmnxDynSvcNotifyPrefix 0 }

-- ----------------------------------------------------------------------------
--  Textual Conventions
-- ----------------------------------------------------------------------------

TmnxDynSrvAcctStatsType ::= TEXTUAL-CONVENTION
    STATUS  current
    DESCRIPTION
        "The TmnxDynSrvAcctStatsType data type is an enumerated integer that
         describes the values used to identify the type of accounting
         statistics gathered."
    SYNTAX  INTEGER {
                volumeTime (1),
                time       (2)
                }

-- ----------------------------------------------------------------------------
--
--      The Dynamic Services Policy  Table
-- 

tmnxDynSvcPlcyTable OBJECT-TYPE
    SYNTAX      SEQUENCE OF TmnxDynSvcPlcyEntry
    MAX-ACCESS  not-accessible
    STATUS      current
    DESCRIPTION
        "The tmnxDynSvcPlcyTable allows configuration of 
         policies for Dynamic Services."
    ::= { tmnxDynSvcObjs 1 }

tmnxDynSvcPlcyEntry OBJECT-TYPE
    SYNTAX      TmnxDynSvcPlcyEntry
    MAX-ACCESS  not-accessible
    STATUS      current
    DESCRIPTION
        "Each entry represents the configuration for 
         a particular Dynamic Services profile.
         
         Entries in this table can be created and deleted via SNMP SET
         operations to tmnxDynSvcPlcyRowStatus."
    INDEX { IMPLIED tmnxDynSvcPlcyName }
    ::= { tmnxDynSvcPlcyTable 1 }

TmnxDynSvcPlcyEntry ::=
    SEQUENCE {
        tmnxDynSvcPlcyName               TNamedItem,
        tmnxDynSvcPlcyRowStatus          RowStatus,
        tmnxDynSvcPlcyLastCh             TimeStamp,
        tmnxDynSvcPlcyDescription        TItemDescription,
        tmnxDynSvcPlcyScriptPlcy         TNamedItemOrEmpty,
        tmnxDynSvcPlcyCliUser            TNamedItemOrEmpty,
        tmnxDynSvcPlcySapLimit           Unsigned32       
    }

tmnxDynSvcPlcyName OBJECT-TYPE
    SYNTAX      TNamedItem
    MAX-ACCESS  not-accessible
    STATUS      current
    DESCRIPTION
        "The value of tmnxDynSvcPlcyName specifies the identifier name of this 
         Dynamic Services policy."
    ::= { tmnxDynSvcPlcyEntry 1 }
    
tmnxDynSvcPlcyRowStatus OBJECT-TYPE
    SYNTAX      RowStatus
    MAX-ACCESS  read-create
    STATUS      current
    DESCRIPTION
        "The value of tmnxDynSvcPlcyRowStatus controls the creation and
         deletion of rows in the table."
    ::= { tmnxDynSvcPlcyEntry 2 }

tmnxDynSvcPlcyLastCh OBJECT-TYPE
    SYNTAX      TimeStamp
    MAX-ACCESS  read-only
    STATUS      current
    DESCRIPTION
        "The value of tmnxDynSvcPlcyLastCh indicates the sysUpTime at
         the time of the most recent management-initiated change to this
         conceptual row."
    ::= { tmnxDynSvcPlcyEntry 3 }

tmnxDynSvcPlcyDescription OBJECT-TYPE
    SYNTAX      TItemDescription
    MAX-ACCESS  read-create
    STATUS      current
    DESCRIPTION
        "The value of tmnxDynSvcPlcyDescription specifies 
         the description of this Dynamic Services policy."
    DEFVAL { "" }
    ::= { tmnxDynSvcPlcyEntry 4 }

tmnxDynSvcPlcyScriptPlcy OBJECT-TYPE
    SYNTAX      TNamedItemOrEmpty
    MAX-ACCESS  read-create
    STATUS      current
    DESCRIPTION
        "The value of tmnxDynSvcPlcyScriptPlcy specifies the identifier name 
         of the script policy associated with this Dynamic Services policy.
         
         For a non-empty value, a row with the same value for the object tmnxRadScriptPlcyName
         must exist in the TIMETRA-RADIUS-MIB::tmnxRadScriptPlcyTable."
    DEFVAL { "" }
    ::= { tmnxDynSvcPlcyEntry 5 }

tmnxDynSvcPlcyCliUser OBJECT-TYPE
    SYNTAX      TNamedItemOrEmpty
    MAX-ACCESS  read-create
    STATUS      current
    DESCRIPTION
        "The value of tmnxDynSvcPlcyCliUser specifies the identifier name 
         of the CLI user associated with this Dynamic Services policy.
         
         For a non-empty value, a row with the same value for the object tmnxUserName
         must exist in the TIMETRA-SECURITY-MIB::tmnxUserTable."
    DEFVAL { "" }
    ::= { tmnxDynSvcPlcyEntry 6 }
    
tmnxDynSvcPlcySapLimit OBJECT-TYPE
    SYNTAX      Unsigned32 (0..131072)
    MAX-ACCESS  read-create
    STATUS      current
    DESCRIPTION
        "The value of tmnxDynSvcPlcySapLimit specifies 
         the limit of the number of SAP's (Service Access Point)
         that can be created using this Dynamic Services policy.
         
         Each SAP counts for a dynamic service instance.
         
         Changing the value from any nonzero value to zero specifies that no
         new SAP's can be created."
    DEFVAL { 1 }
    ::= { tmnxDynSvcPlcyEntry 7 }
       
--
--      The Dynamic Services Policy Accounting policies Table
-- 

tmnxDynSvcPlcyApTable OBJECT-TYPE
    SYNTAX      SEQUENCE OF TmnxDynSvcPlcyApEntry
    MAX-ACCESS  not-accessible
    STATUS      current
    DESCRIPTION
        "The tmnxDynSvcPlcyApTable allows configuration of 
         accounting policies associated with Dynamic Services policies."
    ::= { tmnxDynSvcObjs 2 }

tmnxDynSvcPlcyApEntry OBJECT-TYPE
    SYNTAX      TmnxDynSvcPlcyApEntry
    MAX-ACCESS  not-accessible
    STATUS      current
    DESCRIPTION
        "Each entry represents the configuration for 
         a particular Dynamic Services profile.
         
         Two rows in this table are created automatically by the system for each
         row in the tmnxDynSvcPlcyTable."
    INDEX { tmnxDynSvcPlcyName,
            tmnxDynSvcPlcyApIndex }
    ::= { tmnxDynSvcPlcyApTable 1 }

TmnxDynSvcPlcyApEntry ::=
    SEQUENCE {
        tmnxDynSvcPlcyApIndex              Unsigned32,
        tmnxDynSvcPlcyApLastCh             TimeStamp,
        tmnxDynSvcPlcyApName               TNamedItemOrEmpty,
        tmnxDynSvcPlcyApStatsType          TmnxDynSrvAcctStatsType,
        tmnxDynSvcPlcyApUpdateInterval     Unsigned32,
        tmnxDynSvcPlcyApUpdateIvlJitter    INTEGER
    }

tmnxDynSvcPlcyApIndex OBJECT-TYPE
    SYNTAX      Unsigned32 (1..2)
    MAX-ACCESS  not-accessible
    STATUS      current
    DESCRIPTION
        "The value of tmnxDynSvcPlcyApIndex specifies the identifier number
         of this row within the scope of a Dynamic Services policy."
    ::= { tmnxDynSvcPlcyApEntry 1 }
    
tmnxDynSvcPlcyApLastCh OBJECT-TYPE
    SYNTAX      TimeStamp
    MAX-ACCESS  read-only
    STATUS      current
    DESCRIPTION
        "The value of tmnxDynSvcPlcyApLastCh indicates the sysUpTime at
         the time of the most recent management-initiated change to this
         conceptual row."
    ::= { tmnxDynSvcPlcyApEntry 2 }
  
tmnxDynSvcPlcyApName OBJECT-TYPE
    SYNTAX      TNamedItemOrEmpty
    MAX-ACCESS  read-create
    STATUS      current
    DESCRIPTION
        "The value of tmnxDynSvcPlcyApName specifies the identifier name 
         of a RADIUS server policy to be used for accounting.
         
         For a non-empty value, a row with the same value for the object tmnxRadSrvPlcyName
         must exist in the TIMETRA-RADIUS-MIB::tmnxRadSrvPlcyTable."
    DEFVAL { "" }
    ::= { tmnxDynSvcPlcyApEntry 3 }

tmnxDynSvcPlcyApStatsType OBJECT-TYPE
    SYNTAX      TmnxDynSrvAcctStatsType
    MAX-ACCESS  read-create
    STATUS      current
    DESCRIPTION
        "The value of tmnxDynSvcPlcyApStatsType specifies what type of
         statistics are sent to the accounting server."
    DEFVAL { volumeTime }
    ::= { tmnxDynSvcPlcyApEntry 4 }

tmnxDynSvcPlcyApUpdateInterval OBJECT-TYPE
    SYNTAX      Unsigned32 (0 | 5..259200)
    UNITS       "minutes"
    MAX-ACCESS  read-create
    STATUS      current
    DESCRIPTION
        "The value of tmnxDynSvcPlcyApUpdateInterval specifies 
         the time interval between consecutive accounting updates
         when using this Dynamic Services policy.
         
         The value zero specifies that no intermediate updates be sent."
    DEFVAL { 0 }
    ::= { tmnxDynSvcPlcyApEntry 5 }

tmnxDynSvcPlcyApUpdateIvlJitter OBJECT-TYPE
    SYNTAX      INTEGER( -10 | 0..3600 )
    MAX-ACCESS  read-create
    STATUS      current
    DESCRIPTION
        "The value of tmnxDynSvcPlcyApUpdateIvlJitter specifies the amount of
         jitter to be applied on the update interval which is 
         configured in tmnxDynSvcPlcyApUpdateInterval and can be overrruled by RADIUS.
         
         A value between 0..3600 specifies the amount of jitter in seconds.

         The (default) value -10 corresponds to a jitter value of 10% of 
         the update interval.
         
         The operational value used by the system will never be bigger then 
         10% of the update interval."
    DEFVAL { -10 }
    ::= { tmnxDynSvcPlcyApEntry 6 }

-- ----------------------------------------------------------------------------
--      The "Service Range" Group
-- ----------------------------------------------------------------------------

tmnxDynSvcRange OBJECT IDENTIFIER ::= { tmnxDynSvcObjs 3 }

-- set the values of these objects with a single SNMP set request

tmnxDynSvcRangeStart OBJECT-TYPE
    SYNTAX      TmnxServId ( 0 | 1..2147483647 )
    MAX-ACCESS  read-write
    STATUS      current
    DESCRIPTION 
        "The value of tmnxDynSvcRangeStart specifies 
         the start of the range of service identifiers
         used as dynamic services."
    DEFVAL { 0 }
    ::= { tmnxDynSvcRange 1 }

tmnxDynSvcRangeEnd OBJECT-TYPE
    SYNTAX      TmnxServId ( 0 | 1..2147483647 )
    MAX-ACCESS  read-write
    STATUS      current
    DESCRIPTION 
        "The value of tmnxDynSvcRangeStart specifies 
         the end of the range of service identifiers
         used as dynamic services.
         
         The value of tmnxDynSvcRangeEnd must be 
         greater than or equal to the value of tmnxDynSvcRangeStart."
    DEFVAL { 0 }
    ::= { tmnxDynSvcRange 2 }

-- 
-- tmnxDynSvcSapTable
--

tmnxDynSvcSapTable OBJECT-TYPE
    SYNTAX       SEQUENCE OF TmnxDynSvcSapEntry
    MAX-ACCESS   not-accessible
    STATUS       current
    DESCRIPTION  
       "The tmnxDynSvcSapTable contains the Service Access Points (SAP's) created
        for Dynamic Services.
        
        Conceptual rows in this table are created and destroyed automatically by
        the system."
    ::= { tmnxDynSvcObjs 4 }

tmnxDynSvcSapEntry OBJECT-TYPE
    SYNTAX       TmnxDynSvcSapEntry
    MAX-ACCESS   not-accessible
    STATUS       current
    DESCRIPTION  
       "Each conceptual row presents information about a particular 
        Dynamic Services SAP."
    INDEX { sapPortId, 
            sapEncapValue }
    ::= { tmnxDynSvcSapTable 1 }

TmnxDynSvcSapEntry ::=
    SEQUENCE {
        tmnxDynSvcSapAcctSessionId        TmnxSubAcctSessionId,
        tmnxDynSvcSapAcctSessionIdCtrl    TmnxSubAcctSessionId,
        tmnxDynSvcSapPolicy               TNamedItemOrEmpty,
        tmnxDynSvcSapScriptsExecuted      Counter32,
        tmnxDynSvcSapScriptsSuccess       Counter32,
        tmnxDynSvcSapLastScriptAction     INTEGER,
        tmnxDynSvcSapLastScriptTime       DateAndTime,
        tmnxDynSvcSapOrphaned             TruthValue,
        tmnxDynSvcSapService              TmnxServId,
        tmnxDynSvcSapLastScriptParams     OCTET STRING
  }

tmnxDynSvcSapAcctSessionId OBJECT-TYPE
    SYNTAX      TmnxSubAcctSessionId
    MAX-ACCESS  read-only
    STATUS      current
    DESCRIPTION
        "The value of tmnxDynSvcSapAcctSessionId indicates
         the identifier used for accounting."
    ::= { tmnxDynSvcSapEntry 1 }

tmnxDynSvcSapAcctSessionIdCtrl OBJECT-TYPE
    SYNTAX      TmnxSubAcctSessionId
    MAX-ACCESS  read-only
    STATUS      current
    DESCRIPTION
        "The value of tmnxDynSvcSapAcctSessionIdCtrl indicates
         the identifier used for accounting of the Customer Premises 
         Equipment's (CPE) control channel that is associated with this SAP."
    ::= { tmnxDynSvcSapEntry 2 }

tmnxDynSvcSapPolicy OBJECT-TYPE
    SYNTAX      TNamedItemOrEmpty
    MAX-ACCESS  read-only
    STATUS      current
    DESCRIPTION
        "The value of tmnxDynSvcSapPolicy indicates
         the Dynamic Services policy associated with this SAP.
         
         It refers to a conceptual row in the tmnxDynSvcPlcyTable."
    ::= { tmnxDynSvcSapEntry 3 }

tmnxDynSvcSapScriptsExecuted OBJECT-TYPE
    SYNTAX      Counter32
    MAX-ACCESS  read-only
    STATUS      current
    DESCRIPTION
        "The value of tmnxDynSvcSapScriptsExecuted indicates
         the number of times a script was executed for this SAP."
    ::= { tmnxDynSvcSapEntry 4 }
    
tmnxDynSvcSapScriptsSuccess OBJECT-TYPE
    SYNTAX      Counter32
    MAX-ACCESS  read-only
    STATUS      current
    DESCRIPTION
        "The value of tmnxDynSvcSapScriptsSuccess indicates
         the number of times a script was successfully executed for this SAP."
    ::= { tmnxDynSvcSapEntry 5 }
    
tmnxDynSvcSapLastScriptAction OBJECT-TYPE
    SYNTAX      INTEGER {
                    setup (1), 
                    modify (2), 
                    teardown (3), 
                    commit (4), 
                    revert (5)
                }
    MAX-ACCESS  read-only
    STATUS      current
    DESCRIPTION
        "The value of tmnxDynSvcSapLastScriptAction indicates
         the action of the last script executed for this SAP."
    ::= { tmnxDynSvcSapEntry 6 }
    
tmnxDynSvcSapLastScriptTime OBJECT-TYPE
    SYNTAX      DateAndTime (SIZE(11))
    MAX-ACCESS  read-only
    STATUS      current
    DESCRIPTION
        "The value of tmnxDynSvcSapLastScriptAction indicates
         the time when the last script executed for this SAP."
    ::= { tmnxDynSvcSapEntry 7 }

tmnxDynSvcSapOrphaned OBJECT-TYPE
    SYNTAX      TruthValue
    MAX-ACCESS  read-only
    STATUS      current
    DESCRIPTION
        "The value of tmnxDynSvcSapOrphaned indicates
         whether the corresponding SAP was not deleted after running
         the teardown portion of the script.
         
         If set to 'true', the SAP was not deleted, and manual action is
         needed to get rid of the SAP."
    ::= { tmnxDynSvcSapEntry 8 }

tmnxDynSvcSapService OBJECT-TYPE
    SYNTAX      TmnxServId
    MAX-ACCESS  read-only
    STATUS      current
    DESCRIPTION
        "The value of tmnxDynSvcSapService indicates
         the parent service of this SAP.
         
         The value zero indicates that the parent service is currently unknown."
    ::= { tmnxDynSvcSapEntry 9 }

tmnxDynSvcSapLastScriptParams OBJECT-TYPE
    SYNTAX      OCTET STRING (SIZE (0..1000))
    MAX-ACCESS  read-only
    STATUS      current
    DESCRIPTION
        "The value of tmnxDynSvcSapLastScriptParams indicates
         the parameter string of the script instance that was last executed
         on this SAP.
         
         The value of this object corresponds with the content of the
         RADIUS vendor-specific Alc-Dyn-Serv-Script-Params option.
         
         The value of this object is subjected to the same constraints as
         for the DisplayString syntax."
    ::= { tmnxDynSvcSapEntry 10 }

-- 
-- tmnxDynSvcSapAcctTable
--

tmnxDynSvcSapAcctTable OBJECT-TYPE
    SYNTAX       SEQUENCE OF TmnxDynSvcSapAcctEntry
    MAX-ACCESS   not-accessible
    STATUS       current
    DESCRIPTION  
       "The tmnxDynSvcSapAcctTable contains the Dynamic Services SAP's
        accounting information.
        
        Conceptual rows in this table are created and destroyed automatically by
        the system."
    ::= { tmnxDynSvcObjs 5 }

tmnxDynSvcSapAcctEntry OBJECT-TYPE
    SYNTAX       TmnxDynSvcSapAcctEntry
    MAX-ACCESS   not-accessible
    STATUS       current
    DESCRIPTION  
       "Each conceptual row presents information about an accounting instance
        of a particular Dynamic Services SAP."
    INDEX { sapPortId, 
            sapEncapValue,
            tmnxDynSvcSapAcctIndex }
    ::= { tmnxDynSvcSapAcctTable 1 }

TmnxDynSvcSapAcctEntry ::=
    SEQUENCE {
        tmnxDynSvcSapAcctIndex           Unsigned32,
        tmnxDynSvcSapAcctAcctStatus      TmnxEnabledDisabled,
        tmnxDynSvcSapAcctStatsType       TmnxDynSrvAcctStatsType,
        tmnxDynSvcSapAcctAcctInterval    Unsigned32
  }

tmnxDynSvcSapAcctIndex OBJECT-TYPE
    SYNTAX      Unsigned32 (1..2)
    MAX-ACCESS  not-accessible
    STATUS      current
    DESCRIPTION
        "The value of tmnxDynSvcSapAcctIndex specifies
         the identifier number of this conceptual row within the scope of a
         Dynamic Services SAP."
    ::= { tmnxDynSvcSapAcctEntry 1 }

tmnxDynSvcSapAcctAcctStatus OBJECT-TYPE
    SYNTAX      TmnxEnabledDisabled
    MAX-ACCESS  read-only
    STATUS      current
    DESCRIPTION
        "The value of tmnxDynSvcSapAcctAcctStatus indicates
         the operational status of this accounting instance."
    ::= { tmnxDynSvcSapAcctEntry 2 }

tmnxDynSvcSapAcctStatsType OBJECT-TYPE
    SYNTAX      TmnxDynSrvAcctStatsType
    MAX-ACCESS  read-only
    STATUS      current
    DESCRIPTION
        "The value of tmnxDynSvcSapAcctStatsType indicates
         the actual type of accounting statistics 
         gathered by this accounting instance.
         
         It can be specified by the associated Dynamic Services policy
         (the object tmnxDynSvcPlcyApStatsType), or by the AAA server."
    ::= { tmnxDynSvcSapAcctEntry 3 }

tmnxDynSvcSapAcctAcctInterval OBJECT-TYPE
    SYNTAX      Unsigned32
    UNITS       "minutes"
    MAX-ACCESS  read-only
    STATUS      current
    DESCRIPTION
        "The value of tmnxDynSvcSapAcctAcctInterval indicates
         the actual accounting update interval for this accounting instance. 
         
         It can be specified by the associated Dynamic Services policy
         (the object tmnxDynSvcPlcyApUpdateInterval), or by the AAA server."
    ::= { tmnxDynSvcSapAcctEntry 4 }

-- 
-- tmnxDynSvcRootObjTable
--

tmnxDynSvcRootObjTable OBJECT-TYPE
    SYNTAX       SEQUENCE OF TmnxDynSvcRootObjEntry
    MAX-ACCESS   not-accessible
    STATUS       current
    DESCRIPTION  
       "The tmnxDynSvcRootObjTable contains information of the Root objects
        created by Dynamic Services.
        
        A root object is an object created by a Dynamic Service of which the 
        parent is not created by a Dynamic Service.
                
        Conceptual rows in this table are created and destroyed automatically by
        the system."
    ::= { tmnxDynSvcObjs 6 }

tmnxDynSvcRootObjEntry OBJECT-TYPE
    SYNTAX       TmnxDynSvcRootObjEntry
    MAX-ACCESS   not-accessible
    STATUS       current
    DESCRIPTION  
       "Each conceptual row presents information about a Dynamic Services root object."
    INDEX { tmnxDynSvcRootObjIndex }
    ::= { tmnxDynSvcRootObjTable 1 }

TmnxDynSvcRootObjEntry ::=
    SEQUENCE {
        tmnxDynSvcRootObjIndex           Unsigned32,
        tmnxDynSvcRootObjInstance        RowPointer,
        tmnxDynSvcRootObjOrphanTime      TimeStamp,
        tmnxDynSvcRootObjSnippetName     DisplayString,
        tmnxDynSvcRootObjSnippetInstance DisplayString
  }

tmnxDynSvcRootObjIndex OBJECT-TYPE
    SYNTAX      Unsigned32
    MAX-ACCESS  not-accessible
    STATUS      current
    DESCRIPTION
        "The value of tmnxDynSvcRootObjIndex specifies the index that identifies 
         this conceptual row within the scope of a Dynamic Services Root object."
    ::= { tmnxDynSvcRootObjEntry 1 }
    
tmnxDynSvcRootObjInstance OBJECT-TYPE 
    SYNTAX      RowPointer
    MAX-ACCESS  read-only
    STATUS      current
    DESCRIPTION  
        "The value of tmnxDynSvcRootObjInstance indicates the concerned root object."
     ::= { tmnxDynSvcRootObjEntry 2 }
    
tmnxDynSvcRootObjOrphanTime OBJECT-TYPE
    SYNTAX      TimeStamp
    MAX-ACCESS  read-only
    STATUS      current
    DESCRIPTION
        "The value of tmnxDynSvcRootObjOrphanTime indicates the sysUpTime when
         the object was orphaned.
         
         When the object is not orphaned or when the time is unknown, the 
         tmnxDynSvcRootObjOrphanTime is set to 0."
    ::= { tmnxDynSvcRootObjEntry 3 }

tmnxDynSvcRootObjSnippetName OBJECT-TYPE
    SYNTAX      DisplayString
    MAX-ACCESS  read-only
    STATUS      current
    DESCRIPTION
        "The value of tmnxDynSvcRootObjSnippetName indicates the type-name  
         from the snippet to which the root object belongs.
         
         A 'snippet' is the name of a set of python functions to create, modify
         or destroy configuration; for example: a snippet called 'vprn' in order
         to create/modify/destroy VPRN services.

         When the tmnxDynSvcRootObjSnippetName is an empty string it implies
         that there is no snippet."
    ::= { tmnxDynSvcRootObjEntry 4 }

tmnxDynSvcRootObjSnippetInstance OBJECT-TYPE
    SYNTAX      DisplayString
    MAX-ACCESS  read-only
    STATUS      current
    DESCRIPTION
        "The value of tmnxDynSvcRootObjSnippetInstance indicates the identifier
         from the snippet to which the object belongs and is unique within
         the snippet scope.

         A 'snippet instance' is an instance of the configuration created by a snippet;
         for example: a particular VPRN service.

        When the tmnxDynSvcRootObjSnippetInstance is an empty string it implies
        that there is no snippet."
    ::= { tmnxDynSvcRootObjEntry 5 }

-- 
-- tmnxDynSvcStatsTable
--

tmnxDynSvcStatsTable OBJECT-TYPE
    SYNTAX       SEQUENCE OF TmnxDynSvcStatsEntry
    MAX-ACCESS   not-accessible
    STATUS       current
    DESCRIPTION  
       "The tmnxDynSvcStatsTable shows statistics information of the Dynamic Services."
    ::= { tmnxDynSvcObjs 7 }

tmnxDynSvcStatsEntry OBJECT-TYPE
    SYNTAX       TmnxDynSvcStatsEntry
    MAX-ACCESS   not-accessible
    STATUS       current
    DESCRIPTION  
       "Each conceptual row represents a statistic counter.

        Entries in this table are created and destroyed by the system.
         
        Rows are only created where the statistics value is nonzero;
        this allows faster walking through this table; hence, it is recommended
        to perform only get-next-request operations to retrieve information
        from this table."
    INDEX { tmnxDynSvcStatsId }
    ::= { tmnxDynSvcStatsTable 1 }

TmnxDynSvcStatsEntry ::=
    SEQUENCE {
        tmnxDynSvcStatsId                Unsigned32,
        tmnxDynSvcStatsDescr             TItemDescription,
        tmnxDynSvcStatsVal               Counter32
  }

tmnxDynSvcStatsId OBJECT-TYPE
    SYNTAX      Unsigned32
    MAX-ACCESS  not-accessible
    STATUS      current
    DESCRIPTION
        "The value of tmnxDynSvcStatsId specifies the number that identifies 
         this conceptual row within the scope of a Dynamic Services."
    ::= { tmnxDynSvcStatsEntry 1 }
    
tmnxDynSvcStatsDescr OBJECT-TYPE
    SYNTAX      TItemDescription
    MAX-ACCESS  read-only
    STATUS      current
    DESCRIPTION 
       "The value of the object tmnxDynSvcStatsDescr specifies
        the description of the statistic counter
        contained in this conceptual row."
    ::= { tmnxDynSvcStatsEntry 2 }

tmnxDynSvcStatsVal OBJECT-TYPE
    SYNTAX      Counter32
    MAX-ACCESS  read-only
    STATUS      current
    DESCRIPTION 
       "The value of the object tmnxDynSvcStatsVal indicates
        the value of the statistics contained in this conceptual row."
    ::= { tmnxDynSvcStatsEntry 3 }    

-- 
-- tmnxDynSvcSnippetTable
--

tmnxDynSvcSnippetTable OBJECT-TYPE
    SYNTAX       SEQUENCE OF TmnxDynSvcSnippetEntry
    MAX-ACCESS   not-accessible
    STATUS       current
    DESCRIPTION  
       "The tmnxDynSvcSnippetTable contains information of the snippets
        created by Dynamic Services.
        
        Conceptual rows in this table are created and destroyed automatically by
        the system."
    ::= { tmnxDynSvcObjs 8 }

tmnxDynSvcSnippetEntry OBJECT-TYPE
    SYNTAX       TmnxDynSvcSnippetEntry
    MAX-ACCESS   not-accessible
    STATUS       current
    DESCRIPTION  
       "Each conceptual row presents information about a snippet
        within the scope of Dynamic Services."
    INDEX { tmnxDynSvcSnippetName,
            tmnxDynSvcSnippetInstance }
    ::= { tmnxDynSvcSnippetTable 1 }

TmnxDynSvcSnippetEntry ::=
    SEQUENCE {
        tmnxDynSvcSnippetName            DisplayString,
        tmnxDynSvcSnippetInstance        DisplayString,
        tmnxDynSvcSnippetRefCount        Counter32,
        tmnxDynSvcSnippetDictLength      Unsigned32
  }

tmnxDynSvcSnippetName OBJECT-TYPE
    SYNTAX      DisplayString (SIZE(0..32))
    MAX-ACCESS  not-accessible
    STATUS      current
    DESCRIPTION
        "The value of tmnxDynSvcSnippetName specifies the type-name from the snippet 
         that identifies this conceptual row within the scope of a Dynamic Services.
             
         The type-name is used to lookup the set of python functions to create, modify
         or destroy configuration; for example: a snippet with type-name 'vprn' could be 
         used to create/modify/destroy VPRN services."
    ::= { tmnxDynSvcSnippetEntry 1 }
    
tmnxDynSvcSnippetInstance OBJECT-TYPE
    SYNTAX      DisplayString (SIZE(0..48))
    MAX-ACCESS  not-accessible
    STATUS      current
    DESCRIPTION 
       "The value of the object tmnxDynSvcSnippetInstance specifies the identifier
        from the snippet that in combination with the type-name uniquely identifies a
        snippet.

        A 'snippet instance' is an instance of the configuration created by a snippet;
        for example: a particular VPRN service."
    ::= { tmnxDynSvcSnippetEntry 2 }

tmnxDynSvcSnippetRefCount OBJECT-TYPE
    SYNTAX      Counter32
    MAX-ACCESS  read-only
    STATUS      current
    DESCRIPTION 
       "The value of the object tmnxDynSvcSnippetRefCount indicates
        the number of times this snippet is referenced by other snippets."
    ::= { tmnxDynSvcSnippetEntry 3 }  
    
tmnxDynSvcSnippetDictLength OBJECT-TYPE
    SYNTAX      Unsigned32
    MAX-ACCESS  read-only
    STATUS      current
    DESCRIPTION 
       "The value of the object tmnxDynSvcSnippetDictLength indicates
        the length of the python dictionary stored for this snippet."
    ::= { tmnxDynSvcSnippetEntry 4 }       

-- 
-- tmnxDynSvcSnippetRootObjTable
--

tmnxDynSvcSnippetRootObjTable OBJECT-TYPE
    SYNTAX       SEQUENCE OF TmnxDynSvcSnippetRootObjEntry
    MAX-ACCESS   not-accessible
    STATUS       current
    DESCRIPTION  
       "The tmnxDynSvcSnippetRootObjTable contains information of the root objects 
        created by a snippet within the scope of a Dynamic Service.
        
        Conceptual rows in this table are created and destroyed automatically by
        the system."
    ::= { tmnxDynSvcObjs 9 }

tmnxDynSvcSnippetRootObjEntry OBJECT-TYPE
    SYNTAX       TmnxDynSvcSnippetRootObjEntry
    MAX-ACCESS   not-accessible
    STATUS       current
    DESCRIPTION  
       "Each conceptual row presents information about a root object 
        created by a snippet within the scope of a Dynamic Service."
    INDEX { tmnxDynSvcSnippetName,
            tmnxDynSvcSnippetInstance,
            tmnxDynSvcSnippetRootObjIdx }
    ::= { tmnxDynSvcSnippetRootObjTable 1 }

TmnxDynSvcSnippetRootObjEntry ::=
    SEQUENCE {
        tmnxDynSvcSnippetRootObjIdx      Unsigned32,
        tmnxDynSvcSnippetRootObjOid      RowPointer
  }

tmnxDynSvcSnippetRootObjIdx OBJECT-TYPE
    SYNTAX      Unsigned32
    MAX-ACCESS  not-accessible
    STATUS      current
    DESCRIPTION 
       "The value of the object tmnxDynSvcSnippetRootObjIdx specifies
        the index that identifies this conceptual row within the scope of the snippet."
    ::= { tmnxDynSvcSnippetRootObjEntry 1 }  
    
tmnxDynSvcSnippetRootObjOid OBJECT-TYPE
    SYNTAX      RowPointer
    MAX-ACCESS  read-only
    STATUS      current
    DESCRIPTION 
       "The value of the object tmnxDynSvcSnippetRootObjOid indicates
        the concerned root object that was created by the snippet."
    ::= { tmnxDynSvcSnippetRootObjEntry 2 }    
    
-- 
-- tmnxDynSvcSnippetRefTable
--

tmnxDynSvcSnippetRefTable OBJECT-TYPE
    SYNTAX       SEQUENCE OF TmnxDynSvcSnippetRefEntry
    MAX-ACCESS   not-accessible
    STATUS       current
    DESCRIPTION  
       "The tmnxDynSvcSnippetRefTable contains information of the referenced snippets 
        created by a phyton script within the scope of a Dynamic Service.
        
        Conceptual rows in this table are created and destroyed automatically by
        the system."
    ::= { tmnxDynSvcObjs 10 }

tmnxDynSvcSnippetRefEntry OBJECT-TYPE
    SYNTAX       TmnxDynSvcSnippetRefEntry
    MAX-ACCESS   not-accessible
    STATUS       current
    DESCRIPTION  
       "Each conceptual row presents information about a referenced snippet 
        created by a phyton script within the scope of a Dynamic Service."
    INDEX { tmnxDynSvcSnippetName,
            tmnxDynSvcSnippetInstance,
            tmnxDynSvcSnippetRefIdx }
    ::= { tmnxDynSvcSnippetRefTable 1 }

TmnxDynSvcSnippetRefEntry ::=
    SEQUENCE {
        tmnxDynSvcSnippetRefIdx         Unsigned32,
        tmnxDynSvcSnippetRefSnipName    DisplayString,
        tmnxDynSvcSnippetRefSnipInst    DisplayString
  }

tmnxDynSvcSnippetRefIdx OBJECT-TYPE
    SYNTAX      Unsigned32
    MAX-ACCESS  not-accessible
    STATUS      current
    DESCRIPTION 
       "The value of the object tmnxDynSvcSnippetRefIdx specifies the index that  
        identifies this conceptual row within the scope of the snippet."
    ::= { tmnxDynSvcSnippetRefEntry 1 }  
    
tmnxDynSvcSnippetRefSnipName OBJECT-TYPE
    SYNTAX      DisplayString (SIZE(0..32))
    MAX-ACCESS  read-only
    STATUS      current
    DESCRIPTION 
       "The value of the object tmnxDynSvcSnippetRefSnipName indicates
        the type-name from the snippet created or referenced by a phyton script."
    ::= { tmnxDynSvcSnippetRefEntry 2 }   
     
tmnxDynSvcSnippetRefSnipInst OBJECT-TYPE
    SYNTAX      DisplayString (SIZE(0..48))
    MAX-ACCESS  read-only
    STATUS      current
    DESCRIPTION 
       "The value of the object tmnxDynSvcSnippetRefSnipInst indicates
        the identifier from the snippet created or referenced by a phyton script."
    ::= { tmnxDynSvcSnippetRefEntry 3 }   
    
-- 
-- tmnxDynSvcSnippetResIdTable
--

tmnxDynSvcSnippetResIdTable OBJECT-TYPE
    SYNTAX       SEQUENCE OF TmnxDynSvcSnippetResIdEntry
    MAX-ACCESS   not-accessible
    STATUS       current
    DESCRIPTION  
       "The tmnxDynSvcSnippetResIdTable contains information of the identifiers 
        reserved by a phyton script within the scope of a Dynamic Service.
        
        Conceptual rows in this table are created and destroyed automatically by
        the system."
    ::= { tmnxDynSvcObjs 11 }

tmnxDynSvcSnippetResIdEntry OBJECT-TYPE
    SYNTAX       TmnxDynSvcSnippetResIdEntry
    MAX-ACCESS   not-accessible
    STATUS       current
    DESCRIPTION  
       "Each conceptual row presents information about an identifier 
        reserved by a phyton script within the scope of a Dynamic Service."
    INDEX { tmnxDynSvcSnippetName,
            tmnxDynSvcSnippetInstance,
            tmnxDynSvcSnippetResIdIdx }
    ::= { tmnxDynSvcSnippetResIdTable 1 }

TmnxDynSvcSnippetResIdEntry ::=
    SEQUENCE {
        tmnxDynSvcSnippetResIdIdx       Unsigned32,
        tmnxDynSvcSnippetResIdType      DisplayString,
        tmnxDynSvcSnippetResIdValue     DisplayString
  }

tmnxDynSvcSnippetResIdIdx OBJECT-TYPE
    SYNTAX      Unsigned32
    MAX-ACCESS  not-accessible
    STATUS      current
    DESCRIPTION 
       "The value of the object tmnxDynSvcSnippetResIdIdx specifies the index that  
        identifies this conceptual row within the scope of the snippet."
    ::= { tmnxDynSvcSnippetResIdEntry 1 }  
    
tmnxDynSvcSnippetResIdType OBJECT-TYPE
    SYNTAX      DisplayString (SIZE(0..32))
    MAX-ACCESS  read-only
    STATUS      current
    DESCRIPTION 
       "The value of the object tmnxDynSvcSnippetResIdType indicates
        the type-name from the identifier reserved by a phyton script."
    ::= { tmnxDynSvcSnippetResIdEntry 2 }   
     
tmnxDynSvcSnippetResIdValue OBJECT-TYPE
    SYNTAX      DisplayString (SIZE(0..48))
    MAX-ACCESS  read-only
    STATUS      current
    DESCRIPTION 
       "The value of the object tmnxDynSvcSnippetResIdValue indicates
        the value from the identifier reserved by a phyton script."
    ::= { tmnxDynSvcSnippetResIdEntry 3 }  

-- ----------------------------------------------------------------------------
--      The "timer" Group
-- ----------------------------------------------------------------------------

tmnxDynSvcTimer OBJECT IDENTIFIER ::= { tmnxDynSvcObjs 12 }

tmnxDynSvcTimerAccSetupTimeout OBJECT-TYPE
    SYNTAX      Unsigned32( 2..3600 )
    MAX-ACCESS  read-write
    STATUS      current
    DESCRIPTION 
        "The value of tmnxDynSvcTimerAccSetupTimeout specifies 
         the timeout in seconds after which a script is cancelled for 
         setup actions received via RADIUS Access-Accept messages."
    DEFVAL { 30 }
    ::= { tmnxDynSvcTimer 1 }

                
-- --------------------------------------------------------
-- Scalar objects
-- --------------------------------------------------------

tmnxDynSvcPlcyTableLastCh OBJECT-TYPE
    SYNTAX      TimeStamp
    MAX-ACCESS  read-only
    STATUS      current
    DESCRIPTION
        "The value of the object tmnxDynSvcPlcyTableLastCh indicates
         the value of sysUpTime at the time of the last modification of
         an entry in the tmnxDynSvcPlcyTable."
    ::= { tmnxDynSvcObjs 100 }

tmnxDynSvcPlcyApTableLastCh OBJECT-TYPE
    SYNTAX      TimeStamp
    MAX-ACCESS  read-only
    STATUS      current
    DESCRIPTION
        "The value of the object tmnxDynSvcPlcyApTableLastCh indicates
         the value of sysUpTime at the time of the last modification of
         an entry in the tmnxDynSvcPlcyApTable."
    ::= { tmnxDynSvcObjs 101 }

tmnxDynSvcSapTableLastCh OBJECT-TYPE
    SYNTAX       TimeStamp
    MAX-ACCESS   read-only
    STATUS       current
    DESCRIPTION
        "The value of tmnxDynSvcSapTableLastCh indicates the
         sysUpTime at the time of the last change of a row in the
         tmnxDynSvcSapTable or an associated row in the tmnxDynSvcSapAcctTable.

         If no changes occurred since the last re-initialization
         of the local network management subsystem, then this object
         contains a zero value."
    ::= { tmnxDynSvcObjs 102 }

tmnxDynSvcRootObjTableLastCh OBJECT-TYPE
    SYNTAX       TimeStamp
    MAX-ACCESS   read-only
    STATUS       current
    DESCRIPTION
        "The value of the object tmnxDynSvcRootObjTableLastCh indicates
         the value of sysUpTime at the time of the last modification of
         an entry in the tmnxDynSvcRootObjTable."
    ::= { tmnxDynSvcObjs 103 }

tmnxDynSvcNonStoredRootObjCount  OBJECT-TYPE
    SYNTAX   Counter32    
    MAX-ACCESS   read-only
    STATUS       current
    DESCRIPTION
        "The value of the object tmnxDynSvcNonStoredRootObjCount indicates
        the number of root objects that are currently not stored in the 
        tmnxDynSvcRootObjTable.
        
        The value of tmnxDynSvcNonStoredRootObjCount can go back to 0
        when the objects that could not be stored in the tmnxDynSvcRootObjTable
        are deleted again."    
    ::= { tmnxDynSvcObjs 104 }
    
tmnxDynSvcSnippetTableLastCh OBJECT-TYPE
    SYNTAX       TimeStamp
    MAX-ACCESS   read-only
    STATUS       current
    DESCRIPTION
        "The value of the object tmnxDynSvcSnippetTableLastCh indicates
         the value of sysUpTime at the time of the last modification of
         an entry in the tmnxDynSvcSnippetTable."
    ::= { tmnxDynSvcObjs 105 }  
    
tmnxDynSvcSnipRootObjTblLastCh OBJECT-TYPE
    SYNTAX       TimeStamp
    MAX-ACCESS   read-only
    STATUS       current
    DESCRIPTION
        "The value of the object tmnxDynSvcSnipRootObjTblLastCh indicates
         the value of sysUpTime at the time of the last modification of
         an entry in the tmnxDynSvcSnippetRootObjTable."
    ::= { tmnxDynSvcObjs 106 }  
     
tmnxDynSvcSnippetRefTableLastCh OBJECT-TYPE
    SYNTAX       TimeStamp
    MAX-ACCESS   read-only
    STATUS       current
    DESCRIPTION
        "The value of the object tmnxDynSvcSnippetRefTableLastCh indicates
         the value of sysUpTime at the time of the last modification of
         an entry in the tmnxDynSvcSnippetRefTable."
    ::= { tmnxDynSvcObjs 107 }  
     
tmnxDynSvcSnippetResIdTblLastCh OBJECT-TYPE
    SYNTAX       TimeStamp
    MAX-ACCESS   read-only
    STATUS       current
    DESCRIPTION
        "The value of the object tmnxDynSvcSnippetResIdTblLastCh indicates
         the value of sysUpTime at the time of the last modification of
         an entry in the tmnxDynSvcSnippetResIdTable."
    ::= { tmnxDynSvcObjs 108 }  

tmnxDynSvcStatsLastClearedTime OBJECT-TYPE
    SYNTAX          TimeStamp
    MAX-ACCESS      read-only
    STATUS          current
    DESCRIPTION
        "The value of the object tmnxDynSvcStatsLastClearedTime indicates
         the value of sysUpTime at the time when the counters in 
         tmnxDynSvcStatsTable were last cleared."
    ::= { tmnxDynSvcObjs 109 }  

--  Notification objects

tmnxDynSvcNotifDescription  OBJECT-TYPE
    SYNTAX      DisplayString (SIZE(0..255))
    MAX-ACCESS  accessible-for-notify
    STATUS      current
    DESCRIPTION
        "The object tmnxDynSvcNotifDescription is a printable character 
         string."
    ::= { tmnxDynSvcNotificationObjs 1 }

tmnxDynSvcNotifSapPortId OBJECT-TYPE
    SYNTAX          TmnxPortID
    MAX-ACCESS      accessible-for-notify
    STATUS          current
    DESCRIPTION     
        "The object tmnxDynSvcNotifSapPortId is the ID number 
         of the access port where a SAP is defined."
    ::= { tmnxDynSvcNotificationObjs 2 }

tmnxDynSvcNotifSapEncapValue OBJECT-TYPE
    SYNTAX      TmnxEncapVal
    MAX-ACCESS  accessible-for-notify
    STATUS      current
    DESCRIPTION
        "The object tmnxDynSvcNotifSapEncapValue is the value of the label
         used to identify a SAP on the access port specified 
         by tmnxDynSvcNotifSapPortId."
     ::= { tmnxDynSvcNotificationObjs 3 }

tmnxDynSvcNotifSapAcctSessionId OBJECT-TYPE
    SYNTAX      TmnxSubAcctSessionId
    MAX-ACCESS  accessible-for-notify
    STATUS      current
    DESCRIPTION
        "The object tmnxDynSvcNotifSapAcctSessionId is the value of
         the identifier used for accounting."
    ::= { tmnxDynSvcNotificationObjs 4 }
    
--  Notifications

tmnxDynSvcSapFailed NOTIFICATION-TYPE
    OBJECTS {
        tmnxDynSvcNotifSapAcctSessionId,
        tmnxDynSvcNotifSapPortId,
        tmnxDynSvcNotifSapEncapValue,
        tmnxDynSvcNotifDescription
    }
    STATUS current
    DESCRIPTION
        "[CAUSE] The tmnxDynSvcSapFailed notification is sent when 
         a Dynamic Services service SAP creation, modification or removal failed.
         
         [EFFECT] The desired new configuration is not in effect; the
         system has returned to the original configuration if possible.

         [RECOVERY] No recovery is necessary when the original configuration
         could be restored.
         
         If the SAP does not exist in the tmnxDynSvcSapTable at the time
         of this notification, the value 'invalid portid' is put 
         in the object tmnxDynSvcNotifSapPortId."
    ::= { tmnxDynSvcNotifications 1 }

-- ----------------------------------------------------------------------------
--  Conformance Groups
-- ----------------------------------------------------------------------------
tmnxDynSvcGroup   OBJECT-GROUP
    OBJECTS {
        tmnxDynSvcPlcyRowStatus,
        tmnxDynSvcPlcyLastCh,
        tmnxDynSvcPlcyDescription,
        tmnxDynSvcPlcyScriptPlcy,
        tmnxDynSvcPlcyCliUser,
        tmnxDynSvcPlcySapLimit,
        tmnxDynSvcPlcyTableLastCh,
        tmnxDynSvcPlcyApLastCh,
        tmnxDynSvcPlcyApName,
        tmnxDynSvcPlcyApStatsType,
        tmnxDynSvcPlcyApUpdateInterval,
        tmnxDynSvcPlcyApTableLastCh,
        tmnxDynSvcRangeStart,
        tmnxDynSvcRangeEnd,
        tmnxDynSvcSapAcctSessionId ,
        tmnxDynSvcSapAcctSessionIdCtrl,
        tmnxDynSvcSapPolicy,
        tmnxDynSvcSapScriptsExecuted,
        tmnxDynSvcSapScriptsSuccess,
        tmnxDynSvcSapLastScriptAction,
        tmnxDynSvcSapLastScriptTime,
        tmnxDynSvcSapOrphaned,
        tmnxDynSvcSapService,
        tmnxDynSvcSapLastScriptParams,
        tmnxDynSvcSapTableLastCh,
        tmnxDynSvcSapAcctAcctStatus,
        tmnxDynSvcSapAcctStatsType,
        tmnxDynSvcSapAcctAcctInterval,
        tmnxDynSvcPlcyApUpdateIvlJitter,
        tmnxDynSvcRootObjInstance,
        tmnxDynSvcRootObjOrphanTime,
        tmnxDynSvcRootObjSnippetName,
        tmnxDynSvcRootObjSnippetInstance,
        tmnxDynSvcRootObjTableLastCh,
        tmnxDynSvcNonStoredRootObjCount,
        tmnxDynSvcStatsDescr,
        tmnxDynSvcStatsVal,
        tmnxDynSvcSnippetRefCount,
        tmnxDynSvcSnippetDictLength,
        tmnxDynSvcSnippetRootObjOid,
        tmnxDynSvcSnippetRefSnipName,
        tmnxDynSvcSnippetRefSnipInst,
        tmnxDynSvcSnippetResIdType,
        tmnxDynSvcSnippetResIdValue,
        tmnxDynSvcSnippetTableLastCh,
        tmnxDynSvcSnipRootObjTblLastCh,
        tmnxDynSvcSnippetRefTableLastCh,
        tmnxDynSvcSnippetResIdTblLastCh,
        tmnxDynSvcTimerAccSetupTimeout,
        tmnxDynSvcStatsLastClearedTime
    }
    STATUS      current
    DESCRIPTION
        "The group of objects for the
         management of Dynamic Services
         on Alcatel-Lucent SROS series systems."
    ::= { tmnxDynSvcGroups 1 }

tmnxDynSvcNotifyObjsGroup OBJECT-GROUP
    OBJECTS {   
        tmnxDynSvcNotifSapAcctSessionId,
        tmnxDynSvcNotifSapPortId,
        tmnxDynSvcNotifSapEncapValue,
        tmnxDynSvcNotifDescription
    }
    STATUS        current
    DESCRIPTION
        "The group of notification objects supporting Dynamic Services notifications
         on Alcatel-Lucent SROS series systems."
    ::= { tmnxDynSvcGroups 99 }

-- ----------------------
-- NOTIFICATION-GROUPS
-- ----------------------

tmnxDynSvcNotifyGroup NOTIFICATION-GROUP
    NOTIFICATIONS {
        tmnxDynSvcSapFailed
    }
    STATUS      current
    DESCRIPTION
        "The group of notifications supporting Dynamic Services
         on Alcatel-Lucent SROS series systems."
    ::= { tmnxDynSvcGroups 100 }
  
-- ----------------------------------------------------------------------------
--  Compliance information
-- ----------------------------------------------------------------------------
tmnxDynSvcCompliance MODULE-COMPLIANCE
    STATUS  current
    DESCRIPTION
        "The compliance statement for management of Dynamic Services
         on Alcatel-Lucent 7xxx series systems."
    MODULE  -- this module
        MANDATORY-GROUPS {
            tmnxDynSvcGroup
        }
    ::= { tmnxDynSvcCompliances 1 }

tmnxDynSvcNotifyCompliance MODULE-COMPLIANCE
    STATUS  current
    DESCRIPTION
        "The compliance statement for Dynamic Services notifications
         on Alcatel-Lucent SROS series systems."
    MODULE  -- this module
        MANDATORY-GROUPS {
            tmnxDynSvcNotifyGroup
        }
    ::= { tmnxDynSvcCompliances 2 }
END
