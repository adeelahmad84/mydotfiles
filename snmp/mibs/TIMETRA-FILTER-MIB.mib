TIMETRA-FILTER-MIB DEFINITIONS ::= BEGIN

IMPORTS
    MODULE-IDENTITY, OBJECT-TYPE, NOTIFICATION-TYPE,
    Unsigned32, Integer32, IpAddress, Counter32, Counter64,
    Gauge32, TimeTicks, Opaque
        FROM SNMPv2-SMI

    MODULE-COMPLIANCE, OBJECT-GROUP, NOTIFICATION-GROUP
        FROM SNMPv2-CONF

    TEXTUAL-CONVENTION, RowStatus, MacAddress,
    TruthValue, DisplayString, TimeStamp,
    RowPointer
        FROM SNMPv2-TC

    timetraSRMIBModules, tmnxSRObjs, tmnxSRNotifyPrefix,
    tmnxSRConfs
        FROM TIMETRA-GLOBAL-MIB

    TmnxAdminState, TmnxOperState, TNamedItem,
    TNamedItemOrEmpty, Dot1PPriority, IpAddressPrefixLength,
    ServiceAccessPoint, TItemDescription, TDSCPNameOrEmpty,
    TDSCPFilterActionValue, TIpProtocol, TIpOption,
    TTcpUdpPort, TTcpUdpPortOperator, TFrameType,
    TmnxServId, TmnxPortID, TmnxEncapVal,
    SdpBindId, SvcISID, QTagFullRange,
    QTagFullRangeOrNone, TMacFilterType, TmnxVRtrIDOrZero,
    TLNamedItemOrEmpty, TRegularExpression, TmnxHttpRedirectUrl,
    IPv6FlowLabel, IPv6FlowLabelMask, TmnxVRtrMplsLspID, TmnxNatSubscriberType,
    TOperator
        FROM TIMETRA-TC-MIB

    InetAddressIPv6,InetAddressPrefixLength, InetAddressType,
    InetAddress
        FROM INET-ADDRESS-MIB
    ;

timetraFilterMIBModule MODULE-IDENTITY
        LAST-UPDATED "201401010000Z"
        ORGANIZATION "Alcatel-Lucent"
        CONTACT-INFO
            "Alcatel-Lucent SROS Support
             Web: http://support.alcatel-lucent.com"
        DESCRIPTION
        "This document is the SNMP MIB module to manage and provision
         Filter features on Alcatel-Lucent SROS systems.

         Copyright 2003-2014 Alcatel-Lucent. All rights reserved.
         Reproduction of this document is authorized on the condition that
         the foregoing copyright notice is included.

         This SNMP MIB module (Specification) embodies Alcatel-Lucent's
         proprietary intellectual property.  Alcatel-Lucent retains
         all title and ownership in the Specification, including any
         revisions.

         Alcatel-Lucent grants all interested parties a non-exclusive
         license to use and distribute an unmodified copy of this
         Specification in connection with management of Alcatel-Lucent
         products, and without fee, provided this copyright notice and
         license appear on all copies.

         This Specification is supplied 'as is', and Alcatel-Lucent
         makes no warranty, either express or implied, as to the use,
         operation, condition, or performance of the Specification."

--
-- Revision History
--
        REVISION        "201401010000Z"
        DESCRIPTION     "Rev 12.0                1 Jan 2014 00:00
                         12.0 release of the TIMETRA-FILTER-MIB."

        REVISION        "201208010000Z"
        DESCRIPTION     "Rev 11.0                1 Aug 2012 00:00
                         11.0 release of the TIMETRA-FILTER-MIB."

        REVISION        "201102010000Z"
        DESCRIPTION     "Rev 9.0                01 Feb 2011 00:00
                         9.0 release of the TIMETRA-FILTER-MIB."

        REVISION        "200907010000Z"
        DESCRIPTION     "Rev 8.0                01 Jul 2009 00:00
                         8.0 release of the TIMETRA-FILTER-MIB."

        REVISION        "200807010000Z"
        DESCRIPTION     "Rev 6.1                01 Jul 2008 00:00
                         6.1 release of the TIMETRA-FILTER-MIB."

        REVISION        "200801010000Z"
        DESCRIPTION     "Rev 6.0                01 Jan 2008 00:00
                         6.0 release of the TIMETRA-FILTER-MIB."

        REVISION        "200701010000Z"
        DESCRIPTION     "Rev 5.0                01 Jan 2007 00:00
                         5.0 release of the TIMETRA-FILTER-MIB."

        REVISION        "200602280000Z"
        DESCRIPTION     "Rev 4.0                28 Feb 2006 00:00
                         4.0 release of the TIMETRA-FILTER-MIB."

        REVISION        "200508310000Z"
        DESCRIPTION     "Rev 3.0                31 Aug 2005 00:00
                         3.0 release of the TIMETRA-FILTER-MIB."

        REVISION        "200501240000Z"
        DESCRIPTION     "Rev 2.1                24 Jan 2005 00:00
                         2.1 release of the TIMETRA-FILTER-MIB."

        REVISION        "200401150000Z"
        DESCRIPTION     "Rev 2.0                15 Jan 2004 00:00
                         2.0 release of the TIMETRA-FILTER-MIB."

        REVISION        "200308150000Z"
        DESCRIPTION     "Rev 1.2                15 Aug 2003 00:00
                         1.2 release of the TIMETRA-FILTER-MIB."

        REVISION        "200301290000Z"
        DESCRIPTION     "Rev 0.1                29 Jan 2003 00:00
                         Initial version of the TIMETRA-FILTER-MIB."

        ::= { timetraSRMIBModules 21 }

tFilterObjects             OBJECT IDENTIFIER ::= { tmnxSRObjs 21 }
tFilterNotificationsPrefix OBJECT IDENTIFIER ::= { tmnxSRNotifyPrefix 21 }
    tFilterNotifications   OBJECT IDENTIFIER ::= { tFilterNotificationsPrefix 0 }
tFilterMIBConformance      OBJECT IDENTIFIER ::= { tmnxSRConfs 21 }

tFilterNotificationObjects OBJECT IDENTIFIER ::= { tFilterObjects 8 }
tFilterTimeStampObjects    OBJECT IDENTIFIER ::= { tFilterObjects 9 }

--
-- TEXTUAL-CONVENTIONs for Alcatel-Lucent SROS series Filter Elements
--

TFilterID ::= TEXTUAL-CONVENTION
    STATUS current
    DESCRIPTION
        "The identification number of a filter. 0 indicates an invalid
         filter-id."
    SYNTAX Unsigned32 (0..65535)

TIPFilterID ::= TEXTUAL-CONVENTION
    STATUS current
    DESCRIPTION
        "The identification number of an IP filter."
    SYNTAX TFilterID

TIPFilterIdOrEmpty ::= TEXTUAL-CONVENTION
    STATUS current
    DESCRIPTION
        "The identification number of an IP filter."
    SYNTAX INTEGER (-1|0..65535)

TMACFilterID ::= TEXTUAL-CONVENTION
    STATUS current
    DESCRIPTION
        "The identification number of a MAC filter."
    SYNTAX TFilterID

TAnyFilterID ::= TEXTUAL-CONVENTION
    STATUS current
    DESCRIPTION
        "Indicates a filter Id. Any value greater than 65535 indicates a
         filter that was created by the system.

         - The range 0x0100xxxx (xxxx: 0000 .. FFFF)
           indicates a filter used for BGP Flow Spec. (the value
           xxxx indicating the vRtrID where the filter is active).
         
          - Filter that are autogenerated by the system for handing
            RADIUS provided filter rules that are to be shared between
            users are encoded as follows:
            - the hightest 3 bits (0b00100000) indicate that it is a composed
              (shared) filter
            - the subsequent 13 bits indicate which 
              RADIUS provided filter list is inserted
              This corresponds to the second mumber in the filter id as
              displayed in CLI - the '1' in the example [100:1]
            - the subsequent 16 bits indicate the base filter.
              This corresponds to the first number (100) in  [100:1]"
    SYNTAX Unsigned32

TFilterScope ::= TEXTUAL-CONVENTION
    STATUS current
    DESCRIPTION
        "This textual-convention determines some aspects of an item's
         behavior regarding creation and use, unused entry garbage collection,
         and automated promulgation by Element Management System to
         other systems in the service domain.

         TFilterScope is an extension of the textual-convention TItemScope.

         exclusive:

            When the scope of an item is defined as exclusive, the item can
            only be applied once, for example to a single SAP.  Attempting
            to assign the policy to a second SAP is not allowed and will
            result in an error.  If the item is removed from the exclusive
            SAP, it will become available for assignment to another
            exclusive SAP.

            A non-applied exclusive scope policy is a candidate to be removed
            from the system by a TBD garbage collection command.

            The system default policies cannot be put into the exclusive scope.
            An error will be generated if scope exclusive is executed in
            any policies with a policy-id equal to 1.

         template:

            When the scope of an item is defined as template, the item can be
            applied any number of times.  Policies with template scope
            will not be considered for deletion by a TBD garbage collection
            command; all items of scope 'template' must be deleted explicitly.

            The system default policies will always be scope template.
            An error will occur if a policy-id 1 is attempted to be
            set to scope exclusive.

         embedded:

            When the scope of a filter is defined as embedded, this indicates
            that the filter may be embedded in other non-embedded filters.
            An embedded filter may not be applied anywhere in the system.
            Attempting to set scope to embedded for a filter which is
            already applied will be rejected by the system."
    SYNTAX INTEGER { exclusive(1), template(2), embedded(3) }

TItemMatch ::= TEXTUAL-CONVENTION
    STATUS current
    DESCRIPTION
        "when set to off, the item is not matched.
         when set to false, packets without the item match the filter.
         when set to true, packets with the item match the filter."
    SYNTAX INTEGER { off(1), false(2), true(3) }

TEntryIndicator ::= TEXTUAL-CONVENTION
    STATUS current
    DESCRIPTION
        "Uniquely identifies an entry in a policy or filter table. The
         value 0 is not a valid entry-id. When used as insertion point
         the value 0 indicates that entries must be inserted at the very
         beginning, i.e.before the first entry defined."
    SYNTAX Unsigned32 (0..65535)

TEntryId ::= TEXTUAL-CONVENTION
    STATUS current
    DESCRIPTION
        "Uniquely identifies an entry in a policy or filter table.
         To facilitate insertion of entries in the tables, we recommend
         assigning entry IDs by 10s:  10, 20, 30, etc."
    SYNTAX TEntryIndicator (1..65535)

TAnyEntryId ::= TEXTUAL-CONVENTION
    STATUS current
    DESCRIPTION
        "Uniquely identifies an entry in a filter table.
        
         The values 1..65535 are available for user configuration.
         The range (65536 .. 131070) is used internally by the system to map
         BGP flow spec generated filter entries."
    SYNTAX Unsigned32 (1..131070)

TEntryIdOrZero ::= TEXTUAL-CONVENTION
    STATUS current
    DESCRIPTION
        "uniquely identifies an entry in a policy or filter table.
         to facilitate insertion of entries in the tables, we recommend
         assigning entry IDs by 10s:  10, 20, 30, etc.
         The value 0, means that the object does not refer to a filter
         entry at this time."
    SYNTAX TEntryIndicator (0..65535)

TFilterAction ::= TEXTUAL-CONVENTION
    STATUS current
    DESCRIPTION
        "Action to take on a packet:
         - drop        (1): packets matching the filter entry are dropped.
         - forward     (2): packets matching the filter entry are forwarded.
         - httpRedirect(4): packets matching the filter entry are redirected.
         - nat         (5): packets matching the filter entry are forwarded to
                            the NAT function in the system.
         - reassemble  (6): packets matching the filter entry are forwarded to
                            the packet reassembly function in the system.
         - gtpLclBrkout(7): packets matching the filter entry are broken out
                            locally from a GTP tunnel (and thereby bypass the
                            mobile packet core). For packets that are not sent
                            in the context of a GTP tunnel, this action is
                            equivalent to 'forward'"
    SYNTAX INTEGER { drop        (1),
                     forward     (2),
                     httpRedirect(4),
                     nat         (5),
                     reassemble  (6),
                     gtpLclBrkout(7)
                   }

TFilterActionOrDefault ::= TEXTUAL-CONVENTION
    STATUS current
    DESCRIPTION
        "Action to take on a packet:
         - drop        (1): packets matching the filter entry are dropped.
         - forward     (2): packets matching the filter entry are forwarded.
         - default     (3): packets matching the filter entry get the applicable
                            default behavior. Note: the value 'default' is
                            currently not supported.
         - httpRedirect(4): packets matching the filter entry are redirected.
         - nat         (5): packets matching the filter entry are forwarded to
                            the NAT function in the system.
         - reassemble  (6): packets matching the filter entry are forwarded to
                            the packet REASSEMBLE function in the system.
         - gtpLclBrkout(7): packets matching the filter entry are broken out
                            locally from a GTP tunnel (and thereby bypass the
                            mobile packet core). For packets that are not sent
                            in the context of a GTP tunnel, this action is
                            equivalent to 'forward'"
    SYNTAX INTEGER { drop        (1),
                     forward     (2),
                     default     (3),
                     httpRedirect(4),
                     nat         (5),
                     reassemble  (6),
                     gtpLclBrkout(7)
                   }

TFilterLogId ::= TEXTUAL-CONVENTION
    STATUS current
    DESCRIPTION
        "Uniquely identifies an entry in the filter log table. 0 indicates an
         invalid log-id."
    SYNTAX Unsigned32 (0 | 101..199)

TFilterLogDestination ::= TEXTUAL-CONVENTION
    STATUS current
    DESCRIPTION
        "Determines the location where filtered packets are logged."
    SYNTAX INTEGER { memory(1),  
                     syslog(2),
                     file(3)
                   }

TTimeRangeState ::= TEXTUAL-CONVENTION
    STATUS current
    DESCRIPTION
        "The textual convention TTimeRangeState is used to indicate the state
         of an object that is controlled by a time range.
         - timeRangeNotApplic:
           no time range is applicable for this entry.
         - timeRangeNotActive:
           A time range is defined but is not active at this moment.
         - timeRangeActive.
           A time range is defined, and is activated successfully.
         - timeRangeActiveDownloadFailed:
           A time range is defined and is activated, but the corresponding
           object could not be installed due to resource problems."
    SYNTAX INTEGER { timeRangeNotApplic(0),
                     timeRangeNotActive(1),
                     timeRangeActive(2),
                     timeRangeActiveDownloadFailed(3) }

TFilterLogSummaryCriterium ::= TEXTUAL-CONVENTION
    STATUS current
    DESCRIPTION
        "Indicates the field on which log summarisation will be done.
         - when set to srcAddr, received log packets are summarized
           based on the src ip/mac-addr
         - when set to dstAddr, received log packets are summarized
           based on the dst ip/mac-addr"
    SYNTAX INTEGER { srcAddr  (0),
                     dstAddr  (1) }

TFilterType ::= TEXTUAL-CONVENTION
    STATUS current
    DESCRIPTION
        "Type of filter."
    SYNTAX INTEGER { fltrtypeselNone   (0),
                     fltrtypeselIp     (1),
                     fltrtypeselMac    (2),
                     fltrtypeselCpm    (3),
                     fltrtypeselIpv6   (4),
                     fltrtypeselCpm6   (5),
                     fltrtypeselCpmMac (6)
                   }

TFilterSubInsSpaceOwner ::= TEXTUAL-CONVENTION
    STATUS current
    DESCRIPTION
        "Application cacapble of inserting filter entries into an
         existing filter"
    SYNTAX INTEGER { none             (0),
                     radius           (1),
                     creditControl    (2),
                     bgpFlowspec      (3),
                     li               (4),
                     embedded         (5),
                     radiusSharedHost (6),
                     openflow         (7)
                   }

TDHCPFilterID ::= TEXTUAL-CONVENTION
    STATUS current
    DESCRIPTION
        "The identification number of a DHCP filter."
    SYNTAX TFilterID

TDhcpFilterAction ::= TEXTUAL-CONVENTION
    STATUS current
    DESCRIPTION
        "Action to take on DHCP host creation when the filter entry matches.

         When set to none(1), host creation proceeds as normal.

         When set to bypass-host-creation(2), host creation is bypassed.

         When set to drop(3), the DHCP message is dropped. "
    SYNTAX INTEGER { none                (1), 
                     bypass-host-creation(2),
                     drop                (3)
                   }

TDhcpFilterMatch ::= TEXTUAL-CONVENTION
    STATUS current
    DESCRIPTION
        "Match condition for a DHCP option in a DHCP filter entry

         When set to present(1) the related DHCP option must be present,
         when set to absent(2) the related DHCP option must be absent.

         When set to string(3) the option must (partially) match a specified
         ASCII string, setting string-exact(4) requires an exact match, setting
         string-invert(5) requires the option not to (partially) match, setting
         string-exact-invert(6) requires the option not to match exact.

         Setting hex(7), hex-exact(8), hex-invert(9) or hex-exact-invert(10)
         will use a hex octet string for the matching."
    SYNTAX INTEGER { present            (1),
                     absent             (2),
                     string             (3),
                     string-exact       (4),
                     string-invert      (5),
                     string-exact-invert(6),
                     hex                (7),
                     hex-exact          (8),
                     hex-invert         (9),
                     hex-exact-invert   (10)
                   }

TFltrPrefixListType ::= TEXTUAL-CONVENTION
    STATUS current
    DESCRIPTION
        "The type TFltrPrefixListType enumerates all possible prefix list
         types."
    SYNTAX INTEGER { ipv4 (1),
                     ipv6 (2)
                   }

TmnxEmbeddedFltrOperState ::= TEXTUAL-CONVENTION
    STATUS current
    DESCRIPTION
        "The TmnxEmbeddedFltrOperState data type is an enumerated integer that
         describes the current operational state of a filter embedding request."
    SYNTAX INTEGER { embedFailedNoResources    (-1),
                     inactive                  (0),
                     active                    (1)
                   }

TmnxFltrEmbeddedEntryState ::= TEXTUAL-CONVENTION
    STATUS current
    DESCRIPTION
        "The TmnxFltrEmbeddedEntryState data type is an enumerated integer that
         describes the current operational state of an embedded filter entry."
    SYNTAX INTEGER { inserted(1),  
                     overruled(2),
                     inactiveAdminDown(3),
                     inactiveNoResources(4)
                   }

                    
TmnxFilterApplyPathSource ::= TEXTUAL-CONVENTION
    STATUS current
    DESCRIPTION
        "The TmnxFilterApplyPathSource data type is an enumerated integer that 
         describes the source of the apply-path imported prefixes"
    SYNTAX INTEGER { unknown   (0),
                     bgp-peers (1)
                   }

TFltrPortSelector ::= TEXTUAL-CONVENTION
    STATUS current
    DESCRIPTION
        "This textual convention specifies how the source-port and
         destination-port filter objects are combined to form the filter match
         criterion.
         - If the selector takes the value and-port(0) then the source-port
           and destination-port objects (if set) are combined into 1 filter
           condition that fires if both conditions are met (i.e. a logical
           and-operation of both is done). If one of them is not set (default
           values) then only the other one is taken into account for the match
           condition.
         - If the selector takes the value or-port(1) then the source-port
           objects are used as match condition for either source-port or
           destination-port (i.e. a logical or-operation is done). In this case,
           non-default values must be set for the source-port objects. In this
           case the destination-port objects are (silently) copied from the
           source-port objects by the system; any other values set by the user
           are overwritten by the system."
    SYNTAX INTEGER { and-port(0),
                     or-port(1)
                   }

TFilterPacketLength ::= TEXTUAL-CONVENTION
    STATUS current
    DESCRIPTION
        "The TFilterPacketLength textual convention is used to specify
         a packet length value."
    SYNTAX Unsigned32 (0..65535)

--
-- mib objects
--

--
-- IP Filter Table
--

tIPFilterTable OBJECT-TYPE
    SYNTAX      SEQUENCE OF TIPFilterEntry
    MAX-ACCESS  not-accessible
    STATUS      current
    DESCRIPTION
        "Contains a List of all ip filters configured on this system."
    ::= { tFilterObjects 1 }

tIPFilterEntry OBJECT-TYPE
    SYNTAX      TIPFilterEntry
    MAX-ACCESS  not-accessible
    STATUS      current
    DESCRIPTION
        "Information about a particular IP Filter entry. Entries are
         created/deleted  by user. Entries have a presumed StorageType of
         nonVolatile."
    INDEX { tIPFilterId }
    ::= { tIPFilterTable 1 }

TIPFilterEntry ::= SEQUENCE
    {
        tIPFilterId                      TAnyFilterID,
        tIPFilterRowStatus               RowStatus,
        tIPFilterScope                   TFilterScope,
        tIPFilterDescription             TItemDescription,
        tIPFilterDefaultAction           TFilterAction,
        tIPFilterRadiusInsertPt          TEntryIdOrZero,
        tIPFilterRadiusInsertSize        TEntryIdOrZero,
        tIPFilterCreditCntrlInsertPt     TEntryIdOrZero,
        tIPFilterCreditCntrlInsertSize   TEntryIdOrZero,
        tIPFilterSubInsertHighWmark      Integer32,
        tIPFilterSubInsertLowWmark       Integer32,
        tIpFilterCreditCntrlNbrInsertd   Unsigned32,
        tIpFilterRadiusNbrInsertd        Unsigned32,
        tIpFilterName                    TLNamedItemOrEmpty,
        tIPFilterHostSharedInsertPt      TEntryIdOrZero,
        tIPFilterHostSharedInsertSize    TEntryIdOrZero,
        tIpFilterHostSharedNbrInsertd    Unsigned32,
        tIPFilterHostSharedHighWmark     Integer32,
        tIPFilterHostSharedLowWmark      Integer32,
        tIPFilterNbrHostSharedFltrs      Unsigned32
    }

tIPFilterId OBJECT-TYPE
    SYNTAX      TAnyFilterID
    MAX-ACCESS  not-accessible
    STATUS      current
    DESCRIPTION
        "Uniquely identifies an ip filter.
         User configured filters can only have values between (1..65535).
         All other values are reserved for system generated filters."
    ::= { tIPFilterEntry 1 }

tIPFilterRowStatus OBJECT-TYPE
    SYNTAX      RowStatus
    MAX-ACCESS  read-create
    STATUS      current
    DESCRIPTION
        "This object allows entries to be created and deleted in the
         tIPFilterTable."
    ::= { tIPFilterEntry 2 }

tIPFilterScope OBJECT-TYPE
    SYNTAX      TFilterScope
    MAX-ACCESS  read-create
    STATUS      current
    DESCRIPTION
        "This object specifies the scope of this filter definition."
    DEFVAL { template }
    ::= { tIPFilterEntry 3 }

tIPFilterDescription OBJECT-TYPE
    SYNTAX      TItemDescription
    MAX-ACCESS  read-create
    STATUS      current
    DESCRIPTION
        "User-provided description for this filter."
    DEFVAL { ''H }
    ::= { tIPFilterEntry 4 }

tIPFilterDefaultAction OBJECT-TYPE
    SYNTAX      TFilterAction
    MAX-ACCESS  read-create
    STATUS      current
    DESCRIPTION
        "The action to take for packets that do not match any filter entries.
         The only allowed values for this field are drop(1) and forward(2)."
    DEFVAL { drop }
    ::= { tIPFilterEntry 5 }

tIPFilterRadiusInsertPt OBJECT-TYPE
    SYNTAX      TEntryIdOrZero
    MAX-ACCESS  read-create
    STATUS      current
    DESCRIPTION
        "The value of tIPFilterRadiusInsertPt specifies at what place the
         host specific filter entries received from Radius will be inserted
         in the filter.

         The area defined here will be dedicated to those entries, no other
         entries will be allowed.

         The value 0 means that no Radius provided host specific filter
         entries can be inserted in the filter.

         If tIPFilterRadiusInsertSize is set to 0, then this object
         will be put to 0 as well. Any change attempts will be
         silently discarded in this case."
    DEFVAL { 0 }
    ::= { tIPFilterEntry 6 }

tIPFilterRadiusInsertSize OBJECT-TYPE
    SYNTAX      TEntryIdOrZero
    MAX-ACCESS  read-create
    STATUS      current
    DESCRIPTION
        "The value of tIPFilterRadiusInsertSize specifies how many
         host specific filter entries received from Radius for subscriber
         hosts can be inserted in the filter.

         If tIPFilterRadiusInsertPt is set to 0, then this object
         will be put to 0 as well. Any change attempts will be
         silently discarded in this case."
    DEFVAL { 0 }
    ::= { tIPFilterEntry 7 }

tIPFilterCreditCntrlInsertPt OBJECT-TYPE
    SYNTAX      TEntryIdOrZero
    MAX-ACCESS  read-create
    STATUS      current
    DESCRIPTION
        "The value of tIPFilterCreditCntrlInsertPt specifies at what place
         the filter entries received from Credit Control for a
         particular subscriber host will be inserted in the filter.

         The area defined here will be dedicated to those entries, no other
         entries will be allowed.

         The value 0 means that no Credit Control provided filter entries
         can be inserted in the filter.

         If tIPFilterCreditCntrlInsertSize is set to 0, then this object
         will be put to 0 as well. Any change attempts will be
         silently discarded in this case."
    DEFVAL { 0 }
    ::= { tIPFilterEntry 8 }

tIPFilterCreditCntrlInsertSize OBJECT-TYPE
    SYNTAX      TEntryIdOrZero
    MAX-ACCESS  read-create
    STATUS      current
    DESCRIPTION
        "The value of tIPFilterCreditCntrlInsertSize specifies how many
         filter entries received from Credit Control can be inserted in the
         filter.

         If tIPFilterCreditCntrlInsertPt is set to 0, then this object
         will be put to 0 as well. Any change attempts will be
         silently discarded in this case."
    DEFVAL { 0 }
    ::= { tIPFilterEntry 9 }

tIPFilterSubInsertHighWmark OBJECT-TYPE
    SYNTAX      Integer32 (0..100)
    MAX-ACCESS  read-create
    STATUS      current
    DESCRIPTION
        "The value of the object tIPFilterSubInsertHighWmark
         specifies the utilization of the filter ranges for filter
         entry insertion, at which a table full alarm will be raised
         by the agent."
    DEFVAL { 95 }
    ::= { tIPFilterEntry 10 }

tIPFilterSubInsertLowWmark OBJECT-TYPE
    SYNTAX      Integer32 (0..100)
    MAX-ACCESS  read-create
    STATUS      current
    DESCRIPTION
        "The value of the object tIPFilterSubInsertLowWmark
         specifies the utilization of the filter ranges for filter
         entry insertion, at which a table full alarm will be cleared
         by the agent."
    DEFVAL { 90 }
    ::= { tIPFilterEntry 11 }

tIpFilterCreditCntrlNbrInsertd OBJECT-TYPE
    SYNTAX      Unsigned32
    MAX-ACCESS  read-only
    STATUS      current
    DESCRIPTION
        "The value of the object tIpFilterCreditCntrlNbrInsertd
         indicates how many filter entries are currently inserted
         in the filter on request of credit control."
    ::= { tIPFilterEntry 12 }

tIpFilterRadiusNbrInsertd OBJECT-TYPE
    SYNTAX      Unsigned32
    MAX-ACCESS  read-only
    STATUS      current
    DESCRIPTION
        "The value of the object tIpFilterRadiusNbrInsertd
         indicates how many host specific filter entries are
         currently inserted in the filter on request of RADIUS."
    ::= { tIPFilterEntry 13 }

tIpFilterName OBJECT-TYPE
    SYNTAX      TLNamedItemOrEmpty
    MAX-ACCESS  read-create
    STATUS      current
    DESCRIPTION
        "The value of tIpFilterName specifies the name to associate
        with this filter."
    DEFVAL { ''H }
    ::= { tIPFilterEntry 14 }

tIPFilterHostSharedInsertPt OBJECT-TYPE
    SYNTAX      TEntryIdOrZero
    MAX-ACCESS  read-create
    STATUS      current
    DESCRIPTION
        "The value of tIPFilterHostSharedInsertPt specifies at what place the
         filter entries received from Radius that are shared between several
         hosts (host common rules) will be inserted in the filter.
    
         The area defined here will be dedicated to those entries, no other
         entries will be allowed.
    
         The value 0 means that no Radius provided host common filter entries
         can be inserted in the filter.
    
         If tIPFilterHostSharedInsertSize is set to 0, then this object
         will be put to 0 as well. Any change attempts will be
         silently discarded in this case."
    DEFVAL { 0 }
    ::= { tIPFilterEntry 15 }

tIPFilterHostSharedInsertSize OBJECT-TYPE
    SYNTAX      TEntryIdOrZero
    MAX-ACCESS  read-create
    STATUS      current
    DESCRIPTION
        "The value of tIPFilterHostSharedInsertSize specifies how many
         host common filter entries received from Radius for subscriber hosts
         can be inserted in the filter.
    
         If tIPFilterHostSharedInsertPt is set to 0, then this object
         will be put to 0 as well. Any change attempts will be
         silently discarded in this case."
    DEFVAL { 0 }
    ::= { tIPFilterEntry 16 }

tIpFilterHostSharedNbrInsertd OBJECT-TYPE
    SYNTAX      Unsigned32
    MAX-ACCESS  read-only
    STATUS      current
    DESCRIPTION
        "The value of the object tIpFilterHostSharedNbrInsertd
         indicates how many Radius Shared Filter rules are
         inserted in the filter."
    ::= { tIPFilterEntry 17 }

tIPFilterHostSharedHighWmark OBJECT-TYPE
    SYNTAX      Integer32 (-1 | 1..8000)
    MAX-ACCESS  read-create
    STATUS      current
    DESCRIPTION
        "The value of the object tIPFilterHostSharedHighWmark
         specifies the number of Radius Shared Filters that can be 
         dynamically created in the system before an high watermark
         notification is generated by the system.
         The value -1 specifies that no notifications are sent.
         If any of the watermarks (high or low) is set to -1, both
         watermarks will be set to -1 by the system."
    DEFVAL { -1 }
    ::= { tIPFilterEntry 18 }

tIPFilterHostSharedLowWmark OBJECT-TYPE
    SYNTAX      Integer32  (-1 | 0..8000)
    MAX-ACCESS  read-create
    STATUS      current
    DESCRIPTION
        "The value of the object tIPFilterHostSharedLowWmark
         specifies the number of Radius Shared Filters that are still
         dynamically created in the system before an high watermark
         notification is cleared by the system.
         The value -1 specifies that no notifications are sent.
         If any of the watermarks (high or low) is set to -1, both
         watermarks will be set to -1 by the system."
    DEFVAL { -1 }
    ::= { tIPFilterEntry 19 }

tIPFilterNbrHostSharedFltrs OBJECT-TYPE
    SYNTAX      Unsigned32
    MAX-ACCESS  read-only
    STATUS      current
    DESCRIPTION
        "The value of the object tIPFilterNbrHostSharedFltrs
         indicates how many Radius Shared Filters are currently
         created based on this filter."
    ::= { tIPFilterEntry 20 }

--
-- IP Filter Entry parameters
--

tIPFilterParamsTable OBJECT-TYPE
    SYNTAX      SEQUENCE OF TIPFilterParamsEntry
    MAX-ACCESS  not-accessible
    STATUS      current
    DESCRIPTION  "A table of all IP filter match entries for all IP filters."
    ::= { tFilterObjects 2 }

tIPFilterParamsEntry OBJECT-TYPE
    SYNTAX      TIPFilterParamsEntry
    MAX-ACCESS  not-accessible
    STATUS      current
    DESCRIPTION
        "Information about a particular IP Filter entry.
        Every IP Filter can have zero or more IP Filter match entries.

        a filter entry with no match criteria set will match every
        packet, and the entry action will be taken.

        Entries are created/deleted by user.

        Additional parameters can be found in tIPFilterParamsExtTable.

        There is no StorageType object, entries have a presumed
        StorageType of nonVolatile.
        "
    INDEX { tIPFilterId, tIPFilterParamsIndex }
    ::= { tIPFilterParamsTable 1 }

TIPFilterParamsEntry ::= SEQUENCE
    {
        tIPFilterParamsIndex               TAnyEntryId,
        tIPFilterParamsRowStatus           RowStatus,
        tIPFilterParamsLogId               TFilterLogId,
        tIPFilterParamsDescription         TItemDescription,
        tIPFilterParamsAction              TFilterActionOrDefault,
        tIPFilterParamsForwardNH           IpAddress,
        tIPFilterParamsForwardNHIndirect   TruthValue,
        tIPFilterParamsRemarkDSCP          TDSCPFilterActionValue,
        tIPFilterParamsRemarkDSCPMask      TDSCPFilterActionValue,
        tIPFilterParamsRemarkDot1p         Dot1PPriority,
        tIPFilterParamsSourceIpAddr        IpAddress,
        tIPFilterParamsSourceIpMask        IpAddressPrefixLength,
        tIPFilterParamsDestinationIpAddr   IpAddress,
        tIPFilterParamsDestinationIpMask   IpAddressPrefixLength,
        tIPFilterParamsProtocol            TIpProtocol,
        tIPFilterParamsSourcePortValue1    TTcpUdpPort,
        tIPFilterParamsSourcePortValue2    TTcpUdpPort,
        tIPFilterParamsSourcePortOperator  TTcpUdpPortOperator,
        tIPFilterParamsDestPortValue1      TTcpUdpPort,
        tIPFilterParamsDestPortValue2      TTcpUdpPort,
        tIPFilterParamsDestPortOperator    TTcpUdpPortOperator,
        tIPFilterParamsDSCP                TDSCPNameOrEmpty,
        tIPFilterParamsFragment            TItemMatch,
        tIPFilterParamsOptionPresent       TItemMatch,
        tIPFilterParamsIpOptionValue       TIpOption,
        tIPFilterParamsIpOptionMask        TIpOption,
        tIPFilterParamsMultipleOption      TItemMatch,
        tIPFilterParamsTcpSyn              TItemMatch,
        tIPFilterParamsTcpAck              TItemMatch,
        tIPFilterParamsIcmpCode            INTEGER,
        tIPFilterParamsIcmpType            INTEGER,
        tIPFilterParamsCflowdSample        TruthValue,
        tIPFilterParamsCflowdIfSample      TruthValue,
        tIPFilterParamsForwardNHInterface  DisplayString,
        tIPFilterParamsIngressHitCount     Counter64,
        tIPFilterParamsEgressHitCount      Counter64,
        tIPFilterParamsLogInstantiated     TruthValue,
        tIPFilterParamsForwardRedPlcy      TNamedItemOrEmpty,
        tIPFilterParamsActiveDest          IpAddress,
        tIPFilterParamsFwdSvcId            TmnxServId,
        tIPFilterParamsFwdSapPortId        TmnxPortID,
        tIPFilterParamsFwdSapEncapVal      TmnxEncapVal,
        tIPFilterParamsFwdSdpBind          SdpBindId,
        tIPFilterParamsTimeRangeName       TNamedItemOrEmpty,
        tIPFilterParamsTimeRangeState      TTimeRangeState,
        tIPFilterParamsRedirectURL         TmnxHttpRedirectUrl,
        tIPFilterParamsSrcIpFullMask       IpAddress,
        tIPFilterParamsDestIpFullMask      IpAddress,
        tIPFilterParamsIngrHitByteCount    Counter64,
        tIPFilterParamsEgrHitByteCount     Counter64,
        tIPFilterParamsFwdRtrId            TmnxVRtrIDOrZero,
        tIPFilterParamsSrcRouteOption      TItemMatch,
        tIPFilterParamsSrcIpPrefixList     TNamedItemOrEmpty,
        tIPFilterParamsDstIpPrefixList     TNamedItemOrEmpty,
        tIPFilterParamsPortSelector        TFltrPortSelector,
        tIPFilterParamsSrcPortList         TNamedItemOrEmpty,
        tIPFilterParamsDstPortList         TNamedItemOrEmpty,
        tIPFilterParamsRdirAllwRadOvrd     TruthValue,
        tIPFilterParamsNatPolicyName       TNamedItemOrEmpty,
        tIPFilterParamsFwdLsp              TmnxVRtrMplsLspID,
        tIPFilterParamsFwdLspRtrId         TmnxVRtrIDOrZero
    }

tIPFilterParamsIndex OBJECT-TYPE
    SYNTAX      TAnyEntryId
    MAX-ACCESS  not-accessible
    STATUS      current
    DESCRIPTION
        "This is the secondary index for the entry. Every ip filter can have
         multiple entries, therefore every ip filter entry is identified by
         the tIPFilterId and tIPFilterParamsIndex.
         
         Refer to the description of the textual convention TAnyEntryId for more
         info on the allowed values for this object."
    ::= { tIPFilterParamsEntry 1 }

tIPFilterParamsRowStatus OBJECT-TYPE
    SYNTAX      RowStatus
    MAX-ACCESS  read-create
    STATUS      current
    DESCRIPTION
        "This object allows entries to be created and deleted in the
         tIPFilterParamsTable."
    ::= { tIPFilterParamsEntry 2 }

tIPFilterParamsLogId OBJECT-TYPE
    SYNTAX      TFilterLogId
    MAX-ACCESS  read-create
    STATUS      current
    DESCRIPTION
        "This object specifies the log to use for packets that match
         this entry. The value zero indicates that logging is disabled."
    DEFVAL { 0 }
    ::= { tIPFilterParamsEntry 3 }

tIPFilterParamsDescription OBJECT-TYPE
    SYNTAX      TItemDescription
    MAX-ACCESS  read-create
    STATUS      current
    DESCRIPTION
        "User-provided description for this filter entry."
    DEFVAL { ''H }
    ::= { tIPFilterParamsEntry 4 }

tIPFilterParamsAction OBJECT-TYPE
    SYNTAX      TFilterActionOrDefault
    MAX-ACCESS  read-create
    STATUS      current
    DESCRIPTION
        "The action to take for packets that match this filter entry. The value
         default(3) specifies this entry to inherit the behavior defined as the
         default for the filter."
    DEFVAL { drop }
    ::= { tIPFilterParamsEntry 5 }

tIPFilterParamsForwardNH OBJECT-TYPE
    SYNTAX      IpAddress
    MAX-ACCESS  read-create
    STATUS      current
    DESCRIPTION
        "The ip-address of the nexthop to which the packet should be forwarded
         if it hits this filter entry. The action of this entry should be
         'forward' in such a case.

         Note that the value of tIPFilterParamsForwardNH is silently cleared
         by the system if tIPFilterParamsAction is set to httpRedirect
         or gtpLclBrkout."
    DEFVAL { '00000000'H }
    ::= { tIPFilterParamsEntry 6 }

tIPFilterParamsForwardNHIndirect OBJECT-TYPE
    SYNTAX      TruthValue
    MAX-ACCESS  read-create
    STATUS      current
    DESCRIPTION
        "tIPFilterParamsForwardNHIndirect specifies if the nexthop is directly/
         indirectly reachable.

         Note that the value of tIPFilterParamsForwardNHIndirect is silently
         cleared by the system if tIPFilterParamsAction is set to httpRedirect
         or gtpLclBrkout."
    DEFVAL { false }
    ::= { tIPFilterParamsEntry 7 }

tIPFilterParamsRemarkDSCP OBJECT-TYPE
    SYNTAX      TDSCPFilterActionValue
    MAX-ACCESS  read-create
    STATUS      current
    DESCRIPTION
        "The DSCP value that should be remarked in case a packet hits this
         filter entry."
    DEFVAL { -1 }
    ::= { tIPFilterParamsEntry 8 }

tIPFilterParamsRemarkDSCPMask OBJECT-TYPE
    SYNTAX      TDSCPFilterActionValue
    MAX-ACCESS  read-create
    STATUS      current
    DESCRIPTION
        "tIPFilterParamsRemarkDSCPMask specifies the care bits while remarking
         with the DSCP value."
    DEFVAL { 255 }
    ::= { tIPFilterParamsEntry 9 }

tIPFilterParamsRemarkDot1p OBJECT-TYPE
    SYNTAX      Dot1PPriority
    MAX-ACCESS  read-create
    STATUS      current
    DESCRIPTION
        "tIPFilterParamsRemarkDot1p specifies the Dot1p value that needs to be
         remarked on the packet if it hits this filter entry."
    DEFVAL { -1 }
    ::= { tIPFilterParamsEntry 10 }

tIPFilterParamsSourceIpAddr OBJECT-TYPE
    SYNTAX      IpAddress
    MAX-ACCESS  read-create
    STATUS      current
    DESCRIPTION
        "IP address to match the source-ip of the packet."
    DEFVAL { '00000000'H }
    ::= { tIPFilterParamsEntry 11 }

tIPFilterParamsSourceIpMask OBJECT-TYPE
    SYNTAX      IpAddressPrefixLength
    MAX-ACCESS  read-create
    STATUS      current
    DESCRIPTION
        "If different from 0, the object tIPFilterParamsSourceIpMask
         specifies the IP Mask value for this policy IP Filter entry.
         The mask is ANDed with the received source IP address to match
         the tIPFilterParamsSourceIpAddr.

         If the value of tIPFilterParamsSourceIpMask is 0, and the
         value of tIPFilterParamsSrcIpFullMask is non zero then the
         value of tIPFilterParamsSrcIpFullMask is used as mask.

         If the value of tIPFilterParamsSourceIpMask is non zero,
         it will be equal to the mask expressed the object
         tIPFilterParamsSrcIpFullMask.

         If both tIPFilterParamsSourceIpMask and
         tIPFilterParamsSrcIpFullMask are set to 0, no matching is done
         on the source Ip address.

         If a value is specified for this object, then the value of the
         object tIPFilterParamsSrcIpFullMask will be set to reflect
         this same mask."
    DEFVAL { 0 }
    ::= { tIPFilterParamsEntry 12 }

tIPFilterParamsDestinationIpAddr OBJECT-TYPE
    SYNTAX      IpAddress
    MAX-ACCESS  read-create
    STATUS      current
    DESCRIPTION
        "IP address to match the destination-ip of the packet."
    DEFVAL { '00000000'H }
    ::= { tIPFilterParamsEntry 13 }

tIPFilterParamsDestinationIpMask OBJECT-TYPE
    SYNTAX      IpAddressPrefixLength
    MAX-ACCESS  read-create
    STATUS      current
    DESCRIPTION
        "If different from 0, the object tIPFilterParamsDestinationIpMask
         specifies the IP Mask value for this policy IP Filter entry.
         The mask is ANDed with the received Destination IP address to match
         the tIPFilterParamsDestinationIpAddr.

         If the value of tIPFilterParamsDestinationIpMask is 0, and the
         value of tIPFilterParamsDestIpFullMask is non zero then the
         value of tIPFilterParamsDestIpFullMask is used as mask.

         If the value of tIPFilterParamsDestinationIpMask is non zero,
         it will be equal to the mask expressed the object
         tIPFilterParamsDestIpFullMask.

         If both tIPFilterParamsDestinationIpMask and
         tIPFilterParamsDestIpFullMask are set to 0, no matching is done
         on the Destination Ip address.

         If a value is specified for this object, then the value of the
         object tIPFilterParamsDestIpFullMask will be set to reflect
         this same mask."
    DEFVAL { 0 }
    ::= { tIPFilterParamsEntry 14 }

tIPFilterParamsProtocol OBJECT-TYPE
    SYNTAX      TIpProtocol
    MAX-ACCESS  read-create
    STATUS      current
    DESCRIPTION
        "IP protocol to match.  set to -1 to disable matching IP protocol. If
         the protocol is changed the protocol specific parameters are reset.
         For instance if protocol is changed from TCP to UDP, then the objects
         tIPFilterParamsTcpSyn and tIPFilterParamsTcpAck will be turned off."
    DEFVAL { -1 }
    ::= { tIPFilterParamsEntry 15 }

tIPFilterParamsSourcePortValue1 OBJECT-TYPE
    SYNTAX      TTcpUdpPort
    MAX-ACCESS  read-create
    STATUS      current
    DESCRIPTION
        "TCP/UDP port value1. The value of this object is used as per the
         description for tIPFilterParamsSourcePortOperator."
    DEFVAL { 0 }
    ::= { tIPFilterParamsEntry 16 }

tIPFilterParamsSourcePortValue2 OBJECT-TYPE
    SYNTAX      TTcpUdpPort
    MAX-ACCESS  read-create
    STATUS      current
    DESCRIPTION
        "TCP/UDP port value2. The value of this object is used as per the
         description for tIPFilterParamsSourcePortOperator."
    DEFVAL { 0 }
    ::= { tIPFilterParamsEntry 17 }

tIPFilterParamsSourcePortOperator OBJECT-TYPE
    SYNTAX      TTcpUdpPortOperator
    MAX-ACCESS  read-create
    STATUS      current
    DESCRIPTION
        "The operator specifies the manner in which
         tIPFilterParamsSourcePortValue1 and tIPFilterParamsSourcePortValue2
         are to be used. The value of these latter 2 objects and
         tIPFilterParamsSourcePortOperator is used as described in
         TTcpUdpPortOperator."
    DEFVAL { none }
    ::= { tIPFilterParamsEntry 18 }

tIPFilterParamsDestPortValue1 OBJECT-TYPE
    SYNTAX      TTcpUdpPort
    MAX-ACCESS  read-create
    STATUS      current
    DESCRIPTION
        "TCP/UDP port value1. The value of this object is used as per the
         description for tIPFilterParamsDestPortOperator."
    DEFVAL { 0 }
    ::= { tIPFilterParamsEntry 19 }

tIPFilterParamsDestPortValue2 OBJECT-TYPE
    SYNTAX      TTcpUdpPort
    MAX-ACCESS  read-create
    STATUS      current
    DESCRIPTION
        "TCP/UDP port value2. 
        
         The value of this object is used as per the
         description for tIPFilterParamsDestPortOperator."
    DEFVAL { 0 }
    ::= { tIPFilterParamsEntry 20 }

tIPFilterParamsDestPortOperator OBJECT-TYPE
    SYNTAX      TTcpUdpPortOperator
    MAX-ACCESS  read-create
    STATUS      current
    DESCRIPTION
        "The operator specifies the manner in which
         tIPFilterParamsDestPortValue1 and tIPFilterParamsDestPortValue2
         are to be used. The value of these latter 2 objects and
         tIPFilterParamsDestPortOperator is used as described in
         TTcpUdpPortOperator."
    DEFVAL { none }
    ::= { tIPFilterParamsEntry 21 }

tIPFilterParamsDSCP OBJECT-TYPE
    SYNTAX      TDSCPNameOrEmpty
    MAX-ACCESS  read-create
    STATUS      current
    DESCRIPTION
        "DSCP to be matched on the packet."
    DEFVAL { ''H }
    ::= { tIPFilterParamsEntry 22 }

tIPFilterParamsFragment OBJECT-TYPE
    SYNTAX      TItemMatch
    MAX-ACCESS  read-create
    STATUS      current
    DESCRIPTION
        "If enabled, this object matches fragmented/unfragmented packets as per
         the value of the object."
    DEFVAL { off }
    ::= { tIPFilterParamsEntry 24 }

tIPFilterParamsOptionPresent OBJECT-TYPE
    SYNTAX      TItemMatch
    MAX-ACCESS  read-create
    STATUS      current
    DESCRIPTION
        "If enabled, this object matches packets if they have options present
         or not as per the value of the object."
    DEFVAL { off }
    ::= { tIPFilterParamsEntry 25 }

tIPFilterParamsIpOptionValue OBJECT-TYPE
    SYNTAX      TIpOption
    MAX-ACCESS  read-create
    STATUS      current
    DESCRIPTION
        "The value of the specific ip-option to match."
    DEFVAL { 0 }
    ::= { tIPFilterParamsEntry 26 }

tIPFilterParamsIpOptionMask OBJECT-TYPE
    SYNTAX      TIpOption
    MAX-ACCESS  read-create
    STATUS      current
    DESCRIPTION
        "Mask is ANDed with the ip-option before being compared to
        tIPFilterParamsIpOptionValue."
    DEFVAL { 0 }
    ::= { tIPFilterParamsEntry 27 }

tIPFilterParamsMultipleOption OBJECT-TYPE
    SYNTAX      TItemMatch
    MAX-ACCESS  read-create
    STATUS      current
    DESCRIPTION
        "If enabled, matches multiple options as per the value of the object."
    DEFVAL { off }
    ::= { tIPFilterParamsEntry 28 }

tIPFilterParamsTcpSyn OBJECT-TYPE
    SYNTAX      TItemMatch
    MAX-ACCESS  read-create
    STATUS      current
    DESCRIPTION
        "If Enabled, matches a TCP Syn as per value of the object."
    DEFVAL { off }
    ::= { tIPFilterParamsEntry 29 }

tIPFilterParamsTcpAck OBJECT-TYPE
    SYNTAX      TItemMatch
    MAX-ACCESS  read-create
    STATUS      current
    DESCRIPTION
        "If Enabled, matches a TCP Ack as per value of the object."
    DEFVAL { off }
    ::= { tIPFilterParamsEntry 30 }

tIPFilterParamsIcmpCode OBJECT-TYPE
    SYNTAX      INTEGER (-1|0..255)
    MAX-ACCESS  read-create
    STATUS      current
    DESCRIPTION
        "Icmp code to be matched. tIPFilterParamsIcmpCode complements the
        object tIPFilterParamsIcmpType. Both of them need to be set to actually
        enable ICMP matching. The value -1 means Icmp code matching is not
        enabled."
    DEFVAL { -1 }
    ::= { tIPFilterParamsEntry 31 }

tIPFilterParamsIcmpType OBJECT-TYPE
    SYNTAX      INTEGER (-1|0..255)
    MAX-ACCESS  read-create
    STATUS      current
    DESCRIPTION
        "Icmp type to be matched. tIPFilterParamsIcmpType complements the
        object tIPFilterParamsIcmpCode. Both of them need to be set to actually
        enable ICMP matching. The value -1 means Icmp type matching is not
        enabled."
    DEFVAL { -1 }
    ::= { tIPFilterParamsEntry 32 }

tIPFilterParamsCflowdSample OBJECT-TYPE
    SYNTAX      TruthValue
    MAX-ACCESS  read-create
    STATUS      current
    DESCRIPTION
        "When tIPFilterParamsCflowdSample has a value of 'true',  Cflowd
         sampling and analysis is performed on those packet streams where this
         filter has been applied.  Only packets matching this IP filter entry
         are subjected to Cflowd sampling and analysis.  A Cflowd profile
         controls the sampling and analysis of data flows through the router."
    DEFVAL { false }
    ::= { tIPFilterParamsEntry 33 }

tIPFilterParamsCflowdIfSample OBJECT-TYPE
    SYNTAX      TruthValue
    MAX-ACCESS  read-create
    STATUS      current
    DESCRIPTION
        "When tIPFilterParamsCflowdIfSample has a value of 'true', Cflowd
         sampling and analysis is performed on those packet streams where this
         filter has been applied.  Only packets matching this IP filter entry
         are subjected to Cflowd sampling and analysis.  A Cflowd profile
         controls the sampling and analysis of data flows through the router."
    DEFVAL { true }
    ::= { tIPFilterParamsEntry 34 }

tIPFilterParamsForwardNHInterface OBJECT-TYPE
    SYNTAX      DisplayString (SIZE(0..32))
    MAX-ACCESS  read-create
    STATUS      current
    DESCRIPTION
        "The interface name for the nexthop to which the packet should be
         forwarded if it hits this filter entry. The action of this entry
         should be 'forward' in such a case.

         Note that the value of tIPFilterParamsForwardNHInterface  is silently
         cleared by the system if tIPFilterParamsAction is set to httpRedirect
         or gtpLclBrkout."
    DEFVAL { ''H }
    ::= { tIPFilterParamsEntry 35 }

tIPFilterParamsIngressHitCount OBJECT-TYPE
    SYNTAX      Counter64
    MAX-ACCESS  read-only
    STATUS      current
    DESCRIPTION
        "This object indicates the number of times an ingress packet
         matched this entry."
    ::= { tIPFilterParamsEntry 36 }

tIPFilterParamsEgressHitCount OBJECT-TYPE
    SYNTAX      Counter64
    MAX-ACCESS  read-only
    STATUS      current
    DESCRIPTION
        "This object indicates the number of times an egress packet
         matched this entry."
    ::= { tIPFilterParamsEntry 37 }

tIPFilterParamsLogInstantiated OBJECT-TYPE
    SYNTAX      TruthValue
    MAX-ACCESS  read-only
    STATUS      current
    DESCRIPTION
        "tIPFilterParamsLogInstantiated indicates if the filter log for
         this filter entry has been instantiated or not."
    ::= { tIPFilterParamsEntry 38 }

tIPFilterParamsForwardRedPlcy OBJECT-TYPE
    SYNTAX      TNamedItemOrEmpty
    MAX-ACCESS  read-create
    STATUS      current
    DESCRIPTION
        "tIPFilterParamsForwardRedPlcy specifies the redirect policy to be
         used to determine the nexthop.

         Note that the value of tIPFilterParamsForwardRedPlcy is silently
         cleared by the system if tIPFilterParamsAction is set to httpRedirect
         or gtpLclBrkout."
    DEFVAL { ''H }
    ::= { tIPFilterParamsEntry 39 }

tIPFilterParamsActiveDest OBJECT-TYPE
    SYNTAX      IpAddress
    MAX-ACCESS  read-only
    STATUS      current
    DESCRIPTION
        "tIPFilterParamsActiveDest indicates the IP address of the active
         destination for this IP filter. A value of 0 indicates that there
         is currently no active destination."
    ::= { tIPFilterParamsEntry 40 }

tIPFilterParamsFwdSvcId OBJECT-TYPE
    SYNTAX      TmnxServId
    MAX-ACCESS  read-only
    STATUS      current
    DESCRIPTION
        "tIPFilterParamsFwdSvcId indicates the service id of the
         destination for this IP filter entry. A value of 0 indicates that
         there is currently no active SAP or SDP destination."
    ::= { tIPFilterParamsEntry 41 }

tIPFilterParamsFwdSapPortId OBJECT-TYPE
    SYNTAX      TmnxPortID
    MAX-ACCESS  read-create
    STATUS      current
    DESCRIPTION
        "tIPFilterParamsFwdSapPortId specifies the sap port identity of the
         destination for this IP filter entry.

         A value of 0 indicates that there is currently no SAP destination
         defined. A value different from 0 can only be specified if the value
         of the tIPFilterParamsAction object of this entry is 'forward'.
         In addition a non-zero value can only be given if the object
         tIPFilterParamsFwdSdpBind has a zero value.

         Note that the value of tIPFilterParamsFwdSapPortId is silently cleared
         by the system if tIPFilterParamsAction is set to httpRedirect
         or gtpLclBrkout."
    DEFVAL { 0 }
    ::= { tIPFilterParamsEntry 42 }

tIPFilterParamsFwdSapEncapVal OBJECT-TYPE
    SYNTAX      TmnxEncapVal
    MAX-ACCESS  read-create
    STATUS      current
    DESCRIPTION
        "tIPFilterParamsFwdSapEncapVal specifies the sap port encap value
         of the destination SAP for this IP filter entry.

         A value different from 0 can only be specified if the value of the
         tIPFilterParamsAction object of this entry is 'forward'.  In addition
         a non-zero value can only be given if the object
         tIPFilterParamsFwdSdpBind has a zero value. A value of 0 indicates
         that either
         1) the sap encapsulation value is not specified when
            tIPFilterParamsFwdSapPortId and tIPFilterParamsFwdSvcId
            have valid values; or
         2) that there is no SAP destination.

         Note that the value of tIPFilterParamsFwdSapEncapVal is silently
         cleared by the system if tIPFilterParamsAction is set to httpRedirect
         or gtpLclBrkout."
    DEFVAL { 0 }
    ::= { tIPFilterParamsEntry 43 }

tIPFilterParamsFwdSdpBind OBJECT-TYPE
    SYNTAX      SdpBindId
    MAX-ACCESS  read-create
    STATUS      current
    DESCRIPTION
        "tIPFilterParamsFwdSdpBind specifies the sdp bind identity of the
         destination for this IP filter entry.

         A value of 0 indicates that there is currently no SDP binding defined.
         A value different from 0 can only be specified if the value of the
         tIPFilterParamsAction object of this entry is 'forward'. In addition
         a non-zero value can only be given if the objects
         tIPFilterParamsFwdSapPortId and tIPFilterParamsFwdSapEncapVal have a
         zero value.

         Note that the value of tIPFilterParamsFwdSdpBind is silently cleared
         by the system if tIPFilterParamsAction is set to httpRedirect
         or gtpLclBrkout."
    DEFVAL { '0'H }
    ::= { tIPFilterParamsEntry 44 }

tIPFilterParamsTimeRangeName OBJECT-TYPE
    SYNTAX      TNamedItemOrEmpty
    MAX-ACCESS  read-create
    STATUS      current
    DESCRIPTION
        "tIPFilterParamsTimeRangeName specifies the tmnxTimeRangeEntry to be
         associated with this filter entry.

         A value for this object can only be specified during row creation, and
         cannot be altered lateron.
         Also, a value is accepted only if the tmnxTimeRangeEntry is defined
         in the TIMETRA-SCHEDULER-MIB::tmnxTimeRangeTable.tTimeRangeName."
    DEFVAL { ''H }
    ::= { tIPFilterParamsEntry 45 }

tIPFilterParamsTimeRangeState OBJECT-TYPE
    SYNTAX      TTimeRangeState
    MAX-ACCESS  read-only
    STATUS      current
    DESCRIPTION
        "tIPFilterParamsTimeRangeState indicates whether or not the entry
         is currently in effect.
         - timeRangeNotApplic:
           no time range is applicable for this entry.
         - timeRangeNotActive:
           A time range is defined in tIPFilterParamsTimeRangeName, but is not
           active at this moment. Consequently the filter entry is not
           installed.
         - timeRangeActive.
           A time range is defined in tIPFilterParamsTimeRangeName, and is
           activated successfully.
         - timeRangeActiveDownloadFailed:
           A time range is defined in tIPFilterParamsTimeRangeName, and is
           activated, but the corresponding filter entry could not be
           installed due to resource problems."
    ::= { tIPFilterParamsEntry 46 }

tIPFilterParamsRedirectURL OBJECT-TYPE
    SYNTAX      TmnxHttpRedirectUrl
    MAX-ACCESS  read-create
    STATUS      current
    DESCRIPTION
        "The value of tIPFilterParamsRedirectURL specifies the URL
         to redirect to, when the value of tIPFilterParamsAction is
         'httpRedirect'.

         The following macro substitions are applicable in this context:
         $URL, $MAC, $IP, $SUB, $SAP, $SAPDESC, $CID, and $RID.

         Note that the value of tIPFilterParamsRedirectURL is silently cleared
         by the system if tIPFilterParamsAction is set to any value other than
         httpRedirect."
    DEFVAL { ''H }
    ::= { tIPFilterParamsEntry 47 }

tIPFilterParamsSrcIpFullMask OBJECT-TYPE
    SYNTAX      IpAddress
    MAX-ACCESS  read-create
    STATUS      current
    DESCRIPTION
        "If different from 0, the object tIPFilterParamsSrcIpFullMask
         specifies the IP Mask value for this policy IP Filter entry.
         The mask is ANDed with the received Source IP address to match
         the tIPFilterParamsSourceIpAddr.

         If the value of tIPFilterParamsSourceIpMask is non zero,
         it will be equal to the mask expressed the object
         tIPFilterParamsSrcIpFullMask.

         If both tIPFilterParamsSourceIpMask and
         tIPFilterParamsSrcIpFullMask are set to 0, no matching is done
         on the Source Ip address.

         This object should contain consecutive ones and zeros. Both
         a regular and an inverse mask is allowed (i.e. the sequence of
         consecutive ones can appear at the front or at the end of the
         mask).

         If a regular mask is specified for tIPFilterParamsSrcIpFullMask
         then the value of tIPFilterParamsSourceIpMask will be changed
         to reflect this value. If an inverse is specified, the value of
         tIPFilterParamsSourceIpMask will be set to 0."
    DEFVAL { 0 }
    ::= { tIPFilterParamsEntry 48 }

tIPFilterParamsDestIpFullMask OBJECT-TYPE
    SYNTAX      IpAddress
    MAX-ACCESS  read-create
    STATUS      current
    DESCRIPTION
        "If different from 0, the object tIPFilterParamsDestIpFullMask
         specifies the IP Mask value for this policy IP Filter entry.
         The mask is ANDed with the received Destination IP address to match
         the tIPFilterParamsDestinationIpAddr.

         If the value of tIPFilterParamsDestinationIpMask is non zero,
         it will be equal to the mask expressed the object
         tIPFilterParamsDestIpFullMask.

         If both tIPFilterParamsDestinationIpMask and
         tIPFilterParamsDestIpFullMask are set to 0, no matching is done
         on the Destination Ip address.

         This object should contain consecutive ones and zeros. Both
         a regular and an inverse mask is allowed (i.e. the sequence of
         consecutive ones can appear at the front or at the end of the
         mask).

         If a regular mask is specified for tIPFilterParamsDestIpFullMask
         then the value of tIPFilterParamsDestinationIpMask will be changed
         to reflect this value. If an inverse is specified, the value of
         tIPFilterParamsDestinationIpMask will be set to 0."
    DEFVAL { 0 }
    ::= { tIPFilterParamsEntry 49 }

tIPFilterParamsIngrHitByteCount OBJECT-TYPE
    SYNTAX      Counter64
    MAX-ACCESS  read-only
    STATUS      current
    DESCRIPTION
        "The value of tIPFilterParamsIngrHitByteCount indicates the number
         of bytes of all ingress packets that matched this entry."
    ::= { tIPFilterParamsEntry 50 }

tIPFilterParamsEgrHitByteCount OBJECT-TYPE
    SYNTAX      Counter64
    MAX-ACCESS  read-only
    STATUS      current
    DESCRIPTION
        "The value of tIPFilterParamsEgrHitByteCount indicates the number
         of bytes of all egress packets that matched this entry."
    ::= { tIPFilterParamsEntry 51 }

tIPFilterParamsFwdRtrId OBJECT-TYPE
    SYNTAX      TmnxVRtrIDOrZero
    MAX-ACCESS  read-create
    STATUS      current
    DESCRIPTION
        "tIPFilterParamsFwdRtrId specifies, if different from '0',
         the router id into which the packet should be forwarded
         if it hits this filter entry.

         The action of this entry should be 'forward' in such a case."
    DEFVAL { 0 }
    ::= { tIPFilterParamsEntry 52 }

tIPFilterParamsSrcRouteOption OBJECT-TYPE
    SYNTAX      TItemMatch
    MAX-ACCESS  read-create
    STATUS      current
    DESCRIPTION
        "tIPFilterParamsSrcRouteOption specifies, when enabled,
         that this filter should match if a (strict or loose) source route
         option is present/not present at any location within the IP header,
         as per the value of this object."
    DEFVAL { off }
    ::= { tIPFilterParamsEntry 53 }

tIPFilterParamsSrcIpPrefixList OBJECT-TYPE
    SYNTAX      TNamedItemOrEmpty
    MAX-ACCESS  read-create
    STATUS      current
    DESCRIPTION
        "The value of this object specifies the ip-prefix-list used as match
         criterion for the source ip address.

         The value specified for this object must correspond to a prefix-list
         defined in tFilterPrefixListTable.

         If the value of this object is empty then the values of the objects
         tIPFilterParamsSourceIpAddr and tIPFilterParamsSourceIpMask are used as
         source ip address match criterion.

         When this object is set to a non-empty value then the objects
         tIPFilterParamsSourceIpAddr and tIPFilterParamsSourceIpMask are reset
         to their default values by the system.

         Vice versa, when a new (non-default) value is provided for the objects
         tIPFilterParamsSourceIpAddr and tIPFilterParamsSourceIpMask then this
         object is reset to its default (empty) value by the system.

         An attempt to set tIPFilterParamsSrcIpPrefixList to a non-default value
         in combination with setting any of tIPFilterParamsSourceIpAddr or
         tIPFilterParamsSourceIpMask to (a) non-default value(s) is rejected by
         the system"
    DEFVAL { ''H }
    ::= { tIPFilterParamsEntry 54 }

tIPFilterParamsDstIpPrefixList OBJECT-TYPE
    SYNTAX      TNamedItemOrEmpty
    MAX-ACCESS  read-create
    STATUS      current
    DESCRIPTION
        "The value of this object specifies the ip-prefix-list used as match
         criterion for the destination ip address.

         The value specified for this object must correspond to a prefix-list
         defined in tFilterPrefixListTable.

         If the value of this object is empty then the values of the objects
         tIPFilterParamsDestinationIpAddr and tIPFilterParamsDestinationIpMask
         are used as destination ip address match criterion.

         When this object is set to a non-empty value then the objects
         tIPFilterParamsDestinationIpAddr and tIPFilterParamsDestinationIpMask
         are reset to their default values by the system.

         Vice versa, when a new (non-default) value is provided for the objects
         tIPFilterParamsDestinationIpAddr and tIPFilterParamsDestinationIpMask
         then this object is reset to its default (empty) value by the system.

         An attempt to set tIPFilterParamsDstIpPrefixList to a non-default value
         in combination with setting any of tIPFilterParamsDestinationIpAddr or
         tIPFilterParamsDestinationIpMask to (a) non-default value(s) is
         rejected by the system"
    DEFVAL { ''H }
    ::= { tIPFilterParamsEntry 55 }

tIPFilterParamsPortSelector OBJECT-TYPE
    SYNTAX      TFltrPortSelector
    MAX-ACCESS  read-create
    STATUS      current
    DESCRIPTION
        "This object specifies how the source-port objects
         (tIPFilterParamsSourcePortValue1, tIPFilterParamsSourcePortValue2,
         tIPFilterParamsSourcePortOperator, tIPFilterParamsSrcPortList) and
         destination-port objects (tIPFilterParamsDestPortValue1,
         tIPFilterParamsDestPortValue2, tIPFilterParamsDestPortOperator,
         tIPFilterParamsDstPortList) are combined to form the filter match
         criterion. See description of TFltrPortSelector."
    DEFVAL { and-port }
    ::= { tIPFilterParamsEntry 56 }

tIPFilterParamsSrcPortList OBJECT-TYPE
    SYNTAX      TNamedItemOrEmpty
    MAX-ACCESS  read-create
    STATUS      current
    DESCRIPTION
        "The value of this object specifies the port-list used as match
         criterion for the source port.

         The value specified for this object must correspond to a port-list
         defined in tFilterPortListTable.

         If the value of this object is empty then the values of the objects
         tIPFilterParamsSourcePortValue1, tIPFilterParamsSourcePortValue2, and
         tIPFilterParamsSourcePortOperator are used as source port match
         criterion.

         When this object is set to a non-empty value then the objects
         tIPFilterParamsSourcePortValue1, tIPFilterParamsSourcePortValue2, and
         tIPFilterParamsSourcePortOperator are reset to their default values by
         the system.

         Vice versa, when a new (non-default) value is provided for one of the
         objects tIPFilterParamsSourcePortValue1,
         tIPFilterParamsSourcePortValue2, or tIPFilterParamsSourcePortOperator
         then tIPFilterParamsSrcPortList is reset to its default (empty) value
         by the system.

         Setting any one of the objects tIPFilterParamsSourcePortValue1,
         tIPFilterParamsSourcePortValue2, or tIPFilterParamsSourcePortOperator
         to a non-default value in combination with a non-default value for the
         object tIPFilterParamsSrcPortList is rejected by the system."
    DEFVAL { ''H }
    ::= { tIPFilterParamsEntry 57 }

tIPFilterParamsDstPortList OBJECT-TYPE
    SYNTAX      TNamedItemOrEmpty
    MAX-ACCESS  read-create
    STATUS      current
    DESCRIPTION
        "The value of this object specifies the port-list used as match
         criterion for the destination port.

         The value specified for this object must correspond to a port-list
         defined in tFilterPortListTable.

         If the value of this object is empty then the values of the objects
         tIPFilterParamsDestPortValue1, tIPFilterParamsDestPortValue2, and
         tIPFilterParamsDestPortOperator are used as destination port match
         criterion.

         When this object is set to a non-empty value then the objects
         tIPFilterParamsDestPortValue1, tIPFilterParamsDestPortValue2, and
         tIPFilterParamsDestPortOperator are reset to their default values by
         the system.

         Vice versa, when a new (non-default) value is provided for one of the
         objects tIPFilterParamsDestPortValue1, tIPFilterParamsDestPortValue2,
         or tIPFilterParamsDestPortOperator then tIPFilterParamsDstPortList is
         reset to its default (empty) value by the system.

         Setting any one of the objects tIPFilterParamsDestPortValue1,
         tIPFilterParamsDestPortValue2, or tIPFilterParamsDestPortOperator
         to a non-default value in combination with a non-default value for the
         object tIPFilterParamsDstPortList is rejected by the system."
    DEFVAL { ''H }
    ::= { tIPFilterParamsEntry 58 }

tIPFilterParamsRdirAllwRadOvrd OBJECT-TYPE
    SYNTAX      TruthValue
    MAX-ACCESS  read-create
    STATUS      current
    DESCRIPTION
        "The value of this object specifies whether or not the value of
         tIPFilterParamsRedirectURL can be over-ridden by a Radius VSA. The
         default value is false (i.e. the URL cannot be over-ridden by Radius).
         The value of tIPFilterParamsRdirAllwRadOvrd is relevant only if the
         value of tIPFilterParamsAction is httpRedirect.

         Setting the value of tIPFilterParamsRdirAllwRadOvrd to true is
         ignored by the system if the value of tIPFilterParamsAction is not
         httpRedirect. Furthermore, the value of
         tIPFilterParamsRdirAllwRadOvrd is silently reset to false by the
         system if tIPFilterParamsAction is set to any value other than
         httpRedirect."
    DEFVAL { false }
    ::= { tIPFilterParamsEntry 59 }

tIPFilterParamsNatPolicyName OBJECT-TYPE
    SYNTAX      TNamedItemOrEmpty
    MAX-ACCESS  read-create
    STATUS      current
    DESCRIPTION
        "The value of this object specifies the name of the NAT policy to be
         used when the value of tIPFilterParamsAction is nat. If the value is
         empty then a default policy is used. If the value is non-empty then it
         must correspond to a policy defined in tmnxNatPlcyTable.

         The value of tIPFilterParamsNatPolicyName is relevant only if the value
         of tIPFilterParamsAction is nat. Setting the value of
         tIPFilterParamsNatPolicyName to a non-empty string is ignored by the
         system if the value of tIPFilterParamsAction is not nat.

         Furthermore, the value of tIPFilterParamsNatPolicyName is silently
         reset to an empty string by the system if tIPFilterParamsAction is set
         to any value other than nat."
    DEFVAL { "" }
    ::= { tIPFilterParamsEntry 60 }

tIPFilterParamsFwdLsp OBJECT-TYPE
    SYNTAX      TmnxVRtrMplsLspID
    MAX-ACCESS  read-create
    STATUS      current
    DESCRIPTION
         "If different from zero the value of the object tIPFilterParamsFwdLsp
          together with the value of the object tIPFilterParamsFwdLspRtrId
          specifies the LSP into which a packet should be forwarded if it hits
          this filter entry.

          The value of the object tIPFilterParamsAction of this entry
          must be 'forward' in such case. Otherwise the value of the object
          tIPFilterParamsFwdLsp is ignored by the system.

          The value is reset to '0' if the value of the object
          tIPFilterParamsAction is set to any value other than forward.

          The value of the object tIPFilterParamsFwdLsp cannot be set to a
          non-zero value if other destinations are already specified.

          The value has to be '0' if the value of the object
          tIPFilterParamsFwdLspRtrId is not set (i.e. is '0').

          If a non-zero value is set, the value of the object
          tIPFilterParamsFwdLspRtrId has to be set as well."
    DEFVAL { 0 }
    ::= { tIPFilterParamsEntry 61 }

tIPFilterParamsFwdLspRtrId OBJECT-TYPE
    SYNTAX      TmnxVRtrIDOrZero
    MAX-ACCESS  read-create
    STATUS      current
    DESCRIPTION
         "The value of the object tIPFilterParamsFwdLspRtrId specifies
          the router ID that the LSP ID defined by the value of the object
          tIPFilterParamsFwdLsp belongs to.

          The value of the object tIPFilterParamsAction of this entry
          must be 'forward' in such case. Otherwise the value of the object
          tIPFilterParamsFwdLspRtrId is ignored by the system.

          The value is reset to '0' if the value of the object
          tIPFilterParamsAction is set to any value other than forward.

          The value of this object cannot be set to a non-zero value if
          other destinations are already specified.

          The value has to be '0' if the value of the object
          tIPFilterParamsFwdLsp is not set (i.e. is '0').

          If a non-zero value is set, the value of the object
          tIPFilterParamsFwdLsp has to be set as well.

          The ID of the base router or '0' are the only allowed value with this
          version of the product."
    DEFVAL { 0 }
    ::= { tIPFilterParamsEntry 62 }

--
-- MAC filter table
--

tMacFilterTable OBJECT-TYPE
    SYNTAX      SEQUENCE OF TMacFilterEntry
    MAX-ACCESS  not-accessible
    STATUS      current
    DESCRIPTION
        "Contains a List of all mac filters configured on this system."
    ::= { tFilterObjects 3 }

tMacFilterEntry OBJECT-TYPE
    SYNTAX      TMacFilterEntry
    MAX-ACCESS  not-accessible
    STATUS      current
    DESCRIPTION
        "Information about a particular MAC Filter. Entries are created/deleted
         by user. Entries have a presumed StorageType of nonVolatile."
    INDEX { tMacFilterId }
    ::= { tMacFilterTable 1 }

TMacFilterEntry ::= SEQUENCE
    {
        tMacFilterId            TMACFilterID,
        tMacFilterRowStatus     RowStatus,
        tMacFilterScope         TFilterScope,
        tMacFilterDescription   TItemDescription,
        tMacFilterDefaultAction TFilterAction,
        tMacFilterType          TMacFilterType,
        tMacFilterName          TLNamedItemOrEmpty
    }

tMacFilterId OBJECT-TYPE
    SYNTAX      TMACFilterID (1..65535)
    MAX-ACCESS  not-accessible
    STATUS      current
    DESCRIPTION
        "Uniquely identifies a mac filter as configures on this system."
    ::= { tMacFilterEntry 1 }

tMacFilterRowStatus OBJECT-TYPE
    SYNTAX      RowStatus
    MAX-ACCESS  read-create
    STATUS      current
    DESCRIPTION
        "This object allows entries to be created and deleted in the
         tMacFilterTable."
    ::= { tMacFilterEntry 2 }

tMacFilterScope OBJECT-TYPE
    SYNTAX      TFilterScope
    MAX-ACCESS  read-create
    STATUS      current
    DESCRIPTION
        "This object specifies the scope of this filter definition."
    DEFVAL { template }
    ::= { tMacFilterEntry 3 }

tMacFilterDescription OBJECT-TYPE
    SYNTAX      TItemDescription
    MAX-ACCESS  read-create
    STATUS      current
    DESCRIPTION
        "User-provided description for this filter."
    DEFVAL { ''H }
    ::= { tMacFilterEntry 4 }

tMacFilterDefaultAction OBJECT-TYPE
    SYNTAX      TFilterAction
    MAX-ACCESS  read-create
    STATUS      current
    DESCRIPTION
        "The action to take for packets that do not match any filter entries.
         The only allowed values for this field are drop(1) and forward(2)."
    DEFVAL { drop }
    ::= { tMacFilterEntry 5 }

tMacFilterType OBJECT-TYPE
    SYNTAX      TMacFilterType
    MAX-ACCESS  read-create
    STATUS      current
    DESCRIPTION
        "tMacFilterType specifies which type of entries this mac filter
         can contain.

         If tMacFilterType is set to 'normal(1)', all match criteria
         are accepted except the criteria mentioned below that belong to type
         isid(2) and vid(3).

         if tMacFilterType is set to 'isid(2)' the only accepted match
         criteria for the filter entries are:
         - tMacFilterParamsLowISID
         - tMacFilterParamsHighISID

         If tMacFilterType is set to vid(3) the only accepted match
         criteria for the filter entries are:
         - tMacFilterParamsInnerTagValue
         - tMacFilterParamsInnerTagMask
         - tMacFilterParamsOuterTagValue
         - tMacFilterParamsOuterTagMask

         tMacFilterType can only be changed if the filter is not applied
         and has no entries."
    DEFVAL { normal }
    ::= { tMacFilterEntry 6 }

tMacFilterName OBJECT-TYPE
    SYNTAX      TLNamedItemOrEmpty
    MAX-ACCESS  read-create
    STATUS      current
    DESCRIPTION
        "The value of tMacFilterName specifies the name to associate
        with this filter."
    DEFVAL { ''H }
    ::= { tMacFilterEntry 7 }

--
-- MAC Filter Entry parameters
--

tMacFilterParamsTable OBJECT-TYPE
    SYNTAX      SEQUENCE OF TMacFilterParamsEntry
    MAX-ACCESS  not-accessible
    STATUS      current
    DESCRIPTION  "A table of all MAC filter match entries for all MAC filters."
    ::= { tFilterObjects 4 }

tMacFilterParamsEntry OBJECT-TYPE
    SYNTAX      TMacFilterParamsEntry
    MAX-ACCESS  not-accessible
    STATUS      current
    DESCRIPTION
        "Information about a particular MAC Filter entry.
         Every MAC Filter can have zero or more MAC Filter match entries.

         A filter entry with no match criteria set will match every
         packet, and the entry action will be taken.

         Entries are created/deleted by user.

         There is no StorageType object, entries have a presumed
         StorageType of nonVolatile."
    INDEX { tMacFilterId, tMacFilterParamsIndex }
    ::= { tMacFilterParamsTable 1 }

TMacFilterParamsEntry ::= SEQUENCE
    {
        tMacFilterParamsIndex            TEntryId,
        tMacFilterParamsRowStatus        RowStatus,
        tMacFilterParamsLogId            TFilterLogId,
        tMacFilterParamsDescription      TItemDescription,
        tMacFilterParamsAction           TFilterActionOrDefault,
        tMacFilterParamsFrameType        TFrameType,
        tMacFilterParamsSrcMAC           MacAddress,
        tMacFilterParamsSrcMACMask       MacAddress,
        tMacFilterParamsDstMAC           MacAddress,
        tMacFilterParamsDstMACMask       MacAddress,
        tMacFilterParamsDot1pValue       Dot1PPriority,
        tMacFilterParamsDot1pMask        Dot1PPriority,
        tMacFilterParamsEtherType        INTEGER,
        tMacFilterParamsDsap             ServiceAccessPoint,
        tMacFilterParamsDsapMask         ServiceAccessPoint,
        tMacFilterParamsSsap             ServiceAccessPoint,
        tMacFilterParamsSsapMask         ServiceAccessPoint,
        tMacFilterParamsSnapPid          INTEGER,
        tMacFilterParamsSnapOui          INTEGER,
        tMacFilterParamsIngressHitCount  Counter64,
        tMacFilterParamsEgressHitCount   Counter64,
        tMacFilterParamsLogInstantiated  TruthValue,
        tMacFilterParamsFwdSvcId         TmnxServId,
        tMacFilterParamsFwdSapPortId     TmnxPortID,
        tMacFilterParamsFwdSapEncapVal   TmnxEncapVal,
        tMacFilterParamsFwdSdpBind       SdpBindId,
        tMacFilterParamsTimeRangeName    TNamedItemOrEmpty,
        tMacFilterParamsTimeRangeState   TTimeRangeState,
        tMacFilterParamsRedirectURL      TmnxHttpRedirectUrl,
        tMacFilterParamsIngrHitByteCount Counter64,
        tMacFilterParamsEgrHitByteCount  Counter64,
        tMacFilterParamsLowISID          SvcISID,
        tMacFilterParamsHighISID         SvcISID,
        tMacFilterParamsInnerTagValue    QTagFullRangeOrNone,
        tMacFilterParamsInnerTagMask     QTagFullRange,
        tMacFilterParamsOuterTagValue    QTagFullRangeOrNone,
        tMacFilterParamsOuterTagMask     QTagFullRange
    }
tMacFilterParamsIndex OBJECT-TYPE
    SYNTAX      TEntryId
    MAX-ACCESS  not-accessible
    STATUS      current
    DESCRIPTION
        "This is the secondary index for the entry. Every mac filter can have
         multiple entries, therefore every mac filter entry is identified by
         the tMacFilterId and tMacFilterParamsIndex."
    ::= { tMacFilterParamsEntry 1 }

tMacFilterParamsRowStatus OBJECT-TYPE
    SYNTAX      RowStatus
    MAX-ACCESS  read-create
    STATUS      current
    DESCRIPTION
        "This object allows entries to be created and deleted in the
         tMacFilterParamsTable."
    ::= { tMacFilterParamsEntry 2 }

tMacFilterParamsLogId OBJECT-TYPE
    SYNTAX      TFilterLogId
    MAX-ACCESS  read-create
    STATUS      current
    DESCRIPTION
        "This object specifies the log to use for packets that match
         this entry. The value zero indicates that logging is disabled."
    DEFVAL { 0 }
    ::= { tMacFilterParamsEntry 3 }

tMacFilterParamsDescription OBJECT-TYPE
    SYNTAX      TItemDescription
    MAX-ACCESS  read-create
    STATUS      current
    DESCRIPTION
        "User-provided description for this filter entry."
    DEFVAL { ''H }
    ::= { tMacFilterParamsEntry 4 }

tMacFilterParamsAction OBJECT-TYPE
    SYNTAX      TFilterActionOrDefault
    MAX-ACCESS  read-create
    STATUS      current
    DESCRIPTION
        "The action to take for packets that match this filter entry. The value
         default(3) specifies this entry to inherit the behavior defined as the
         default for the filter.
         The values nat(5), reassemble(6), and gtpLclBrkout(7) are not allowed."
    DEFVAL { drop }
    ::= { tMacFilterParamsEntry 5 }

tMacFilterParamsFrameType OBJECT-TYPE
    SYNTAX      TFrameType
    MAX-ACCESS  read-create
    STATUS      current
    DESCRIPTION
        "The type of mac frame for which we are defining this match criteria.

         For filter entries in a Mac filter of type tMacFilterType = dot1q or
         tMacFilterType qinq the default value for this object is set to
         ethernetII (3), and no changes are allowed. In all other cases the
         default value is set to e802dot3 (0) "
    DEFVAL { e802dot3 }
    ::= { tMacFilterParamsEntry 6 }

tMacFilterParamsSrcMAC OBJECT-TYPE
    SYNTAX      MacAddress
    MAX-ACCESS  read-create
    STATUS      current
    DESCRIPTION
        "Source MAC to match for this policy MAC filter entry."
    DEFVAL { '000000000000'H }
    ::= { tMacFilterParamsEntry 8 }

tMacFilterParamsSrcMACMask OBJECT-TYPE
    SYNTAX      MacAddress
    MAX-ACCESS  read-create
    STATUS      current
    DESCRIPTION
        "Source MAC mask value for this policy MAC filter entry.
         The mask is ANDed with the MAC to match tMacFilterParamsSrcMAC.
         A zero bit means ignore this bit, do not match.  a one bit means
         match this bit with tMacFilterParamsSrcMAC.
         Use the value 00-00-00-00-00-00 to disable this filter criteria."
    DEFVAL { '000000000000'H }
    ::= { tMacFilterParamsEntry 9 }

tMacFilterParamsDstMAC OBJECT-TYPE
    SYNTAX      MacAddress
    MAX-ACCESS  read-create
    STATUS      current
    DESCRIPTION
        "Destination MAC mask value for this policy MAC filter entry."
    DEFVAL { '000000000000'H }
    ::= { tMacFilterParamsEntry 10 }

tMacFilterParamsDstMACMask OBJECT-TYPE
    SYNTAX      MacAddress
    MAX-ACCESS  read-create
    STATUS      current
    DESCRIPTION
        "Destination MAC mask value for this policy MAC filter entry.
         The mask is ANDed with the MAC to match tMacFilterParamsDstMAC.
         A zero bit means ignore this bit, do not match.  a one bit means
         match this bit with tMacFilterParamsDstMAC.
         Use the value 00-00-00-00-00-00 to disable this filter criteria."
    DEFVAL { '000000000000'H }
    ::= { tMacFilterParamsEntry 11 }

tMacFilterParamsDot1pValue OBJECT-TYPE
    SYNTAX      Dot1PPriority
    MAX-ACCESS  read-create
    STATUS      current
    DESCRIPTION
         "IEEE 802.1p priority value for this policy MAC filter entry.
      Use -1 to disable matching this filter criteria."
    DEFVAL { -1 }
    ::= { tMacFilterParamsEntry 12 }

tMacFilterParamsDot1pMask OBJECT-TYPE
    SYNTAX      Dot1PPriority (0..7)
    MAX-ACCESS  read-create
    STATUS      current
    DESCRIPTION
         "IEEE 802.1p priority mask value for this policy MAC filter entry.
          Use zero to disable matching, use 7 to match everything."
    DEFVAL { 0 }
    ::= { tMacFilterParamsEntry 13 }

tMacFilterParamsEtherType OBJECT-TYPE
    SYNTAX      INTEGER (-1 | 0..65535)
    MAX-ACCESS  read-create
    STATUS      current
    DESCRIPTION
        "Ethertype for this policy MAC filter entry. Use -1 to disable matching
         by this criteria. This object has no significance if the object
         tMacFilterParamsFrameType is not set to Ethernet_II."
    DEFVAL { -1 }
    ::= { tMacFilterParamsEntry 14 }

tMacFilterParamsDsap OBJECT-TYPE
    SYNTAX      ServiceAccessPoint
    MAX-ACCESS  read-create
    STATUS      current
    DESCRIPTION
        "MAC DSAP to match for this policy MAC filter entry. This object has no
         significance if the object tMacFilterParamsFrameType is not set to
         802dot2LLC.
         In order to reset the value to the default value, both objects
         tMacFilterParamsDsap and tMacFilterParamsDsapMask need to be modified
         together to the default value."
    DEFVAL { -1 }
    ::= { tMacFilterParamsEntry 15 }

tMacFilterParamsDsapMask OBJECT-TYPE
    SYNTAX      ServiceAccessPoint
    MAX-ACCESS  read-create
    STATUS      current
    DESCRIPTION
        "MAC DSAP mask for this policy MAC filter entry. use 0 to disable
         matching by this criteria. This object has no significance if the
         object tMacFilterParamsFrameType is not set to 802dot2LLC.
         In order to reset the value to the default value, both objects
         tMacFilterParamsDsap and tMacFilterParamsDsapMask need to be modified
         together to the default value."
    DEFVAL { -1 }
    ::= { tMacFilterParamsEntry 16 }

tMacFilterParamsSsap OBJECT-TYPE
    SYNTAX      ServiceAccessPoint
    MAX-ACCESS  read-create
    STATUS      current
    DESCRIPTION
        "MAC SSAP to match for this policy MAC filter entry. This object has no
         significance if the object tMacFilterParamsFrameType is not set to
         802dot2LLC.
         In order to reset the value to the default value, both objects
         tMacFilterParamsSsap and tMacFilterParamsSsapMask need to be modified
         together to the default value."
    DEFVAL { -1 }
    ::= { tMacFilterParamsEntry 17 }

tMacFilterParamsSsapMask OBJECT-TYPE
    SYNTAX      ServiceAccessPoint
    MAX-ACCESS  read-create
    STATUS      current
    DESCRIPTION
        "MAC SSAP mask for this policy MAC filter entry. use 0 to disable
         matching by this criteria. This object has no significance if the
         object tMacFilterParamsFrameType is not set to 802dot2LLC.
         In order to reset the value to the default value, both objects
         tMacFilterParamsSsap and tMacFilterParamsSsapMask need to be modified
         together to the default value."
    DEFVAL { -1 }
    ::= { tMacFilterParamsEntry 18 }

tMacFilterParamsSnapPid OBJECT-TYPE
    SYNTAX      INTEGER (-1 | 0..65535)
    MAX-ACCESS  read-create
    STATUS      current
    DESCRIPTION
         "MAC SNAP PID to match for this policy MAC filter entry.  use -1 to
          disable matching by this criteria. This object has no significance if
          object tMacFilterParamsFrameType is not set to 802dot2SNAP."
    DEFVAL { -1 }
    ::= { tMacFilterParamsEntry 19 }

tMacFilterParamsSnapOui OBJECT-TYPE
    SYNTAX      INTEGER { off(1), zero(2), nonZero(3) }
    MAX-ACCESS  read-create
    STATUS      current
    DESCRIPTION
        "MAC SNAP OUI to match. The values zero(2) and nonZero(3) specify what
         to match. Matching can be disabled by the use of the value off(1).
         This object has no significance if the object
         tMacFilterParamsFrameType is not set to 802dot2SNAP."
    DEFVAL { off }
    ::= { tMacFilterParamsEntry 20 }

tMacFilterParamsIngressHitCount OBJECT-TYPE
    SYNTAX      Counter64
    MAX-ACCESS  read-only
    STATUS      current
    DESCRIPTION
        "This object indicates the number of times an ingress packet
         matched this entry."
    ::= { tMacFilterParamsEntry 21 }

tMacFilterParamsEgressHitCount OBJECT-TYPE
    SYNTAX      Counter64
    MAX-ACCESS  read-only
    STATUS      current
    DESCRIPTION
        "This object indicates the number of times an egress packet
         matched this entry."
    ::= { tMacFilterParamsEntry 22 }

tMacFilterParamsLogInstantiated OBJECT-TYPE
    SYNTAX      TruthValue
    MAX-ACCESS  read-only
    STATUS      current
    DESCRIPTION
        "tMacFilterParamsLogInstantiated indicates if the filter log for
         this filter entry has been instantiated or not."
    ::= { tMacFilterParamsEntry 23 }

tMacFilterParamsFwdSvcId OBJECT-TYPE
    SYNTAX      TmnxServId
    MAX-ACCESS  read-only
    STATUS      current
    DESCRIPTION
        "tMacFilterParamsFwdSvcId indicates the service id of the
         destination for this Mac filter entry. A value of 0 indicates that
         there is currently no active SAP or SDP destination."
    ::= { tMacFilterParamsEntry 24 }

tMacFilterParamsFwdSapPortId OBJECT-TYPE
    SYNTAX      TmnxPortID
    MAX-ACCESS  read-create
    STATUS      current
    DESCRIPTION
        "tMacFilterParamsFwdSapPortId specifies the sap port identity of the
         destination for this Mac filter entry. A value of 0 indicates that
         there is currently no SAP destination defined.
         A value different from 0 can only be specified if the
         tMacFilterParamsFwdSvcId object also has a non-zero value,
         and if the the value of the tMacFilterParamsAction object of this
         entry is 'forward'. In addition a non-zero value can only be given if
         the object tMacFilterParamsFwdSdpBind has a zero value."
    DEFVAL { 0 }
    ::= { tMacFilterParamsEntry 25 }

tMacFilterParamsFwdSapEncapVal OBJECT-TYPE
    SYNTAX      TmnxEncapVal
    MAX-ACCESS  read-create
    STATUS      current
    DESCRIPTION
        "tMacFilterParamsFwdSapEncapVal specifies the sap port encap value
         of the destination SAP for this Mac filter entry.
         A value different from 0 can only be specified if the
         tMacFilterParamsFwdSvcId object also has a non-zero value,
         the tMacFilterParamsFwdSapPortId object has a non zero value,
         and if the the value of the tMacFilterParamsAction object of this entry
         is 'forward'.
         In addition a non-zero value can only be given if the object
         tMacFilterParamsFwdSdpBind has a zero value.
         A value of 0 indicates that either
         1) the sap encapsulation value is not specified when
            tMacFilterParamsFwdSapPortId and tMacFilterParamsFwdSvcId
            have valid values; or
         2) that there is no SAP destination."
    DEFVAL { 0 }
    ::= { tMacFilterParamsEntry 26 }

tMacFilterParamsFwdSdpBind OBJECT-TYPE
    SYNTAX      SdpBindId
    MAX-ACCESS  read-create
    STATUS      current
    DESCRIPTION
        "tMacFilterParamsFwdSdpBind specifies the sdp bibd identity of the
         destination for this Mac filter entry. A value of 0 indicates that
         there is currently no SDP binding defined.
         A value different from 0 can only be specified if the
         tMacFilterParamsFwdSvcId object also has a non-zero value,
         and if the the value of the tMacFilterParamsAction object of this
         entry is 'forward'. In addition a non-zero value can only be given if
         the objects tMacFilterParamsFwdSapPortId and
         tMacFilterParamsFwdSapEncapVal have a zero value."
    DEFVAL { '0'H }
    ::= { tMacFilterParamsEntry 27 }

tMacFilterParamsTimeRangeName OBJECT-TYPE
    SYNTAX      TNamedItemOrEmpty
    MAX-ACCESS  read-create
    STATUS      current
    DESCRIPTION
        "tMacFilterParamsTimeRangeName specifies the tmnxTimeRangeEntry to be
         associated with this filter entry.

         A value for this object can only be specified during row creation, and
         cannot be altered lateron.
         Also, a value is accepted only if the tmnxTimeRangeEntry is defined in
         the TIMETRA-SCHEDULER-MIB::tmnxTimeRangeTable.tTimeRangeName."
    DEFVAL { ''H }
    ::= { tMacFilterParamsEntry 28 }

tMacFilterParamsTimeRangeState OBJECT-TYPE
    SYNTAX      TTimeRangeState
    MAX-ACCESS  read-only
    STATUS      current
    DESCRIPTION
        "tMacFilterParamsTimeRangeState indicates whether or not the entry
         is currently in effect.
         - timeRangeNotApplic:
           no time range is applicable for this entry.
         - timeRangeNotActive:
           A time range is defined in tMacFilterParamsTimeRangeName, but is not
           active at this moment. Consequently the filter entry is not
           installed.
         - timeRangeActive.
           A time range is defined in tMacFilterParamsTimeRangeName, and is
           activated successfully.
         - timeRangeActiveDownloadFailed:
           A time range is defined in tMacFilterParamsTimeRangeName, and is
           activated, but the corresponding filter entry could not be
           installed due to resource problems."
    ::= { tMacFilterParamsEntry 29 }

tMacFilterParamsRedirectURL OBJECT-TYPE
    SYNTAX      TmnxHttpRedirectUrl
    MAX-ACCESS  read-create
    STATUS      current
    DESCRIPTION
        "The value of tMacFilterParamsRedirectURL specifies the URL
         to redirect to, when the value of tMacFilterParamsAction is
         'httpRedirect'."
    DEFVAL { ''H }
    ::= { tMacFilterParamsEntry 30 }

tMacFilterParamsIngrHitByteCount OBJECT-TYPE
    SYNTAX      Counter64
    MAX-ACCESS  read-only
    STATUS      current
    DESCRIPTION
        "The value of tMacFilterParamsIngrHitByteCount indicates the number
         of bytes of all ingress packets that matched this entry."
    ::= { tMacFilterParamsEntry 31 }

tMacFilterParamsEgrHitByteCount OBJECT-TYPE
    SYNTAX      Counter64
    MAX-ACCESS  read-only
    STATUS      current
    DESCRIPTION
        "The value of tMacFilterParamsEgrHitByteCount indicates the number
         of bytes of all egress packets that matched this entry."
    ::= { tMacFilterParamsEntry 32 }

tMacFilterParamsLowISID OBJECT-TYPE
    SYNTAX      SvcISID
    MAX-ACCESS  read-create
    STATUS      current
    DESCRIPTION
        "The value of tMacFilterParamsLowISID specifies the lowest value of the
         24 bit (0..16777215) service instance identifier for this service that
         matches this entry.

         The default value of -1 indicates no ISID matching will be performed.

         The value of this field can be equal to but not lower than the value
         of the tMacFilterParamsHighISID field.

         Changing the value of this field might also change the value of
         tMacFilterParamsHighISID:
         A value of -1 will change the value of tMacFilterParamsHighISID to -1.
         Changing the value of this field from -1 to any other value will change
         the value of tMacFilterParamsHighISID to this same value.

         Note that tMacFilterParamsLowISID and tMacFilterParamsHighISID can only
         be set if tMacFilterType is set to 'isid(1)'."
    DEFVAL { -1 }
    ::= { tMacFilterParamsEntry 33 }

tMacFilterParamsHighISID OBJECT-TYPE
    SYNTAX      SvcISID
    MAX-ACCESS  read-create
    STATUS      current
    DESCRIPTION
        "The value of tMacFilterParamsHighISID specifies the highest value of
         the 24 bit (0..16777215) service instance identifier for this service
         that matches this entry.

         The default value of -1 indicates no ISID matching will be performed.

         The value of this field can be equal to but not higher than the value
         of the tMacFilterParamsLowISID field.

         Changing the value of this field might also change the value of
         tMacFilterParamsLowISID:
         A value of -1 will change the value of tMacFilterParamsLowISID to -1.
         Changing the value of this field from -1 to any other value will change
         the value of tMacFilterParamsLowISID to this same value.

         Note that tMacFilterParamsLowISID and tMacFilterParamsHighISID can only
         be set if tMacFilterType is set to 'isid(1)'."
    DEFVAL { -1 }
    ::= { tMacFilterParamsEntry 34 }

tMacFilterParamsInnerTagValue OBJECT-TYPE
    SYNTAX      QTagFullRangeOrNone
    MAX-ACCESS  read-create
    STATUS      current
    DESCRIPTION
        "The value of tMacFilterParamsInnerTagValue specifies the value to match
         against the VID of the second VLAN tag in the packet that
         is carried transparently through the service (the second vlan tag after
         the service delimiting tags).

         This object can only be set if tMacFilterType is set to 'vid(3)'.

         The (default) value of '-1' indicates no inner VLAN tag matching will
         be performed."
    DEFVAL { -1 }
    ::= { tMacFilterParamsEntry 35 }

tMacFilterParamsInnerTagMask OBJECT-TYPE
    SYNTAX      QTagFullRange (1..4095)
    MAX-ACCESS  read-create
    STATUS      current
    DESCRIPTION
        "The value of tMacFilterParamsInnerTagMask is applied as a mask to VID
         of the inner VLAN tag of the packet prior to comparing it
         with tMacFilterParamsInnerTagValue.  The inner tag is the second tag in
         the packet that is carried transparently through the service
         (the second tag after the service delimiting tags).

         This object can only be set if tMacFilterType is set to 'vid(3)'."
    DEFVAL { 4095 } -- 0xFFF : all ones mask.
    ::= { tMacFilterParamsEntry 36 }

tMacFilterParamsOuterTagValue OBJECT-TYPE
    SYNTAX      QTagFullRangeOrNone
    MAX-ACCESS  read-create
    STATUS      current
    DESCRIPTION
        "The value of tMacFilterParamsOuterTagValue specifies the value to match
         against the VID of the first VLAN tag in the packet that
         is carried transparently through the service (the first vlan tag after
         the service delimiting tags).

         This object can only be set if tMacFilterType is set to 'vid(3)'.

         The (default) value of '-1' indicates no outer VLAN tag matching will
         be performed."
    DEFVAL { -1 }
    ::= { tMacFilterParamsEntry 37 }

tMacFilterParamsOuterTagMask OBJECT-TYPE
    SYNTAX      QTagFullRange (1..4095)
    MAX-ACCESS  read-create
    STATUS      current
    DESCRIPTION
        "The value of tMacFilterParamsOuterTagMask is applied as a mask to VID
         of the outer VLAN tag of the packet prior to comparing it
         with tMacFilterParamsOuterTagValue.  The outer tag is the first tag in
         the packet that is carried transparently through the service
         (the first tag after the service delimiting tags).

         This object can only be set if tMacFilterType is set to 'vid(3)'."
    DEFVAL { 4095 } -- 0xFFF : all ones mask.
    ::= { tMacFilterParamsEntry 38 }

--
-- Filter Log table
--

tFilterLogTable OBJECT-TYPE
    SYNTAX      SEQUENCE OF TFilterLogEntry
    MAX-ACCESS  not-accessible
    STATUS      current
    DESCRIPTION  "A table of all filter logs."
    ::= { tFilterObjects 5 }

tFilterLogEntry OBJECT-TYPE
    SYNTAX      TFilterLogEntry
    MAX-ACCESS  not-accessible
    STATUS      current
    DESCRIPTION
        "Information about a particular Filter Log entry."
    INDEX { tFilterLogId }
    ::= { tFilterLogTable 1 }

TFilterLogEntry ::= SEQUENCE
    {
        tFilterLogId              TFilterLogId,
        tFilterLogRowStatus       RowStatus,
        tFilterLogDestination     TFilterLogDestination,
        tFilterLogDescription     TItemDescription,
        tFilterLogMaxNumEntries   Unsigned32,
        tFilterLogSysLogId        Unsigned32,
        tFilterLogFileId          Unsigned32,
        tFilterLogStopOnFull      TruthValue,
        tFilterLogEnabled         TruthValue,
        tFilterLogSummaryEnabled  TruthValue,
        tFilterLogSummaryCrit1    TFilterLogSummaryCriterium
    }

tFilterLogId OBJECT-TYPE
    SYNTAX      TFilterLogId
    MAX-ACCESS  not-accessible
    STATUS      current
    DESCRIPTION
        "This is the index for the entry. An entry cannot be created with an
        id of 0."
    ::= { tFilterLogEntry 1 }

tFilterLogRowStatus OBJECT-TYPE
    SYNTAX      RowStatus
    MAX-ACCESS  read-create
    STATUS      current
    DESCRIPTION
        "This object allows entries to be created and deleted in the
         tFilterLogTable."
    ::= { tFilterLogEntry 2 }

tFilterLogDestination OBJECT-TYPE
    SYNTAX      TFilterLogDestination
    MAX-ACCESS  read-create
    STATUS      current
    DESCRIPTION
        "This object specifies the destination of the log."
    DEFVAL { memory }
    ::= { tFilterLogEntry 3 }

tFilterLogDescription OBJECT-TYPE
    SYNTAX      TItemDescription
    MAX-ACCESS  read-create
    STATUS      current
    DESCRIPTION
        "User-provided description for this filter log entry."
    DEFVAL { ''H }
    ::= { tFilterLogEntry 4 }

tFilterLogMaxNumEntries OBJECT-TYPE
    SYNTAX      Unsigned32 (0..50000)
    MAX-ACCESS  read-create
    STATUS      current
    DESCRIPTION
        "The object tFilterLogMaxNumEntries specifies the maximum number
         of entries that the log can store.

         If tFilterLogDestination is not 'memory(1)' then
         the object tFilterLogMaxNumEntries maintains a value of '0',
         and Any change attempts will be silently discarded."
    DEFVAL { 1000 }
    ::= { tFilterLogEntry 5 }

tFilterLogSysLogId OBJECT-TYPE
    SYNTAX      Unsigned32
    MAX-ACCESS  read-create
    STATUS      current
    DESCRIPTION
        "The object tFilterLogSysLogId specifies the syslog Id to be used
         as destination.

         If tFilterLogDestination is not 'sysLog(2)' then the object
         tFilterLogSysLogId maintains a value of '0',
         and any change attempts will be silently discarded."
    DEFVAL { 0 }
    ::= { tFilterLogEntry 6 }

tFilterLogFileId OBJECT-TYPE
    SYNTAX      Unsigned32
    MAX-ACCESS  read-create
    STATUS      current
    DESCRIPTION
        "The object tFilterLogFileId specifies the File Id to be used
         as destination.

         If tFilterLogDestination is not 'file(3)' then the object
         tFilterLogFileId Imaintains a value of '0',
         and any change attempts will be silently discarded."
    DEFVAL { 0 }
    ::= { tFilterLogEntry 7 }

tFilterLogStopOnFull OBJECT-TYPE
    SYNTAX      TruthValue
    MAX-ACCESS  read-create
    STATUS      current
    DESCRIPTION
        ""
    DEFVAL { false }
    ::= { tFilterLogEntry 8 }

tFilterLogEnabled OBJECT-TYPE
    SYNTAX      TruthValue
    MAX-ACCESS  read-create
    STATUS      current
    DESCRIPTION
        ""
    DEFVAL { true }
    ::= { tFilterLogEntry 9 }

tFilterLogSummaryEnabled OBJECT-TYPE
    SYNTAX      TruthValue
    MAX-ACCESS  read-create
    STATUS      current
    DESCRIPTION
         "The value of tFilterLogSummaryEnabled specifies whether
          or not summarization of filter log entries is performed.
          Summarization is only allowed in case tFilterLogDestination is set
          to syslog."
    DEFVAL { false }
    ::= { tFilterLogEntry 10 }

tFilterLogSummaryCrit1 OBJECT-TYPE
    SYNTAX      TFilterLogSummaryCriterium
    MAX-ACCESS  read-create
    STATUS      current
    DESCRIPTION
        "The value of tFilterLogSummaryCrit1 specifies how
         filter log entries will be summarized.

         This field is only meaningful if the object
         tFilterLogSummaryEnabled is set to true."
    DEFVAL { srcAddr }
    ::= { tFilterLogEntry 11 }

--
-- Filter Log Scalars
--

tFilterLogScalars  OBJECT IDENTIFIER ::= { tFilterObjects 6 }

tFilterLogMaxInstances OBJECT-TYPE
    SYNTAX      Gauge32
    MAX-ACCESS  read-only
    STATUS      current
    DESCRIPTION
        "tFilterLogMaxInstances maintains the maximum allowed instances
         of filter logs allowed on the system"
    ::= { tFilterLogScalars 1 }

tFilterLogInstances OBJECT-TYPE
    SYNTAX      Gauge32
    MAX-ACCESS  read-only
    STATUS      current
    DESCRIPTION
        "tFilterLogInstances maintains the instances of filter logs
         presently existing on the system"
    ::= { tFilterLogScalars 2 }

tFilterLogBindings OBJECT-TYPE
    SYNTAX      Gauge32
    MAX-ACCESS  read-only
    STATUS      current
    DESCRIPTION
        "tFilterLogBindings maintains the count of the configured
         filter log bindings presently existing on the system. The
         bindings get instantiated when the filter is instantiated"
    ::= { tFilterLogScalars 3 }


--
-- Filter Redirect Policies
--

tFilterRedirectPolicyTable OBJECT-TYPE
    SYNTAX      SEQUENCE OF TFilterRedirectPolicyEntry
    MAX-ACCESS  not-accessible
    STATUS      current
    DESCRIPTION
        "Contains a List of all redirect policies configured on this system."
    ::= { tFilterObjects 10 }

tFilterRedirectPolicyEntry OBJECT-TYPE
    SYNTAX      TFilterRedirectPolicyEntry
    MAX-ACCESS  not-accessible
    STATUS      current
    DESCRIPTION
        "Information about a particular redirect policy. Entries are
        created/deleted by user."
    INDEX { tFilterRedirectPolicy }
    ::= { tFilterRedirectPolicyTable 1 }

TFilterRedirectPolicyEntry ::= SEQUENCE
    {
        tFilterRedirectPolicy     TNamedItem,
        tFilterRPRowStatus        RowStatus,
        tFilterRPDescription      TItemDescription,
        tFilterRPAdminState       TmnxAdminState,
        tFilterRPActiveDest       IpAddress
    }

tFilterRedirectPolicy OBJECT-TYPE
    SYNTAX      TNamedItem
    MAX-ACCESS  not-accessible
    STATUS      current
    DESCRIPTION
        "tFilterRedirectPolicy uniquely identifies each redirect policy
        configured on this system."
    ::= { tFilterRedirectPolicyEntry 1 }

tFilterRPRowStatus OBJECT-TYPE
    SYNTAX      RowStatus
    MAX-ACCESS  read-create
    STATUS      current
    DESCRIPTION
        "tFilterRPRowStatus allows entries to be created and deleted in the
        tFilterRedirectPolicyTable."
    ::= { tFilterRedirectPolicyEntry 2 }

tFilterRPDescription OBJECT-TYPE
    SYNTAX      TItemDescription
    MAX-ACCESS  read-create
    STATUS      current
    DESCRIPTION
        "User-provided description for this redirect policy is maintained in
        the object tFilterRPDescription."
    DEFVAL { ''H }
    ::= { tFilterRedirectPolicyEntry 3 }

tFilterRPAdminState OBJECT-TYPE
    SYNTAX      TmnxAdminState
    MAX-ACCESS  read-create
    STATUS      current
    DESCRIPTION
        "tFilterRPAdminState holds the admin state of the policy. If the
        admin state is 'outOfService', the tests will not be conducted."
    DEFVAL { outOfService }
    ::= { tFilterRedirectPolicyEntry 4 }

tFilterRPActiveDest OBJECT-TYPE
    SYNTAX      IpAddress
    MAX-ACCESS  read-only
    STATUS      current
    DESCRIPTION
        "tFilterRPActiveDest indicates the IP address of the active
        destination. A value of 0 indicates that there is currently
        no active destination."
    ::= { tFilterRedirectPolicyEntry 5 }

--
-- Filter Redirect Destinations
--

tFilterRedirectDestTable OBJECT-TYPE
    SYNTAX      SEQUENCE OF TFilterRedirectDestEntry
    MAX-ACCESS  not-accessible
    STATUS      current
    DESCRIPTION
        "Contains a List of all redirect destinations configured on this
        system."
    ::= { tFilterObjects 11 }

tFilterRedirectDestEntry OBJECT-TYPE
    SYNTAX      TFilterRedirectDestEntry
    MAX-ACCESS  not-accessible
    STATUS      current
    DESCRIPTION
        "Information about a particular Redirect destination. Entries are
         created/deleted by user."
    INDEX { tFilterRedirectPolicy, tFilterRedirectDest }
    ::= { tFilterRedirectDestTable 1 }

TFilterRedirectDestEntry ::= SEQUENCE
    {
        tFilterRedirectDest       IpAddress,
        tFilterRDRowStatus        RowStatus,
        tFilterRDDescription      TItemDescription,
        tFilterRDAdminPriority    Unsigned32,
        tFilterRDOperPriority     Unsigned32,
        tFilterRDAdminState       TmnxAdminState,
        tFilterRDOperState        TmnxOperState
    }

tFilterRedirectDest OBJECT-TYPE
    SYNTAX      IpAddress
    MAX-ACCESS  not-accessible
    STATUS      current
    DESCRIPTION
        "tFilterRedirectDest holds the IP address of the destination
        entry."
    ::= { tFilterRedirectDestEntry 1 }

tFilterRDRowStatus OBJECT-TYPE
    SYNTAX      RowStatus
    MAX-ACCESS  read-create
    STATUS      current
    DESCRIPTION
        "tFilterRDRowStatus allows entries to be created and deleted
        in the tFilterRedirectDestTable."
    ::= { tFilterRedirectDestEntry 2 }

tFilterRDDescription OBJECT-TYPE
    SYNTAX      TItemDescription
    MAX-ACCESS  read-create
    STATUS      current
    DESCRIPTION
        "User-provided description for this destination is maintained in
        the object tFilterRDDescription."
    DEFVAL { ''H }
    ::= { tFilterRedirectDestEntry 3 }

tFilterRDAdminPriority OBJECT-TYPE
    SYNTAX      Unsigned32 (1..255)
    MAX-ACCESS  read-create
    STATUS      current
    DESCRIPTION
        "tFilterRDAdminPriority holds the configured base priority for
        the destination."
    DEFVAL { 100 }
    ::= { tFilterRedirectDestEntry 4 }

tFilterRDOperPriority OBJECT-TYPE
    SYNTAX      Unsigned32 (0..255)
    MAX-ACCESS  read-only
    STATUS      current
    DESCRIPTION
        "tFilterRDAdminPriority maintains the operational value of the
        priority for this destination. The highest operational priority
        across multiple destinations is used as the preferred destination.

        A value of '0' is maintained if the destination if tFilterRDOperState
        is 'outOfService'."
    ::= { tFilterRedirectDestEntry 5 }

tFilterRDAdminState OBJECT-TYPE
    SYNTAX      TmnxAdminState
    MAX-ACCESS  read-create
    STATUS      current
    DESCRIPTION
        "tFilterRDAdminState maintains the configured state of the destination.
        If the admin state is 'outOfService', the tests for this destination
        will not be conducted."
    DEFVAL { outOfService }
    ::= { tFilterRedirectDestEntry 6 }

tFilterRDOperState OBJECT-TYPE
    SYNTAX      TmnxOperState
    MAX-ACCESS  read-only
    STATUS      current
    DESCRIPTION
        "The value of tFilterRDOperState indicates the operational state of
         the destination."
    ::= { tFilterRedirectDestEntry 7 }

--
-- Filter Redirect SNMP Test Table
--

tFilterRedirectSNMPTestTable OBJECT-TYPE
    SYNTAX      SEQUENCE OF TFilterRedirectSNMPTestEntry
    MAX-ACCESS  not-accessible
    STATUS      current
    DESCRIPTION
        "Contains a List of all redirect SNMP tests configured on this
        system."
    ::= { tFilterObjects 12 }

tFilterRedirectSNMPTestEntry OBJECT-TYPE
    SYNTAX      TFilterRedirectSNMPTestEntry
    MAX-ACCESS  not-accessible
    STATUS      current
    DESCRIPTION
        "Information about a specific SNMP test configured for a destination.
        Entries are created/deleted  by user."
    INDEX {
              tFilterRedirectPolicy,
              tFilterRedirectDest,
              tFilterRedirectSNMPTest
          }
    ::= { tFilterRedirectSNMPTestTable 1 }

TFilterRedirectSNMPTestEntry ::= SEQUENCE
    {
        tFilterRedirectSNMPTest       TNamedItem,
        tFilterRSTRowStatus           RowStatus,
        tFilterRSTOID                 OBJECT IDENTIFIER,
        tFilterRSTCommunity           DisplayString,
        tFilterRSTSNMPVersion         INTEGER,
        tFilterRSTInterval            Unsigned32,
        tFilterRSTTimeout             Unsigned32,
        tFilterRSTDropCount           Unsigned32,
        tFilterRSTHoldDown            Unsigned32,
        tFilterRSTHoldDownRemain      Unsigned32,
        tFilterRSTLastActionTime      TimeStamp,
        tFilterRSTLastOID             OBJECT IDENTIFIER,
        tFilterRSTLastType            INTEGER,
        tFilterRSTLastCounter32Val    Counter32,
        tFilterRSTLastUnsigned32Val   Unsigned32,
        tFilterRSTLastTimeTicksVal    TimeTicks,
        tFilterRSTLastInt32Val        Integer32,
        tFilterRSTLastOctetStringVal  OCTET STRING,
        tFilterRSTLastIpAddressVal    IpAddress,
        tFilterRSTLastOidVal          OBJECT IDENTIFIER,
        tFilterRSTLastCounter64Val    Counter64,
        tFilterRSTLastOpaqueVal       Opaque,
        tFilterRSTLastAction          INTEGER,
        tFilterRSTLastPrioChange      Integer32,
        tFilterRSTNextRespIndex       Integer32
    }

tFilterRedirectSNMPTest OBJECT-TYPE
    SYNTAX      TNamedItem
    MAX-ACCESS  not-accessible
    STATUS      current
    DESCRIPTION
        "tFilterRedirectSNMPTest specifies the name of the SNMP test."
    ::= { tFilterRedirectSNMPTestEntry 1 }

tFilterRSTRowStatus OBJECT-TYPE
    SYNTAX      RowStatus
    MAX-ACCESS  read-create
    STATUS      current
    DESCRIPTION
        "tFilterRSTRowStatus allows tests to be created and deleted in the
         tFilterRedirectSNMPTestTable."
    ::= { tFilterRedirectSNMPTestEntry 2 }

tFilterRSTOID OBJECT-TYPE
    SYNTAX      OBJECT IDENTIFIER
    MAX-ACCESS  read-create
    STATUS      current
    DESCRIPTION
        "tFilterRSTOID stores the OID of the object to be fetched from the
        destination.
        The value of this object can only be changed if the object
        tFilterRSTCommunity is changed at the same time."
    ::= { tFilterRedirectSNMPTestEntry 3 }

tFilterRSTCommunity OBJECT-TYPE
    SYNTAX      DisplayString (SIZE(0..32))
    MAX-ACCESS  read-create
    STATUS      current
    DESCRIPTION
        "The value of tFilterRSTCommunity is the SNMPv1 or SNMPv2c Community
         String or the SNMPv3 Context Name used to conduct this SNMP test as
         described in RFC2571 and RFC2737.

         When the value of tFilterRSTSNMPVersion is 'snmpv1' or 'snmpv2c'
         this object represents a community string.  When the value of
         tFilterRSTSNMPVersion is 'snmpv3' this object represents a SNMPv3
         context name.
         The value of this object can only be changed if the object
         tFilterRSTOID is changed at the same time."
    DEFVAL { ''H }
    ::= { tFilterRedirectSNMPTestEntry 4 }

tFilterRSTSNMPVersion OBJECT-TYPE
    SYNTAX      INTEGER {
                     snmpv1 (1),
                     snmpv2c (2),
                     snmpv3 (3)
                 }
    MAX-ACCESS  read-create
    STATUS      current
    DESCRIPTION
        "tFilterRSTSNMPVersion specifies the SNMP PDU format to be used while
         conducting the test. Currently only snmpv2c is supported"
    DEFVAL { snmpv2c }
    ::= { tFilterRedirectSNMPTestEntry 5 }

tFilterRSTInterval OBJECT-TYPE
    SYNTAX      Unsigned32 (1..60)
    UNITS        "seconds"
    MAX-ACCESS  read-create
    STATUS      current
    DESCRIPTION
        "The value of tFilterRSTInterval specifies the amount of time
        in seconds between consecutive requests sent to the far end
        host."
    DEFVAL { 1 }
    ::= { tFilterRedirectSNMPTestEntry 6 }

tFilterRSTTimeout OBJECT-TYPE
    SYNTAX      Unsigned32 (1..60)
    UNITS        "seconds"
    MAX-ACCESS  read-create
    STATUS      current
    DESCRIPTION
        "The value of tFilterRSTTimeout specifies the amount of time
        in seconds that is allowed for receiving a response from the
        far end host. If a reply is not received within this time the
        far end host is considered unresponsive."
    DEFVAL { 1 }
    ::= { tFilterRedirectSNMPTestEntry 7 }

tFilterRSTDropCount OBJECT-TYPE
    SYNTAX      Unsigned32 (1..60)
    MAX-ACCESS  read-create
    STATUS      current
    DESCRIPTION
        "The value of tFilterRSTDropCount specifies the number of
        consecutive requests that must fail for the destination to
        declared unreachable."
    DEFVAL { 3 }
    ::= { tFilterRedirectSNMPTestEntry 8 }

tFilterRSTHoldDown OBJECT-TYPE
    SYNTAX      Unsigned32 (0..86400)
    UNITS        "seconds"
    MAX-ACCESS  read-create
    STATUS      current
    DESCRIPTION
        "The value of tFilterRSTHoldDown specifies the amount of time
        in seconds that the system should be held down if any of the test
        has marked it unreachable."
    DEFVAL { 0 }
    ::= { tFilterRedirectSNMPTestEntry 9 }

tFilterRSTHoldDownRemain OBJECT-TYPE
    SYNTAX      Unsigned32 (0..86400)
    UNITS        "seconds"
    MAX-ACCESS  read-only
    STATUS      current
    DESCRIPTION
        "The value of tFilterRSTHoldDownRemain indicates the amount of time
        in seconds that the system will remain in held down state before
        being used again."
    ::= { tFilterRedirectSNMPTestEntry 10 }

tFilterRSTLastActionTime OBJECT-TYPE
    SYNTAX      TimeStamp
    MAX-ACCESS  read-only
    STATUS      current
    DESCRIPTION
        "tFilterRSTLastActionTime maintains the time stamp when this test
        received a response for a probe sent out."
    ::= { tFilterRedirectSNMPTestEntry 11 }

tFilterRSTLastOID OBJECT-TYPE
    SYNTAX     OBJECT IDENTIFIER
    MAX-ACCESS read-only
    STATUS     current
    DESCRIPTION
     "The object tFilterRSTLastOID holds the OID received in the
     response."
    ::= { tFilterRedirectSNMPTestEntry 12 }

tFilterRSTLastType OBJECT-TYPE
    SYNTAX      INTEGER {
                    none(0),
                    counter32(1),
                    unsigned32(2),
                    timeTicks(3),
                    integer32(4),
                    ipAddress(5),
                    octetString(6),
                    objectId(7),
                    counter64(8),
                    opaque(9)
                }
    MAX-ACCESS  read-only
    STATUS      current
    DESCRIPTION
     "tFilterRSTLastType maintains the type of the value received.
      A value of none(0) indicated that no value has been received"
    ::= { tFilterRedirectSNMPTestEntry  13 }

tFilterRSTLastCounter32Val OBJECT-TYPE
    SYNTAX      Counter32
    MAX-ACCESS  read-only
    STATUS      current
    DESCRIPTION
     "The value tFilterRSTLastType is 'counter32'."
    ::= { tFilterRedirectSNMPTestEntry  14 }

tFilterRSTLastUnsigned32Val OBJECT-TYPE
    SYNTAX      Unsigned32
    MAX-ACCESS  read-only
    STATUS      current
    DESCRIPTION
     "The value tFilterRSTLastType is 'unsigned32'."
    ::= { tFilterRedirectSNMPTestEntry  15 }

tFilterRSTLastTimeTicksVal OBJECT-TYPE
    SYNTAX      TimeTicks
    MAX-ACCESS  read-only
    STATUS      current
    DESCRIPTION
     "The value tFilterRSTLastType is 'timeTicks'."
    ::= { tFilterRedirectSNMPTestEntry  16 }

tFilterRSTLastInt32Val OBJECT-TYPE
    SYNTAX      Integer32
    MAX-ACCESS  read-only
    STATUS      current
    DESCRIPTION
     "The value tFilterRSTLastType is 'integer32'."
    ::= { tFilterRedirectSNMPTestEntry  17 }

tFilterRSTLastOctetStringVal OBJECT-TYPE
    SYNTAX      OCTET STRING
    MAX-ACCESS  read-only
    STATUS      current
    DESCRIPTION
     "The value tFilterRSTLastType is 'octetString'."
    ::= { tFilterRedirectSNMPTestEntry  18 }

tFilterRSTLastIpAddressVal OBJECT-TYPE
    SYNTAX      IpAddress
    MAX-ACCESS  read-only
    STATUS      current
    DESCRIPTION
     "The value tFilterRSTLastType is 'ipAddress'. Although
     this seems to be unfriendly for IPv6, we have to
     recognize that there are a number of older MIBs that do
     contain an IPv4 format address, known as IpAddress.

     IPv6 addresses are represented using TAddress or InetAddress,
     and so the underlying datatype is OCTET STRING, and their
     value would be stored in the tFilterRSTLastOctetStringVal
     column."
    ::= { tFilterRedirectSNMPTestEntry  19 }

tFilterRSTLastOidVal OBJECT-TYPE
    SYNTAX      OBJECT IDENTIFIER
    MAX-ACCESS  read-only
    STATUS      current
    DESCRIPTION
     "The value tFilterRSTLastType is 'objectId'."
    ::= { tFilterRedirectSNMPTestEntry  20 }

tFilterRSTLastCounter64Val OBJECT-TYPE
    SYNTAX      Counter64
    MAX-ACCESS  read-only
    STATUS      current
    DESCRIPTION
     "The value tFilterRSTLastType is 'counter64'."
    ::= { tFilterRedirectSNMPTestEntry  21 }

tFilterRSTLastOpaqueVal OBJECT-TYPE
    SYNTAX      Opaque
    MAX-ACCESS  read-only
    STATUS      current
    DESCRIPTION
     "The value tFilterRSTLastType is 'opaque'."
    ::= { tFilterRedirectSNMPTestEntry  22 }

tFilterRSTLastAction OBJECT-TYPE
    SYNTAX      INTEGER {
                     enable (1),
                     disable (2),
                     none (3)
                 }
    MAX-ACCESS  read-only
    STATUS      current
    DESCRIPTION
        "tFilterRSTLastAction maintains impact that the last test probe
        made on the operational status of the destination as maintained
        in tFilterRDOperState.

        If the last action was 'disable', the destination may not be
        used for tFilterRSTHoldDown seconds."
    ::= { tFilterRedirectSNMPTestEntry 23 }

tFilterRSTLastPrioChange OBJECT-TYPE
    SYNTAX      Integer32 (-255..255)
    MAX-ACCESS  read-only
    STATUS      current
    DESCRIPTION
        "If the last action on the operational state of the destination
        i.e. tFilterRSTLastAction is 'enable', tFilterRSTLastPrioChange
        maintains the impact that the last test probe made on the
        operational priority of the destination.

        In other cases, this object has no significance and hence should
        be holding the value '0'."
    ::= { tFilterRedirectSNMPTestEntry 24 }

tFilterRSTNextRespIndex OBJECT-TYPE
    SYNTAX      Integer32 (-1|1..2147483647)
    MAX-ACCESS  read-only
    STATUS      current
    DESCRIPTION
        "The value of tFilterRSTNextRespIndex indicates the next response index
        to be used while creating a row in the tFilterRedirectSNMPRespTable.

        The value of '-1' means that the maximum number of return values
        for this OID are already configured."
    ::= { tFilterRedirectSNMPTestEntry 25 }


--
-- Filter Redirect SNMP Response Table
--

tFilterRedirectSNMPRespTable OBJECT-TYPE
    SYNTAX      SEQUENCE OF TFilterRedirectSNMPRespEntry
    MAX-ACCESS  not-accessible
    STATUS      current
    DESCRIPTION
        "Each row in this table holds the effect of the test on the
        destination for a specific return value.

        Each row is created once and cannot be modified after creation.
        Any change attempts will be silently discarded."
    ::= { tFilterObjects 13 }

tFilterRedirectSNMPRespEntry OBJECT-TYPE
    SYNTAX      TFilterRedirectSNMPRespEntry
    MAX-ACCESS  not-accessible
    STATUS      current
    DESCRIPTION
        "Information about action to be taken for a specific destination
        when a specific response is received.

        Each row is created once and cannot be modified after creation.
        Any change attempts will be silently discarded."
    INDEX {
              tFilterRedirectPolicy,
              tFilterRedirectDest,
              tFilterRedirectSNMPTest,
              tFilterRSTRespId
          }
    ::= { tFilterRedirectSNMPRespTable 1 }

TFilterRedirectSNMPRespEntry ::= SEQUENCE
    {
        tFilterRSTRespId          Integer32,
        tFilterRSTRespRowStatus   RowStatus,
        tFilterRSTRespAction      INTEGER,
        tFilterRSTRespPrioChange  Unsigned32,
        tFilterRSTRespOID         OBJECT IDENTIFIER,
        tFilterRSTRespType        INTEGER,
        tFilterRSTCounter32Val    Counter32,
        tFilterRSTUnsigned32Val   Unsigned32,
        tFilterRSTTimeTicksVal    TimeTicks,
        tFilterRSTInt32Val        Integer32,
        tFilterRSTOctetStringVal  OCTET STRING,
        tFilterRSTIpAddressVal    IpAddress,
        tFilterRSTOidVal          OBJECT IDENTIFIER,
        tFilterRSTCounter64Val    Counter64,
        tFilterRSTOpaqueVal       Opaque
    }

tFilterRSTRespId OBJECT-TYPE
    SYNTAX      Integer32 (1..2147483647)
    MAX-ACCESS  not-accessible
    STATUS      current
    DESCRIPTION
        "tFilterRSTRespId holds the response value received from
        the destination."
    ::= { tFilterRedirectSNMPRespEntry 1 }

tFilterRSTRespRowStatus OBJECT-TYPE
    SYNTAX      RowStatus
    MAX-ACCESS  read-create
    STATUS      current
    DESCRIPTION
        "This object allows response strings to be specified for a specific
        test and the change it will cause to the priority of the destination."
    ::= { tFilterRedirectSNMPRespEntry 2 }

tFilterRSTRespAction OBJECT-TYPE
    SYNTAX      INTEGER {
                     increase (1),
                     decrease (2),
                     disable (3)
                     }
    MAX-ACCESS  read-create
    STATUS      current
    DESCRIPTION
        "tFilterRSTRespAction specifies the type of change that should
        be made to the destination priority tFilterRDOperPriority, if
        the return value is same as tFilterRSTRespId.
        If tFilterRSTRespPrioChange is 0 this field will be set to 'disable'.

        This field cannot be modified after creation. Any change attempts
        will be silently discarded."
    DEFVAL { disable }
    ::= { tFilterRedirectSNMPRespEntry 3 }

tFilterRSTRespPrioChange OBJECT-TYPE
    SYNTAX      Unsigned32 (0..255)
    MAX-ACCESS  read-create
    STATUS      current
    DESCRIPTION
        "tFilterRSTRespPrioChange specifies the amount of change to
        be made to the priority of the destination if the
        tFilterRSTRespAction is either 'increase' or 'decrease'.
        If tFilterRSTRespAction is 'disable', this field will be set to 0.

        This field cannot be modified after creation. Any change attempts
        will be silently discarded."
    DEFVAL { 0 }
    ::= { tFilterRedirectSNMPRespEntry 4 }

tFilterRSTRespOID OBJECT-TYPE
    SYNTAX     OBJECT IDENTIFIER
    MAX-ACCESS read-create
    STATUS     current
    DESCRIPTION
        "The object tFilterRSTRespOID holds the OID to be received in the
        response.

        This field cannot be modified after creation. Any change attempts
        will be silently discarded."
    ::= { tFilterRedirectSNMPRespEntry 5 }

tFilterRSTRespType OBJECT-TYPE
    SYNTAX      INTEGER {
                    counter32(1),
                    unsigned32(2),
                    timeTicks(3),
                    integer32(4),
                    ipAddress(5),
                    octetString(6),
                    objectId(7),
                    counter64(8),
                    opaque(9)
                }
    MAX-ACCESS  read-create
    STATUS      current
    DESCRIPTION
     "tFilterRSTRespType maintains the type of the value to be received.

      Note: types 'objectId' and 'counter64' are not supported for now,
      and will be rejected when used.

      This field cannot be modified after creation. Any change attempts
      will be silently discarded."
    ::= { tFilterRedirectSNMPRespEntry  6 }

tFilterRSTCounter32Val OBJECT-TYPE
    SYNTAX      Counter32
    MAX-ACCESS  read-create
    STATUS      current
    DESCRIPTION
     "The value tFilterRSTRespType is 'counter32'.
      This field cannot be modified after creation. Any change attempts
      will be silently discarded."
    ::= { tFilterRedirectSNMPRespEntry  7 }

tFilterRSTUnsigned32Val OBJECT-TYPE
    SYNTAX      Unsigned32
    MAX-ACCESS  read-create
    STATUS      current
    DESCRIPTION
     "The value tFilterRSTRespType is 'unsigned32'.
      This field cannot be modified after creation. Any change attempts
      will be silently discarded."
    ::= { tFilterRedirectSNMPRespEntry  8 }

tFilterRSTTimeTicksVal OBJECT-TYPE
    SYNTAX      TimeTicks
    MAX-ACCESS  read-create
    STATUS      current
    DESCRIPTION
     "The value tFilterRSTRespType is 'timeTicks'.
      This field cannot be modified after creation. Any change attempts
      will be silently discarded."
    ::= { tFilterRedirectSNMPRespEntry  9 }

tFilterRSTInt32Val OBJECT-TYPE
    SYNTAX      Integer32
    MAX-ACCESS  read-create
    STATUS      current
    DESCRIPTION
     "The value tFilterRSTRespType is 'integer32'.
      This field cannot be modified after creation. Any change attempts
      will be silently discarded."
    ::= { tFilterRedirectSNMPRespEntry  10 }

tFilterRSTOctetStringVal OBJECT-TYPE
    SYNTAX      OCTET STRING
    MAX-ACCESS  read-create
    STATUS      current
    DESCRIPTION
     "The value tFilterRSTRespType is 'octetString'.
      This field cannot be modified after creation. Any change attempts
      will be silently discarded."
    ::= { tFilterRedirectSNMPRespEntry  11 }

tFilterRSTIpAddressVal OBJECT-TYPE
    SYNTAX      IpAddress
    MAX-ACCESS  read-create
    STATUS      current
    DESCRIPTION
     "The value tFilterRSTRespType is 'ipAddress'. Although
     this seems to be unfriendly for IPv6, we have to
     recognize that there are a number of older MIBs that do
     contain an IPv4 format address, known as IpAddress.

     IPv6 addresses are represented using TAddress or InetAddress,
     and so the underlying datatype is OCTET STRING, and their
     value would be stored in the tFilterRSTOctetStringVal
     column.

     This field cannot be modified after creation. Any change attempts
     will be silently discarded."
    ::= { tFilterRedirectSNMPRespEntry  12 }

tFilterRSTOidVal OBJECT-TYPE
    SYNTAX      OBJECT IDENTIFIER
    MAX-ACCESS  read-create
    STATUS      current
    DESCRIPTION
     "The response value if tFilterRSTRespType is set to 'objectId'.
      This field cannot be modified after creation. Any change attempts
      will be silently discarded."
    ::= { tFilterRedirectSNMPRespEntry  13 }

tFilterRSTCounter64Val OBJECT-TYPE
    SYNTAX      Counter64
    MAX-ACCESS  read-create
    STATUS      current
    DESCRIPTION
     "The response value if tFilterRSTRespType is set to 'counter64'.
      This field cannot be modified after creation. Any change attempts
      will be silently discarded."
    ::= { tFilterRedirectSNMPRespEntry  14 }

tFilterRSTOpaqueVal OBJECT-TYPE
    SYNTAX      Opaque
    MAX-ACCESS  read-create
    STATUS      current
    DESCRIPTION
     "The value tFilterRSTRespType is 'opaque'.
      This field cannot be modified after creation. Any change attempts
      will be silently discarded."
    ::= { tFilterRedirectSNMPRespEntry  15 }


--
-- Filter Redirect URL Test Table
--

tFilterRedirectURLTestTable OBJECT-TYPE
    SYNTAX      SEQUENCE OF TFilterRedirectURLTestEntry
    MAX-ACCESS  not-accessible
    STATUS      current
    DESCRIPTION
        "Contains a List of all redirect snmp tests configured on this
        system."
    ::= { tFilterObjects 14 }

tFilterRedirectURLTestEntry OBJECT-TYPE
    SYNTAX      TFilterRedirectURLTestEntry
    MAX-ACCESS  not-accessible
    STATUS      current
    DESCRIPTION
        "Information about a specific URL test configured for a destination.
        Entries are created/deleted  by user. Entries have a presumed
        StorageType of nonVolatile."
    INDEX {
              tFilterRedirectPolicy,
              tFilterRedirectDest,
              tFilterRedirectURLTest
          }
    ::= { tFilterRedirectURLTestTable 1 }

TFilterRedirectURLTestEntry ::= SEQUENCE
    {
        tFilterRedirectURLTest    TNamedItem,
        tFilterRUTRowStatus       RowStatus,
        tFilterRUTURL             DisplayString,
        tFilterRUTHTTPVersion     DisplayString,
        tFilterRUTInterval        Unsigned32,
        tFilterRUTTimeout         Unsigned32,
        tFilterRUTDropCount       Unsigned32,
        tFilterRUTHoldDown        Unsigned32,
        tFilterRUTHoldDownRemain  Unsigned32,
        tFilterRUTLastActionTime  TimeStamp,
        tFilterRUTLastRetCode     Unsigned32,
        tFilterRUTLastAction      INTEGER,
        tFilterRUTLastPrioChange  Integer32
    }

tFilterRedirectURLTest OBJECT-TYPE
    SYNTAX      TNamedItem
    MAX-ACCESS  not-accessible
    STATUS      current
    DESCRIPTION
        "tFilterRedirectURLTest holds the name of the URL test."
    ::= { tFilterRedirectURLTestEntry 1 }

tFilterRUTRowStatus OBJECT-TYPE
    SYNTAX      RowStatus
    MAX-ACCESS  read-create
    STATUS      current
    DESCRIPTION
        "tFilterRUTRowStatus allows tests to be created and deleted in the
        tFilterRedirectURLTestTable."
    ::= { tFilterRedirectURLTestEntry 2 }

tFilterRUTURL OBJECT-TYPE
    SYNTAX      DisplayString
    MAX-ACCESS  read-create
    STATUS      current
    DESCRIPTION
        "This object holds the URL to be probed."
    DEFVAL { ''H }
    ::= { tFilterRedirectURLTestEntry 3 }

tFilterRUTHTTPVersion OBJECT-TYPE
    SYNTAX      DisplayString
    MAX-ACCESS  read-create
    STATUS      current
    DESCRIPTION
        "The HTTP Version to be used while performing the URL test.
        The system by default uses HTTP Version 1.1 until explicitly
        specified."
    DEFVAL { ''H }
    ::= { tFilterRedirectURLTestEntry 4 }

tFilterRUTInterval OBJECT-TYPE
    SYNTAX      Unsigned32 (1..60)
    UNITS        "seconds"
    MAX-ACCESS  read-create
    STATUS      current
    DESCRIPTION
        "The value of tFilterRUTInterval specifies the amount of time
        in seconds between consecutive requests sent to the far end
        host."
    DEFVAL { 1 }
    ::= { tFilterRedirectURLTestEntry 5 }

tFilterRUTTimeout OBJECT-TYPE
    SYNTAX      Unsigned32 (1..60)
    UNITS        "seconds"
    MAX-ACCESS  read-create
    STATUS      current
    DESCRIPTION
        "The value of tFilterRUTTimeout specifies the amount of time
        in seconds that is allowed for receiving a response from the
        far end host. If a reply is not received within this time the
        far end host is considered unresponsive."
    DEFVAL { 1 }
    ::= { tFilterRedirectURLTestEntry 6 }

tFilterRUTDropCount OBJECT-TYPE
    SYNTAX      Unsigned32 (1..60)
    MAX-ACCESS  read-create
    STATUS      current
    DESCRIPTION
        "The value of tFilterRUTDropCount specifies the number of
        consecutive requests that must fail for the destination to
        declared unreachable."
    DEFVAL { 3 }
    ::= { tFilterRedirectURLTestEntry 7 }

tFilterRUTHoldDown OBJECT-TYPE
    SYNTAX      Unsigned32 (0..86400)
    UNITS        "seconds"
    MAX-ACCESS  read-create
    STATUS      current
    DESCRIPTION
        "The value of tFilterRUTHoldDown specifies the amount of time
        in seconds that the system should be held down if any of the test
        has marked it unreachable."
    DEFVAL { 0 }
    ::= { tFilterRedirectURLTestEntry 8 }

tFilterRUTHoldDownRemain OBJECT-TYPE
    SYNTAX      Unsigned32 (0..86400)
    UNITS        "seconds"
    MAX-ACCESS  read-only
    STATUS      current
    DESCRIPTION
        "The value of tFilterRUTHoldDownRemain indicates the amount of time
        in seconds that the system will remain in held down state before
        being used again."
    ::= { tFilterRedirectURLTestEntry 9 }

tFilterRUTLastActionTime OBJECT-TYPE
    SYNTAX      TimeStamp
    MAX-ACCESS  read-only
    STATUS      current
    DESCRIPTION
        "tFilterRUTLastActionTime maintains the time stamp when this test
        received a response for a probe sent out."
    ::= { tFilterRedirectURLTestEntry 10 }

tFilterRUTLastRetCode OBJECT-TYPE
    SYNTAX      Unsigned32
    MAX-ACCESS  read-only
    STATUS      current
    DESCRIPTION
        "tFilterRUTLastRetCode holds the return code received in the last
        response."
    ::= { tFilterRedirectURLTestEntry 11 }

tFilterRUTLastAction OBJECT-TYPE
    SYNTAX      INTEGER {
                     enable (1),
                     disable (2),
                     none (3)
                 }
    MAX-ACCESS  read-only
    STATUS      current
    DESCRIPTION
        "tFilterRUTLastAction maintains impact that the last test probe
        made on the operational status of the destination as maintained
        in tFilterRDOperState.

        If the last action was 'disable', the destination may not be
        used for tFilterRUTHoldDown seconds."
    ::= { tFilterRedirectURLTestEntry 12 }

tFilterRUTLastPrioChange OBJECT-TYPE
    SYNTAX      Integer32 (-255..255)
    MAX-ACCESS  read-only
    STATUS      current
    DESCRIPTION
        "If the last action on the operational state of the destination
        i.e. tFilterRUTLastAction is 'enable', tFilterRUTLastPrioChange
        maintains the impact that the last test probe made on the
        operational priority of the destination.

        In other cases, this object has no significance and hence should
        be holding the value '0'."
    ::= { tFilterRedirectURLTestEntry 13 }


--
-- Filter Redirect URL Response Table
--

tFilterRedirectURLRespTable OBJECT-TYPE
    SYNTAX      SEQUENCE OF TFilterRedirectURLRespEntry
    MAX-ACCESS  not-accessible
    STATUS      current
    DESCRIPTION
        "Each row in this table holds the effect of the test on
        the destination for a range of return values."
    ::= { tFilterObjects 15 }

tFilterRedirectURLRespEntry OBJECT-TYPE
    SYNTAX      TFilterRedirectURLRespEntry
    MAX-ACCESS  not-accessible
    STATUS      current
    DESCRIPTION
        "Information about action to be taken for a specific destination
        when a return value within the range specified between
        tFilterRedirectURLLowRespCode and tFilterRedirectURLHighRespCode
        is received."
    INDEX {
              tFilterRedirectPolicy,
              tFilterRedirectDest,
              tFilterRedirectURLTest,
              tFilterRedirectURLLowRespCode,
              tFilterRedirectURLHighRespCode
          }
    ::= { tFilterRedirectURLRespTable 1 }

TFilterRedirectURLRespEntry ::= SEQUENCE
    {
        tFilterRedirectURLLowRespCode  Unsigned32,
        tFilterRedirectURLHighRespCode Unsigned32,
        tFilterRUTRespRowStatus        RowStatus,
        tFilterRUTRespAction           INTEGER,
        tFilterRUTRespPrioChange       Unsigned32
    }

tFilterRedirectURLLowRespCode OBJECT-TYPE
    SYNTAX      Unsigned32
    MAX-ACCESS  not-accessible
    STATUS      current
    DESCRIPTION
        "tFilterRedirectURLLowRespCode specifies the lower return
        code of the range specified by this entry."
    ::= { tFilterRedirectURLRespEntry 1 }

tFilterRedirectURLHighRespCode OBJECT-TYPE
    SYNTAX      Unsigned32
    MAX-ACCESS  not-accessible
    STATUS      current
    DESCRIPTION
        "tFilterRedirectURLHighRespCode specifies the higher return
        code of the range specified by this entry."
    ::= { tFilterRedirectURLRespEntry 2 }

tFilterRUTRespRowStatus OBJECT-TYPE
    SYNTAX      RowStatus
    MAX-ACCESS  read-create
    STATUS      current
    DESCRIPTION
        "tFilterRUTRespRowStatus allows the mapping of a range of
        return codes returned from a specific test to the change it
        will cause to the priority of the destination."
    ::= { tFilterRedirectURLRespEntry 3 }

tFilterRUTRespAction OBJECT-TYPE
    SYNTAX      INTEGER {
                     increase (1),
                     decrease (2),
                     disable  (3)
                     }
    MAX-ACCESS  read-create
    STATUS      current
    DESCRIPTION
        "If the tFilterRUTRespAction is either 'increase(1)' or 'decrease(2)'
        tFilterRUTRespPrioChange specifies the offset to be applied to the
        destination base priority (tFilterRDAdminPriority) in order to
        compute the tFilterRDOperPriority as a result of this test.

        If the tFilterRUTRespAction is set to 'disable(3)', on the reception
        of the specified response, the destination will be deemed
        unusable and the tFilterRDOperPriority will be set to '0'.

        The value of tFilterRUTRespAction will be forced by the system to the
        value 'disable(3)' if the tFilterRUTRespPrioChange has the value '0'.
        Any change attempts will be silently discarded in this case."
    DEFVAL { disable }
    ::= { tFilterRedirectURLRespEntry 4 }

tFilterRUTRespPrioChange OBJECT-TYPE
    SYNTAX      Unsigned32 (0..255)
    MAX-ACCESS  read-create
    STATUS      current
    DESCRIPTION
        "tFilterRUTRespPrioChange specifies the amount of change
        to be made to the priority of the destination if the
        tFilterRUTRespAction is either 'increase' or 'decrease'.

        If tFilterRUTRespAction is 'disable', tFilterRUTRespPrioChange will
        be forced to 0. Any change to tFilterRUTRespPrioChange will be
        silently discarded in this case.

        Setting the object tFilterRUTRespPrioChange to 0 will cause the value of
        tFilterRUTRespAction to be set to 'disable'."
    DEFVAL { 0 }
    ::= { tFilterRedirectURLRespEntry 5 }

--
-- Filter Redirect Ping Test Table
--

tFilterRedirectPingTestTable OBJECT-TYPE
    SYNTAX      SEQUENCE OF TFilterRedirectPingTestEntry
    MAX-ACCESS  not-accessible
    STATUS      current
    DESCRIPTION
        "Contains a List of all redirect Ping tests configured on this
        system."
    ::= { tFilterObjects 16 }

tFilterRedirectPingTestEntry OBJECT-TYPE
    SYNTAX      TFilterRedirectPingTestEntry
    MAX-ACCESS  not-accessible
    STATUS      current
    DESCRIPTION
        "Information about a specific Ping test configured for a destination.
        Entries are created/deleted  by user. Entries have a presumed
        StorageType of nonVolatile."
    INDEX {
              tFilterRedirectPolicy,
              tFilterRedirectDest
          }
    ::= { tFilterRedirectPingTestTable 1 }

TFilterRedirectPingTestEntry ::= SEQUENCE
    {
        tFilterRPTRowStatus       RowStatus,
        tFilterRPTInterval        Unsigned32,
        tFilterRPTTimeout         Unsigned32,
        tFilterRPTDropCount       Unsigned32,
        tFilterRPTHoldDown        Unsigned32,
        tFilterRPTHoldDownRemain  Unsigned32,
        tFilterRPTLastActionTime  TimeStamp,
        tFilterRPTLastAction      INTEGER
    }

tFilterRPTRowStatus OBJECT-TYPE
    SYNTAX      RowStatus
    MAX-ACCESS  read-create
    STATUS      current
    DESCRIPTION
        "This object allows tests to be created and deleted in the
         tFilterRedirectPingTestTable."
    ::= { tFilterRedirectPingTestEntry 1 }

tFilterRPTInterval OBJECT-TYPE
    SYNTAX      Unsigned32 (1..60)
    UNITS        "seconds"
    MAX-ACCESS  read-create
    STATUS      current
    DESCRIPTION
        "The value of tFilterRPTInterval specifies the amount of time
        in seconds between consecutive requests sent to the far end
        host.

        Note that the value of tFilterRPTInterval can only be modified if the
        value of the corresponding tFilterRPAdminState and/or
        tFilterRDAdminState object is outOfService."
    DEFVAL { 1 }
    ::= { tFilterRedirectPingTestEntry 2 }

tFilterRPTTimeout OBJECT-TYPE
    SYNTAX      Unsigned32 (1..60)
    UNITS        "seconds"
    MAX-ACCESS  read-create
    STATUS      current
    DESCRIPTION
        "The value of tFilterRPTTimeout specifies the amount of time
        in seconds that is allowed for receiving a response from the
        far end host. If a reply is not received within this time the
        far end host is considered unresponsive.

        Note that the value of tFilterRPTTimeout can only be modified if the
        value of the corresponding tFilterRPAdminState and/or
        tFilterRDAdminState object is outOfService."
    DEFVAL { 1 }
    ::= { tFilterRedirectPingTestEntry 3 }

tFilterRPTDropCount OBJECT-TYPE
    SYNTAX      Unsigned32 (1..60)
    MAX-ACCESS  read-create
    STATUS      current
    DESCRIPTION
        "The value of tFilterRPTDropCount specifies the number of
        consecutive requests that must fail for the destination to
        declared unreachable."
    DEFVAL { 3 }
    ::= { tFilterRedirectPingTestEntry 4 }

tFilterRPTHoldDown OBJECT-TYPE
    SYNTAX      Unsigned32 (0..86400)
    UNITS        "seconds"
    MAX-ACCESS  read-create
    STATUS      current
    DESCRIPTION
        "The value of tFilterRPTHoldDown specifies the amount of time
        in seconds that the system should be held down if any of the test
        has marked it unreachable."
    DEFVAL { 0 }
    ::= { tFilterRedirectPingTestEntry 5 }

tFilterRPTHoldDownRemain OBJECT-TYPE
    SYNTAX      Unsigned32 (0..86400)
    UNITS        "seconds"
    MAX-ACCESS  read-only
    STATUS      current
    DESCRIPTION
        "The value of tFilterRPTHoldDownRemain indicates the amount of time
        in seconds that the system will remain in held down state before
        being used again."
    ::= { tFilterRedirectPingTestEntry 6 }

tFilterRPTLastActionTime OBJECT-TYPE
    SYNTAX      TimeStamp
    MAX-ACCESS  read-only
    STATUS      current
    DESCRIPTION
        "tFilterRPTLastActionTime maintains the time stamp when this test
        received a response for a probe sent out."
    ::= { tFilterRedirectPingTestEntry 7 }

tFilterRPTLastAction OBJECT-TYPE
    SYNTAX      INTEGER {
                     enable (1),
                     disable (2),
                     none (3)
                 }
    MAX-ACCESS  read-only
    STATUS      current
    DESCRIPTION
        "tFilterRPTLastAction maintains impact that the last test probe
        made on the operational status of the destination as maintained
        in tFilterRDOperState.

        If the last action was 'disable', the destination may not be
        used for tFilterRPTHoldDown seconds."
    ::= { tFilterRedirectPingTestEntry 8 }


--
-- Auto IP Filter Entries
--

tAutoIPFilterEntryTable OBJECT-TYPE
    SYNTAX      SEQUENCE OF TAutoIPFilterEntry
    MAX-ACCESS  not-accessible
    STATUS      obsolete
    DESCRIPTION
        "Defines the Alcatel-Lucent SROS series automatic IP filters
         for providing, via SNMP, the capability of gathering
         information regarding the same.

         tAutoIPFilterEntryTable holds a list of all automatic
         filter entries being used for filtering.

         This table is obsoleted in release 3.0."
    ::= { tFilterObjects 17 }

tAutoIPFilterEntry OBJECT-TYPE
    SYNTAX      TAutoIPFilterEntry
    MAX-ACCESS  not-accessible
    STATUS      obsolete
    DESCRIPTION
        "Defines an entry in the tAutoIPFilterEntryTable.

         Entries are created and deleted in this table by the
         system.

         Each entry provides information about a single active
         automatic filter entry.

         This entry is obsoleted in release 3.0."
    INDEX { tAutoIPFilterId, tAutoIPFilterEntrySourceIpAddr }
    ::= { tAutoIPFilterEntryTable 1 }

TAutoIPFilterEntry ::= SEQUENCE
    {
        tAutoIPFilterId                   TFilterID,
        tAutoIPFilterEntrySourceIpAddr    IpAddress,
        tAutoIPFilterEntrySourceIpMask    IpAddressPrefixLength
    }

tAutoIPFilterId OBJECT-TYPE
    SYNTAX      TFilterID (1..65535)
    MAX-ACCESS  not-accessible
    STATUS      obsolete
    DESCRIPTION
        "tAutoIPFilterId serves as a primary index and uniquely
         identifies an application point such as a routed
         interface or a SAP.

         This object is obsoleted in release 3.0."
    ::= { tAutoIPFilterEntry 1 }

tAutoIPFilterEntrySourceIpAddr OBJECT-TYPE
    SYNTAX      IpAddress
    MAX-ACCESS  not-accessible
    STATUS      obsolete
    DESCRIPTION
        "tAutoIPFilterEntrySourceIpAddr specifies the source
         ip-address and also serves as the secondary index to
         this table.

         This object is obsoleted in release 3.0."
    ::= { tAutoIPFilterEntry 2 }

tAutoIPFilterEntrySourceIpMask OBJECT-TYPE
    SYNTAX      IpAddressPrefixLength
    MAX-ACCESS  read-only
    STATUS      obsolete
    DESCRIPTION
        "The value of tAutoIPFilterEntrySourceIpMask indicates the number
         of bits to be matched in the source ip-address.

         This object is obsoleted in release 3.0."
    ::= { tAutoIPFilterEntry 3 }

--
-- Filter Domain Time Stamp
--

tFilterDomainLastChanged OBJECT-TYPE
    SYNTAX      TimeStamp
    MAX-ACCESS  read-only
    STATUS      current
    DESCRIPTION
        "timestamp of last change to tFilterObjects."
    ::= { tFilterTimeStampObjects 1 }

--
-- IPv6 Filter Table
--

tIPv6FilterTable OBJECT-TYPE
    SYNTAX      SEQUENCE OF TIPv6FilterEntry
    MAX-ACCESS  not-accessible
    STATUS      current
    DESCRIPTION
        "Contains a List of all IPv6 filters configured on this system."
    ::= { tFilterObjects 18 }

tIPv6FilterEntry OBJECT-TYPE
    SYNTAX      TIPv6FilterEntry
    MAX-ACCESS  not-accessible
    STATUS      current
    DESCRIPTION
        "Information about a particular IPv6 Filter entry. Entries are
         created/deleted  by user. Entries have a presumed StorageType of
         nonVolatile."
    INDEX { tIPv6FilterId }
    ::= { tIPv6FilterTable 1 }

TIPv6FilterEntry ::= SEQUENCE
    {
        tIPv6FilterId                    TAnyFilterID,
        tIPv6FilterRowStatus             RowStatus,
        tIPv6FilterScope                 TFilterScope,
        tIPv6FilterDescription           TItemDescription,
        tIPv6FilterDefaultAction         TFilterAction,
        tIPv6FilterRadiusInsertPt        TEntryIdOrZero,
        tIPv6FilterRadiusInsertSize      TEntryIdOrZero,
        tIPv6FilterCreditCntrlInsertPt   TEntryIdOrZero,
        tIPv6FilterCreditCntrlInsertSize TEntryIdOrZero,
        tIPv6FilterSubInsertHighWmark    Integer32,
        tIPv6FilterSubInsertLowWmark     Integer32,
        tIpv6FilterCreditCntrlNbrInsertd Unsigned32,
        tIpv6FilterRadiusNbrInsertd      Unsigned32,
        tIpv6FilterName                  TLNamedItemOrEmpty,
        tIPv6FilterHostSharedInsertPt    TEntryIdOrZero,
        tIPv6FilterHostSharedInsertSize  TEntryIdOrZero,
        tIpv6FilterHostSharedNbrInsertd  Unsigned32,
        tIPv6FilterHostSharedHighWmark   Integer32,
        tIPv6FilterHostSharedLowWmark    Integer32,
        tIPv6FilterNbrHostSharedFltrs    Unsigned32
    }

tIPv6FilterId OBJECT-TYPE
    SYNTAX      TAnyFilterID
    MAX-ACCESS  not-accessible
    STATUS      current
    DESCRIPTION
        "The value of the object tIPv6FilterId uniquely identifies a
         IPv6 filter on this system.
         Refer to the description of the textual convention TAnyFilterID
         for more info on which numbers are available for the user."
    ::= { tIPv6FilterEntry 1 }

tIPv6FilterRowStatus OBJECT-TYPE
    SYNTAX      RowStatus
    MAX-ACCESS  read-create
    STATUS      current
    DESCRIPTION
        "The value of the object tIPv6FilterRowStatus specifies
         the status of the IPv6 filter. The object allows
         entries to be created and deleted in the tIPv6FilterTable."
    ::= { tIPv6FilterEntry 2 }

tIPv6FilterScope OBJECT-TYPE
    SYNTAX      TFilterScope
    MAX-ACCESS  read-create
    STATUS      current
    DESCRIPTION
        "The value of the object tIPv6FilterScope specifies the
         scope of this filter definition."
    DEFVAL { template }
    ::= { tIPv6FilterEntry 3 }

tIPv6FilterDescription OBJECT-TYPE
    SYNTAX      TItemDescription
    MAX-ACCESS  read-create
    STATUS      current
    DESCRIPTION
        "The value of the object tIPv6FilterDescription specifies
         a user-provided description for this filter."
    DEFVAL { ''H }
    ::= { tIPv6FilterEntry 4 }

tIPv6FilterDefaultAction OBJECT-TYPE
    SYNTAX      TFilterAction
    MAX-ACCESS  read-create
    STATUS      current
    DESCRIPTION
        "The value of the object tIPv6FilterDefaultAction specifies
         the action to be taken for packets that do not match any
         of the filter entries.
         The only allowed values for this field are drop(1) and forward(2)."
    DEFVAL { drop }
    ::= { tIPv6FilterEntry 5 }

tIPv6FilterRadiusInsertPt OBJECT-TYPE
    SYNTAX      TEntryIdOrZero
    MAX-ACCESS  read-create
    STATUS      current
    DESCRIPTION
        "The value of tIPv6FilterRadiusInsertPt specifies at what place the
         host specific filter entries received from Radius will be inserted
         in the filter.
        
         The area defined here will be dedicated to those entries, no other
         entries will be allowed.
        
         The value 0 means that no Radius provided host specific filter
         entries can be inserted in the filter.
        
         If tIPv6FilterRadiusInsertSize is set to 0, then this object
         will be put to 0 as well. Any change attempts will be
         silently discarded in this case."
    DEFVAL { 0 }
    ::= { tIPv6FilterEntry 6 }

tIPv6FilterRadiusInsertSize OBJECT-TYPE
    SYNTAX      TEntryIdOrZero
    MAX-ACCESS  read-create
    STATUS      current
    DESCRIPTION
        "The value of tIPv6FilterRadiusInsertSize specifies how many
         host specific filter entries received from Radius for subscriber
         hosts can be inserted in the filter.
        
         If tIPv6FilterRadiusInsertPt is set to 0, then this object
         will be put to 0 as well. Any change attempts will be
         silently discarded in this case."
    DEFVAL { 0 }
    ::= { tIPv6FilterEntry 7 }

tIPv6FilterCreditCntrlInsertPt OBJECT-TYPE
    SYNTAX      TEntryIdOrZero
    MAX-ACCESS  read-create
    STATUS      current
    DESCRIPTION
        "The value of tIPv6FilterCreditCntrlInsertPt specifies at what place
         the filter entries received from Credit Control for a
         particular subscriber host will be inserted in the filter.

         The area defined here will be dedicated to those entries, no other
         entries will be allowed.

         The value 0 means that no Credit Control provided filter entries
         can be inserted in the filter.

         If tIPv6FilterCreditCntrlInsertSize is set to 0, then this object
         will be put to 0 as well. Any change attempts will be
         silently discarded in this case."
    DEFVAL { 0 }
    ::= { tIPv6FilterEntry 8 }

tIPv6FilterCreditCntrlInsertSize OBJECT-TYPE
    SYNTAX      TEntryIdOrZero
    MAX-ACCESS  read-create
    STATUS      current
    DESCRIPTION
        "The value of tIPv6FilterCreditCntrlInsertSize specifies how many
         filter entries received from Credit Control can be inserted in the
         filter.

         If tIPv6FilterCreditCntrlInsertPt is set to 0, then this object
         will be put to 0 as well. Any change attempts will be
         silently discarded in this case."
    DEFVAL { 0 }
    ::= { tIPv6FilterEntry 9 }

tIPv6FilterSubInsertHighWmark OBJECT-TYPE
    SYNTAX      Integer32 (0..100)
    MAX-ACCESS  read-create
    STATUS      current
    DESCRIPTION
        "The value of the object tIPv6FilterSubInsertHighWmark
         specifies the utilization of the filter ranges for filter
         entry insertion, at which a table full alarm will be raised
         by the agent.
         The value 0 indicates that no alarm will be generated."
    DEFVAL { 95 }
    ::= { tIPv6FilterEntry 10 }

tIPv6FilterSubInsertLowWmark OBJECT-TYPE
    SYNTAX      Integer32 (0..100)
    MAX-ACCESS  read-create
    STATUS      current
    DESCRIPTION
        "The value of the object tIPv6FilterSubInsertLowWmark
         specifies the utilization of the filter ranges for filter
         entry insertion, at which a table full alarm will be cleared
         by the agent."
    DEFVAL { 90 }
    ::= { tIPv6FilterEntry 11 }

tIpv6FilterCreditCntrlNbrInsertd OBJECT-TYPE
    SYNTAX      Unsigned32
    MAX-ACCESS  read-only
    STATUS      current
    DESCRIPTION
        "The value of the object tIpv6FilterCreditCntrlNbrInsertd
         indicates how many filter entries are currently inserted
         in the filter on request of credit control."
    ::= { tIPv6FilterEntry 12 }

tIpv6FilterRadiusNbrInsertd OBJECT-TYPE
    SYNTAX      Unsigned32
    MAX-ACCESS  read-only
    STATUS      current
    DESCRIPTION
        "The value of the object tIpv6FilterRadiusNbrInsertd
         indicates how many host specific filter entries are
         currently inserted in the filter on request of RADIUS."
    ::= { tIPv6FilterEntry 13 }

tIpv6FilterName OBJECT-TYPE
    SYNTAX      TLNamedItemOrEmpty
    MAX-ACCESS  read-create
    STATUS      current
    DESCRIPTION
        "The value of tIpv6FilterName specifies the name to associate
        with this filter."
    DEFVAL { ''H }
    ::= { tIPv6FilterEntry 14 }

tIPv6FilterHostSharedInsertPt OBJECT-TYPE
SYNTAX      TEntryIdOrZero
MAX-ACCESS  read-create
STATUS      current
DESCRIPTION
    "The value of tIPv6FilterHostSharedInsertPt specifies at what place the
     filter entries received from Radius that are shared between several
     hosts (host common rules) will be inserted in the filter.

     The area defined here will be dedicated to those entries, no other
     entries will be allowed.

     The value 0 means that no Radius provided host common filter entries
     can be inserted in the filter.

     If tIPv6FilterHostSharedInsertSize is set to 0, then this object
     will be put to 0 as well. Any change attempts will be
     silently discarded in this case."
DEFVAL { 0 }
::= { tIPv6FilterEntry 15 }

tIPv6FilterHostSharedInsertSize OBJECT-TYPE
SYNTAX      TEntryIdOrZero
MAX-ACCESS  read-create
STATUS      current
DESCRIPTION
    "The value of tIPv6FilterHostSharedInsertSize specifies how many
     host common filter entries received from Radius for subscriber hosts
     can be inserted in the filter.

     If tIPv6FilterHostSharedInsertPt is set to 0, then this object
     will be put to 0 as well. Any change attempts will be
     silently discarded in this case."
DEFVAL { 0 }
::= { tIPv6FilterEntry 16 }

tIpv6FilterHostSharedNbrInsertd OBJECT-TYPE
    SYNTAX      Unsigned32
    MAX-ACCESS  read-only
    STATUS      current
    DESCRIPTION
        "The value of the object tIpv6FilterHostSharedNbrInsertd
         indicates how many host common filter entries are currently
         inserted in the filter on request of Radius."
    ::= { tIPv6FilterEntry 17 }

tIPv6FilterHostSharedHighWmark OBJECT-TYPE
    SYNTAX      Integer32 (-1 | 1..8000)
    MAX-ACCESS  read-create
    STATUS      current
    DESCRIPTION
        "The value of the object tIPv6FilterHostSharedHighWmark
         specifies the number of Radius Shared Filters that can be 
         dynamically created in the system before an high watermark
         notification is generated by the system.
         The value -1 specifies that no notifications are sent.
         If any of the watermarks (high or low) is set to -1, both
         watermarks will be set to -1 by the system."
    DEFVAL { -1 }
    ::= { tIPv6FilterEntry 18 }

tIPv6FilterHostSharedLowWmark OBJECT-TYPE
    SYNTAX      Integer32  (-1 | 0..8000)
    MAX-ACCESS  read-create
    STATUS      current
    DESCRIPTION
        "The value of the object tIPv6FilterHostSharedLowWmark
         specifies the number of Radius Shared Filters that are still
         dynamically created in the system before an high watermark
         notification is cleared by the system.
         The value -1 specifies that no notifications are sent.
         If any of the watermarks (high or low) is set to -1, both
         watermarks will be set to -1 by the system."
    DEFVAL { -1 }
    ::= { tIPv6FilterEntry 19 }

tIPv6FilterNbrHostSharedFltrs OBJECT-TYPE
    SYNTAX      Unsigned32
    MAX-ACCESS  read-only
    STATUS      current
    DESCRIPTION
        "The value of the object tIPv6FilterNbrHostSharedFltrs
         indicates how many Radius Shared Filters are currently
         created based on this filter."
    ::= { tIPv6FilterEntry 20 }

--
-- IPv6 Filter Entry parameters
--

tIPv6FilterParamsTable OBJECT-TYPE
    SYNTAX      SEQUENCE OF TIPv6FilterParamsEntry
    MAX-ACCESS  not-accessible
    STATUS      current
    DESCRIPTION  "A table of all IPv6 filter match entries for all IPv6 filters"
    ::= { tFilterObjects 19 }

tIPv6FilterParamsEntry OBJECT-TYPE
    SYNTAX      TIPv6FilterParamsEntry
    MAX-ACCESS  not-accessible
    STATUS      current
    DESCRIPTION
        "Information about a particular IPv6 Filter entry.
         Every IPv6 Filter can have zero or more IPv6 Filter match entries.

         A filter entry with no match criteria set will match every
         packet, and the entry action will be taken.

         Entries are created/deleted by user.

         Additional match criteria can be found in tIPv6FilterParamsExtTable.
         
         There is no StorageType object, entries have a presumed
         StorageType of nonVolatile."
    INDEX { tIPv6FilterId, tIPv6FilterParamsIndex }
    ::= { tIPv6FilterParamsTable 1 }

TIPv6FilterParamsEntry ::= SEQUENCE
    {
        tIPv6FilterParamsIndex               TAnyEntryId,
        tIPv6FilterParamsRowStatus           RowStatus,
        tIPv6FilterParamsLogId               TFilterLogId,
        tIPv6FilterParamsDescription         TItemDescription,
        tIPv6FilterParamsAction              TFilterActionOrDefault,
        tIPv6FilterParamsForwardNH           InetAddressIPv6,
        tIPv6FilterParamsForwardNHIndirect   TruthValue,
        tIPv6FilterParamsRemarkDSCP          TDSCPFilterActionValue,
        tIPv6FilterParamsRemarkDSCPMask      TDSCPFilterActionValue,
        tIPv6FilterParamsRemarkDot1p         Dot1PPriority,
        tIPv6FilterParamsSourceIpAddr        InetAddressIPv6,
        tIPv6FilterParamsSourceIpMask        InetAddressPrefixLength,
        tIPv6FilterParamsDestinationIpAddr   InetAddressIPv6,
        tIPv6FilterParamsDestinationIpMask   InetAddressPrefixLength,
        tIPv6FilterParamsNextHeader          TIpProtocol,
        tIPv6FilterParamsSourcePortValue1    TTcpUdpPort,
        tIPv6FilterParamsSourcePortValue2    TTcpUdpPort,
        tIPv6FilterParamsSourcePortOperator  TTcpUdpPortOperator,
        tIPv6FilterParamsDestPortValue1      TTcpUdpPort,
        tIPv6FilterParamsDestPortValue2      TTcpUdpPort,
        tIPv6FilterParamsDestPortOperator    TTcpUdpPortOperator,
        tIPv6FilterParamsDSCP                TDSCPNameOrEmpty,
        tIPv6FilterParamsTcpSyn              TItemMatch,
        tIPv6FilterParamsTcpAck              TItemMatch,
        tIPv6FilterParamsIcmpCode            INTEGER,
        tIPv6FilterParamsIcmpType            INTEGER,
        tIPv6FilterParamsCflowdSample        TruthValue,
        tIPv6FilterParamsCflowdIfSample      TruthValue,
        tIPv6FilterParamsForwardNHInterface  DisplayString,
        tIPv6FilterParamsIngressHitCount     Counter64,
        tIPv6FilterParamsEgressHitCount      Counter64,
        tIPv6FilterParamsLogInstantiated     TruthValue,
        tIPv6FilterParamsForwardRedPlcy      TNamedItemOrEmpty,
        tIPv6FilterParamsActiveDest          InetAddressIPv6,
        tIPv6FilterParamsTimeRangeName       TNamedItemOrEmpty,
        tIPv6FilterParamsTimeRangeState      TTimeRangeState,
        tIPv6FilterParamsIngrHitByteCount    Counter64,
        tIPv6FilterParamsEgrHitByteCount     Counter64,
        tIPv6FilterParamsFwdSvcId            TmnxServId,
        tIPv6FilterParamsFwdSapPortId        TmnxPortID,
        tIPv6FilterParamsFwdSapEncapVal      TmnxEncapVal,
        tIPv6FilterParamsFwdSdpBind          SdpBindId,
        tIPv6FilterParamsRedirectURL         TmnxHttpRedirectUrl,
        tIPv6FilterParamsSrcIpPrefixList     TNamedItemOrEmpty,
        tIPv6FilterParamsDstIpPrefixList     TNamedItemOrEmpty,
        tIPv6FilterParamsFragment            INTEGER,
        tIPv6FilterParamsHopByHopOpt         TItemMatch,
        tIPv6FilterParamsRoutingType0        TItemMatch,
        tIPv6FilterParamsPortSelector        TFltrPortSelector,
        tIPv6FilterParamsSrcPortList         TNamedItemOrEmpty,
        tIPv6FilterParamsDstPortList         TNamedItemOrEmpty,
        tIPv6FilterParamsRdirAllwRadOvrd     TruthValue,
        tIPv6FilterParamsFwdRtrId            TmnxVRtrIDOrZero,
        tIPv6FilterParamsSrcIpFullMask       InetAddressIPv6,
        tIPv6FilterParamsDstIpFullMask       InetAddressIPv6,
        tIPv6FilterParamsNatPolicyName       TNamedItemOrEmpty,
        tIPv6FilterParamsFlowLabel           IPv6FlowLabel,
        tIPv6FilterParamsFlowLabelMask       IPv6FlowLabelMask,
        tIPv6FilterParamsFwdLsp              TmnxVRtrMplsLspID,
        tIPv6FilterParamsFwdLspRtrId         TmnxVRtrIDOrZero
    }

tIPv6FilterParamsIndex OBJECT-TYPE
    SYNTAX      TAnyEntryId
    MAX-ACCESS  not-accessible
    STATUS      current
    DESCRIPTION
        "This is the secondary index for the entry. Every IPv6 filter can have
         multiple entries, therefore every IPv6 filter entry is identified by
         the tIPv6FilterId and tIPv6FilterParamsIndex.
         
         Refer to the description of the textual convention TAnyEntryId for more
         info on the allowed values for this object."
    ::= { tIPv6FilterParamsEntry 1 }

tIPv6FilterParamsRowStatus OBJECT-TYPE
    SYNTAX      RowStatus
    MAX-ACCESS  read-create
    STATUS      current
    DESCRIPTION
        "This object allows entries to be created and deleted in the
         tIPv6FilterParamsTable."
    ::= { tIPv6FilterParamsEntry 2 }

tIPv6FilterParamsLogId OBJECT-TYPE
    SYNTAX      TFilterLogId
    MAX-ACCESS  read-create
    STATUS      current
    DESCRIPTION
        "This object specifies the log to use for packets that match
         this entry. The value zero indicates that logging is disabled."
    DEFVAL { 0 }
    ::= { tIPv6FilterParamsEntry 3 }

tIPv6FilterParamsDescription OBJECT-TYPE
    SYNTAX      TItemDescription
    MAX-ACCESS  read-create
    STATUS      current
    DESCRIPTION
        "User-provided description for this filter entry."
    DEFVAL { ''H }
    ::= { tIPv6FilterParamsEntry 4 }

tIPv6FilterParamsAction OBJECT-TYPE
    SYNTAX      TFilterActionOrDefault
    MAX-ACCESS  read-create
    STATUS      current
    DESCRIPTION
        "The action to take for packets that match this filter entry. The value
         default(3) specifies this entry to inherit the behavior defined as the
         default for the filter.
         The following value(s) is(are) not supported:
            nat(5)
            reassemble(6)
        "
    DEFVAL { drop }
    ::= { tIPv6FilterParamsEntry 5 }

tIPv6FilterParamsForwardNH OBJECT-TYPE
    SYNTAX      InetAddressIPv6
    MAX-ACCESS  read-create
    STATUS      current
    DESCRIPTION
        "The ipv6-address of the nexthop to which the packet should be forwarded
         if it hits this filter entry. The action of this entry should be
         'forward' in such a case.

         Note that the value of tIPv6FilterParamsForwardNH  is silently cleared
         by the system if tIPv6FilterParamsAction is set to httpRedirect."
    DEFVAL { '00000000000000000000000000000000'H }
    ::= { tIPv6FilterParamsEntry 6 }

tIPv6FilterParamsForwardNHIndirect OBJECT-TYPE
    SYNTAX      TruthValue
    MAX-ACCESS  read-create
    STATUS      current
    DESCRIPTION
        "tIPv6FilterParamsForwardNHIndirect specifies if the nexthop is
         directly or indirectly reachable.

         Note that the value of tIPv6FilterParamsForwardNHIndirect is silently
         cleared by the system if tIPv6FilterParamsAction is set to
         httpRedirect."
    DEFVAL { false }
    ::= { tIPv6FilterParamsEntry 7 }

tIPv6FilterParamsRemarkDSCP OBJECT-TYPE
    SYNTAX      TDSCPFilterActionValue
    MAX-ACCESS  read-create
    STATUS      current
    DESCRIPTION
        "The DSCP value that should be remarked in case a packet hits this
         filter entry."
    DEFVAL { -1 }
    ::= { tIPv6FilterParamsEntry 8 }

tIPv6FilterParamsRemarkDSCPMask OBJECT-TYPE
    SYNTAX      TDSCPFilterActionValue
    MAX-ACCESS  read-create
    STATUS      current
    DESCRIPTION
        "tIPv6FilterParamsRemarkDSCPMask specifies the care bits while remarking
         with the DSCP value."
    DEFVAL { 255 }
    ::= { tIPv6FilterParamsEntry 9 }

tIPv6FilterParamsRemarkDot1p OBJECT-TYPE
    SYNTAX      Dot1PPriority
    MAX-ACCESS  read-create
    STATUS      current
    DESCRIPTION
        "tIPv6FilterParamsRemarkDot1p specifies the Dot1p value that needs to be
         remarked on the packet if it hits this filter entry."
    DEFVAL { -1 }
    ::= { tIPv6FilterParamsEntry 10 }

tIPv6FilterParamsSourceIpAddr OBJECT-TYPE
    SYNTAX      InetAddressIPv6
    MAX-ACCESS  read-create
    STATUS      current
    DESCRIPTION
        "IPv6 address to match the source-ip of the packet."
    DEFVAL { '00000000000000000000000000000000'H }
    ::= { tIPv6FilterParamsEntry 11 }

tIPv6FilterParamsSourceIpMask OBJECT-TYPE
    SYNTAX      InetAddressPrefixLength (0..128)
    MAX-ACCESS  read-create
    STATUS      current
    DESCRIPTION
        "If different from 0, the object tIPv6FilterParamsSourceIpMask
         specifies the IPv6 prefix length value for this policy IPv6 Filter 
         entry.
         The mask generated from the prefix length value is ANDed with 
         the received source IPv6 address to match 
         the tIPv6FilterParamsSourceIpAddr.

         If the value of tIPv6FilterParamsSourceIpMask is 0, 
         and the value of tIPv6FilterParamsSrcIpFullMask is non zero 
         then the value of tIPv6FilterParamsSrcIpFullMask is used as a mask.

         If the value of tIPv6FilterParamsSourceIpMask is non zero,
         it will be equal to the mask expressed in the object
         tIPv6FilterParamsSrcIpFullMask.

         If both tIPv6FilterParamsSourceIpMask and
         tIPv6FilterParamsSrcIpFullMask are set to 0, no matching is done
         on the source IPv6 address.

         If a value is specified for this object, then the value of the
         object tIPv6FilterParamsSrcIpFullMask will be set to reflect
         this same mask."
    DEFVAL { 0 }
    ::= { tIPv6FilterParamsEntry 12 }

tIPv6FilterParamsDestinationIpAddr OBJECT-TYPE
    SYNTAX      InetAddressIPv6
    MAX-ACCESS  read-create
    STATUS      current
    DESCRIPTION
        "IPv6 address to match the destination-ip of the packet."
    DEFVAL { '00000000000000000000000000000000'H }
    ::= { tIPv6FilterParamsEntry 13 }

tIPv6FilterParamsDestinationIpMask OBJECT-TYPE
    SYNTAX      InetAddressPrefixLength (0..128)
    MAX-ACCESS  read-create
    STATUS      current
    DESCRIPTION
        "If different from 0, the object tIPv6FilterParamsDestinationIpMask
         specifies the IPv6 prefix length value for this policy IPv6 Filter 
         entry.
         The mask generated from the prefix length value is ANDed with 
         the received destination IPv6 address to match
         the tIPv6FilterParamsDestinationIpAddr.

         If the value of tIPv6FilterParamsDestinationIpMask is 0, 
         and the value of tIPv6FilterParamsDstIpFullMask is non zero 
         then the value of tIPv6FilterParamsDstIpFullMask is used as a mask.

         If the value of tIPv6FilterParamsDestinationIpMask is non zero,
         it will be equal to the mask expressed in the object
         tIPv6FilterParamsDstIpFullMask.

         If both tIPv6FilterParamsDestinationIpMask and
         tIPv6FilterParamsDstIpFullMask are set to 0, no matching is done
         on the destination IPv6 address.

         If a value is specified for this object, then the value of the
         object tIPv6FilterParamsDstIpFullMask will be set to reflect
         this same mask."
    DEFVAL { 0 }
    ::= { tIPv6FilterParamsEntry 14 }

tIPv6FilterParamsNextHeader OBJECT-TYPE
    SYNTAX      TIpProtocol
    MAX-ACCESS  read-create
    STATUS      current
    DESCRIPTION
        "IPv6 next header to match.  set to -1 to disable matching IPv6 next
         header. If the next header is changed the next header specific
         parameters are reset. For instance if next header is changed from TCP
         to UDP, then the objects tIPv6FilterParamsTcpSyn and
         tIPv6FilterParamsTcpAck will be turned off.
         Because the match criteria only pertains to the last next-header, the
         following values are not accepted: 0, 43, 44, 50, 51, and 60."
    DEFVAL { -1 }
    ::= { tIPv6FilterParamsEntry 15 }

tIPv6FilterParamsSourcePortValue1 OBJECT-TYPE
    SYNTAX      TTcpUdpPort
    MAX-ACCESS  read-create
    STATUS      current
    DESCRIPTION
        "TCP/UDP port value1. The value of this object is used as per the
         description for tIPv6FilterParamsSourcePortOperator."
    DEFVAL { 0 }
    ::= { tIPv6FilterParamsEntry 16 }

tIPv6FilterParamsSourcePortValue2 OBJECT-TYPE
    SYNTAX      TTcpUdpPort
    MAX-ACCESS  read-create
    STATUS      current
    DESCRIPTION
        "TCP/UDP port value2. The value of this object is used as per the
         description for tIPv6FilterParamsSourcePortOperator."
    DEFVAL { 0 }
    ::= { tIPv6FilterParamsEntry 17 }

tIPv6FilterParamsSourcePortOperator OBJECT-TYPE
    SYNTAX      TTcpUdpPortOperator
    MAX-ACCESS  read-create
    STATUS      current
    DESCRIPTION
        "The operator specifies the manner in which
         tIPFilterParamsSourcePortValue1 and tIPFilterParamsSourcePortValue2
         are to be used."
    DEFVAL { none }
    ::= { tIPv6FilterParamsEntry 18 }

tIPv6FilterParamsDestPortValue1 OBJECT-TYPE
    SYNTAX      TTcpUdpPort
    MAX-ACCESS  read-create
    STATUS      current
    DESCRIPTION
        "TCP/UDP port value1. The value of this object is used as per the
         description for tIPv6FilterParamsDestPortOperator."
    DEFVAL { 0 }
    ::= { tIPv6FilterParamsEntry 19 }

tIPv6FilterParamsDestPortValue2 OBJECT-TYPE
    SYNTAX      TTcpUdpPort
    MAX-ACCESS  read-create
    STATUS      current
    DESCRIPTION
        "TCP/UDP port value2. The value of this object is used as per the
         description for tIPv6FilterParamsDestPortOperator."
    DEFVAL { 0 }
    ::= { tIPv6FilterParamsEntry 20 }

tIPv6FilterParamsDestPortOperator OBJECT-TYPE
    SYNTAX      TTcpUdpPortOperator
    MAX-ACCESS  read-create
    STATUS      current
    DESCRIPTION
        "The operator specifies the manner in which
         tIPFilterParamsDestPortValue1 and tIPFilterParamsDestPortValue2 are to
         be used."
    DEFVAL { none }
    ::= { tIPv6FilterParamsEntry 21 }

tIPv6FilterParamsDSCP OBJECT-TYPE
    SYNTAX      TDSCPNameOrEmpty
    MAX-ACCESS  read-create
    STATUS      current
    DESCRIPTION
        "DSCP to be matched on the packet."
    DEFVAL { ''H }
    ::= { tIPv6FilterParamsEntry 22 }

tIPv6FilterParamsTcpSyn OBJECT-TYPE
    SYNTAX      TItemMatch
    MAX-ACCESS  read-create
    STATUS      current
    DESCRIPTION
        "If Enabled, matches a TCP Syn as per value of the object."
    DEFVAL { off }
    ::= { tIPv6FilterParamsEntry 23 }

tIPv6FilterParamsTcpAck OBJECT-TYPE
    SYNTAX      TItemMatch
    MAX-ACCESS  read-create
    STATUS      current
    DESCRIPTION
        "If Enabled, matches a TCP Ack as per value of the object."
    DEFVAL { off }
    ::= { tIPv6FilterParamsEntry 24 }

tIPv6FilterParamsIcmpCode OBJECT-TYPE
    SYNTAX      INTEGER (-1|0..255)
    MAX-ACCESS  read-create
    STATUS      current
    DESCRIPTION
        "Icmp code to be matched. tIPv6FilterParamsIcmpCode complements the
         object tIPv6FilterParamsIcmpType. Both of them need to be set to
         actually enable ICMP matching. The value -1 means Icmp code matching
         is not enabled."
    DEFVAL { -1 }
    ::= { tIPv6FilterParamsEntry 25 }

tIPv6FilterParamsIcmpType OBJECT-TYPE
    SYNTAX      INTEGER (-1|0..255)
    MAX-ACCESS  read-create
    STATUS      current
    DESCRIPTION
        "Icmp type to be matched. tIPv6FilterParamsIcmpType complements the
         object tIPv6FilterParamsIcmpCode. Both of them need to be set to
         actually enable ICMP matching. The value -1 means Icmp type matching is
         not enabled."
    DEFVAL { -1 }
    ::= { tIPv6FilterParamsEntry 26 }

tIPv6FilterParamsCflowdSample OBJECT-TYPE
    SYNTAX      TruthValue
    MAX-ACCESS  read-create
    STATUS      current
    DESCRIPTION
        "When tIPFilterParamsCflowdSample has a value of 'true',  Cflowd
         sampling and analysis is performed on those packet streams where this
         filter has been applied.  Only packets matching this IPv6 filter entry
         are subjected to Cflowd sampling and analysis.  A Cflowd profile
         controls the sampling and analysis of data flows through the router."
    DEFVAL { false }
    ::= { tIPv6FilterParamsEntry 27 }

tIPv6FilterParamsCflowdIfSample OBJECT-TYPE
    SYNTAX      TruthValue
    MAX-ACCESS  read-create
    STATUS      current
    DESCRIPTION
        "When tIPv6FilterParamsCflowdIfSample has a value of 'true', Cflowd
         sampling and analysis is performed on those packet streams where this
         filter has been applied.  Only packets matching this IPv6 filter entry
         are subjected to Cflowd sampling and analysis.  A Cflowd profile
         controls the sampling and analysis of data flows through the router."
    DEFVAL { true }
    ::= { tIPv6FilterParamsEntry 28 }

tIPv6FilterParamsForwardNHInterface OBJECT-TYPE
    SYNTAX      DisplayString (SIZE(0..32))
    MAX-ACCESS  read-create
    STATUS      current
    DESCRIPTION
        "The interface name for the nexthop to which the packet should be
         forwarded if it hits this filter entry. The action of this entry
         should be 'forward' in such a case.

         Note that the value of tIPv6FilterParamsForwardNHInterface  is silently
         cleared by the system if tIPv6FilterParamsAction is set to
         httpRedirect."
    DEFVAL { ''H }
    ::= { tIPv6FilterParamsEntry 29 }

tIPv6FilterParamsIngressHitCount OBJECT-TYPE
    SYNTAX      Counter64
    MAX-ACCESS  read-only
    STATUS      current
    DESCRIPTION
        "This object indicates the number of times an ingress packet
         matched this entry."
    ::= { tIPv6FilterParamsEntry 30 }

tIPv6FilterParamsEgressHitCount OBJECT-TYPE
    SYNTAX      Counter64
    MAX-ACCESS  read-only
    STATUS      current
    DESCRIPTION
        "This object indicates the number of times an egress packet
         matched this entry."
    ::= { tIPv6FilterParamsEntry 31 }

tIPv6FilterParamsLogInstantiated OBJECT-TYPE
    SYNTAX      TruthValue
    MAX-ACCESS  read-only
    STATUS      current
    DESCRIPTION
        "tIPv6FilterParamsLogInstantiated indicates if the filter log for
         this filter entry has been instantiated or not."
    ::= { tIPv6FilterParamsEntry 32 }

tIPv6FilterParamsForwardRedPlcy OBJECT-TYPE
    SYNTAX      TNamedItemOrEmpty
    MAX-ACCESS  read-create
    STATUS      current
    DESCRIPTION
        "tIPv6FilterParamsForwardRedPlcy specifies the redirect policy to be
         used to determine the nexthop."
    DEFVAL { ''H }
    ::= { tIPv6FilterParamsEntry 33 }

tIPv6FilterParamsActiveDest OBJECT-TYPE
    SYNTAX      InetAddressIPv6
    MAX-ACCESS  read-only
    STATUS      current
    DESCRIPTION
        "tIPv6FilterParamsActiveDest indicates the IPv6 address of the active
         destination for this IPv6 filter. A value of 0 indicates that there
         is currently no active destination."
    ::= { tIPv6FilterParamsEntry 34 }

tIPv6FilterParamsTimeRangeName OBJECT-TYPE
    SYNTAX      TNamedItemOrEmpty
    MAX-ACCESS  read-create
    STATUS      current
    DESCRIPTION
        "tIPv6FilterParamsTimeRangeName specifies the tmnxTimeRangeEntry to be
         associated with this filter entry.

         A value for this object can only be specified during row creation, and
         cannot be altered lateron.
         Also, a value is accepted only if the tmnxTimeRangeEntry is defined in
         the TIMETRA-SCHEDULER-MIB::tmnxTimeRangeTable.tTimeRangeName."
    DEFVAL { ''H }
    ::= { tIPv6FilterParamsEntry 35 }

tIPv6FilterParamsTimeRangeState OBJECT-TYPE
    SYNTAX      TTimeRangeState
    MAX-ACCESS  read-only
    STATUS      current
    DESCRIPTION
        "tIPv6FilterParamsTimeRangeState indicates whether or not the entry
         is currently in effect.
         - timeRangeNotApplic:
           no time range is applicable for this entry.
         - timeRangeNotActive:
           A time range is defined in tIPv6FilterParamsTimeRangeName, but is not
           active at this moment. Consequently the filter entry is not
           installed.
         - timeRangeActive.
           A time range is defined in tIPv6FilterParamsTimeRangeName, and is
           activated successfully.
         - timeRangeActiveDownloadFailed:
           A time range is defined in tIPv6FilterParamsTimeRangeName, and is
           activated, but the corresponding filter entry could not be
           installed due to resource problems."
    ::= { tIPv6FilterParamsEntry 36 }

tIPv6FilterParamsIngrHitByteCount OBJECT-TYPE
    SYNTAX      Counter64
    MAX-ACCESS  read-only
    STATUS      current
    DESCRIPTION
        "The value of tIPv6FilterParamsIngrHitByteCount indicates the number
         of bytes of all ingress packets that matched this entry."
    ::= { tIPv6FilterParamsEntry 37 }

tIPv6FilterParamsEgrHitByteCount OBJECT-TYPE
    SYNTAX      Counter64
    MAX-ACCESS  read-only
    STATUS      current
    DESCRIPTION
        "This tIPv6FilterParamsEgrHitByteCount indicates the number
         of bytes of all egress packets that matched this entry."
    ::= { tIPv6FilterParamsEntry 38 }

tIPv6FilterParamsFwdSvcId OBJECT-TYPE
    SYNTAX      TmnxServId
    MAX-ACCESS  read-only
    STATUS      current
    DESCRIPTION
        "tIPv6FilterParamsFwdSvcId indicates the service id of the
         destination for this filter entry. The value 0 indicates that
         there is no active SAP or SDP destination."
    ::= { tIPv6FilterParamsEntry 39 }

tIPv6FilterParamsFwdSapPortId OBJECT-TYPE
    SYNTAX      TmnxPortID
    MAX-ACCESS  read-create
    STATUS      current
    DESCRIPTION
        "tIPv6FilterParamsFwdSapPortId specifies the sap port id of the
         destination for this filter entry.

         The value 0 indicates that there is no SAP destination
         defined. A value different from 0 can only be specified if the value
         of the tIPv6FilterParamsAction object of this entry is 'forward'.
         In addition a non-zero value can only be given if the object
         tIPv6FilterParamsFwdSdpBind is '0'.

         Note that the value of tIPv6FilterParamsFwdSapPortId is silently
         cleared by the system if tIPv6FilterParamsAction is set to
         httpRedirect."
    DEFVAL { 0 }
    ::= { tIPv6FilterParamsEntry 40 }

tIPv6FilterParamsFwdSapEncapVal OBJECT-TYPE
    SYNTAX      TmnxEncapVal
    MAX-ACCESS  read-create
    STATUS      current
    DESCRIPTION
        "tIPv6FilterParamsFwdSapEncapVal specifies the sap port encap value
         of the destination SAP for this filter entry.

         A value different from 0 can only be specified if the value of the
         tIPv6FilterParamsAction object of this entry is 'forward'. In addition
         a non-zero value can only be given if the object
         tIPv6FilterParamsFwdSdpBind has value '0'. The value 0 indicates
         that either
         1) the sap encapsulation value is not specified when
            tIPv6FilterParamsFwdSapPortId and tIPv6FilterParamsFwdSvcId
            have valid values; or
         2) that there is no SAP destination.

         Note that the value of tIPv6FilterParamsFwdSapEncapVal is silently
         cleared by the system if tIPv6FilterParamsAction is set to
         httpRedirect."
    DEFVAL { 0 }
    ::= { tIPv6FilterParamsEntry 41 }

tIPv6FilterParamsFwdSdpBind OBJECT-TYPE
    SYNTAX      SdpBindId
    MAX-ACCESS  read-create
    STATUS      current
    DESCRIPTION
        "tIPv6FilterParamsFwdSdpBind specifies the sdp bind id of the
         destination for this filter entry.

         The value '0' indicates that there is currently no SDP binding defined.
         A value different from '0' can only be specified if the value of the
         tIPv6FilterParamsAction object of this entry is 'forward'. In addition
         a non-zero value can only be given if the objects
         tIPv6FilterParamsFwdSapPortId and tIPv6FilterParamsFwdSapEncapVal have
         value 0.

         Note that the value of tIPv6FilterParamsFwdSdpBind is silently cleared
         by the system if tIPv6FilterParamsAction is set to httpRedirect."
    DEFVAL { '0'H }
    ::= { tIPv6FilterParamsEntry 42 }

tIPv6FilterParamsRedirectURL OBJECT-TYPE
    SYNTAX      TmnxHttpRedirectUrl
    MAX-ACCESS  read-create
    STATUS      current
    DESCRIPTION
        "The value of tIPv6FilterParamsRedirectURL specifies the URL
         to redirect to, when the value of tIPv6FilterParamsAction is
         'httpRedirect'.

         The following macro substitions are applicable in this context:
         $URL, $MAC, $IP, $SUB, $SAP, $SAPDESC, $CID, and $RID.

         Note that the value of tIPv6FilterParamsRedirectURL is silently
         cleared by the system if tIPv6FilterParamsAction is set to any value
         other than httpRedirect."
    DEFVAL { ''H }
    ::= { tIPv6FilterParamsEntry 43 }

tIPv6FilterParamsSrcIpPrefixList OBJECT-TYPE
    SYNTAX      TNamedItemOrEmpty
    MAX-ACCESS  read-create
    STATUS      current
    DESCRIPTION
        "The value of this object specifies the ipv6-prefix-list used as match
         criterion for the source ipv6 address.

         The value specified for this object must correspond to a prefix-list
         defined in tFilterPrefixListTable.

         If the value of this object is empty then the values of the objects
         tIPv6FilterParamsSourceIpAddr and tIPv6FilterParamsSourceIpMask are
         used as source ipv6 address match criterion.

         When this object is set to a non-empty value then the objects
         tIPv6FilterParamsSourceIpAddr and tIPv6FilterParamsSourceIpMask are
         reset to their default values by the system.

         Vice versa, when a new (non-default) value is provided for the objects
         tIPv6FilterParamsSourceIpAddr and tIPv6FilterParamsSourceIpMask then
         this object is reset to its default (empty) value by the system."
    DEFVAL { ''H }
    ::= { tIPv6FilterParamsEntry 44 }

tIPv6FilterParamsDstIpPrefixList OBJECT-TYPE
    SYNTAX      TNamedItemOrEmpty
    MAX-ACCESS  read-create
    STATUS      current
    DESCRIPTION
        "The value of this object specifies the ipv6-prefix-list used as match
         criterion for the destination ipv6 address.

         The value specified for this object must correspond to a prefix-list
         defined in tFilterPrefixListTable.

         If the value of this object is empty then the values of the objects
         tIPv6FilterParamsDestinationIpAddr and
         tIPv6FilterParamsDestinationIpMask are used as destination ipv6
         address match criterion.

         When this object is set to a non-empty value then the objects
         tIPv6FilterParamsDestinationIpAddr and
         tIPv6FilterParamsDestinationIpMask are reset to their default values by
         the system.

         Vice versa, when a new (non-default) value is provided for the objects
         tIPv6FilterParamsDestinationIpAddr and
         tIPv6FilterParamsDestinationIpMask
         then this object is reset to its default (empty) value by the system."
    DEFVAL { ''H }
    ::= { tIPv6FilterParamsEntry 45 }

 tIPv6FilterParamsFragment OBJECT-TYPE
    SYNTAX INTEGER {
                     off (1),
                     false (2),
                     true (3),
                     first-only (4),
                     non-first-only (5)
                   }
    MAX-ACCESS  read-create
    STATUS      current
    DESCRIPTION
        "If Enabled, matches fragmented/unfragmented packets as per value of
         the object."
     DEFVAL { off }
    ::= { tIPv6FilterParamsEntry 46 }

 tIPv6FilterParamsHopByHopOpt OBJECT-TYPE
    SYNTAX      TItemMatch
    MAX-ACCESS  read-create
    STATUS      current
    DESCRIPTION
        "If Enabled, matches a Hop-By-Hop options Extension Header as per value
         of the object."
    DEFVAL { off }
    ::= { tIPv6FilterParamsEntry 47 }

 tIPv6FilterParamsRoutingType0 OBJECT-TYPE
    SYNTAX      TItemMatch
    MAX-ACCESS  read-create
    STATUS      current
    DESCRIPTION
        "If Enabled, matches a Routing Extension Header as per value of the
         object."
    DEFVAL { off }
    ::= { tIPv6FilterParamsEntry 48 }

tIPv6FilterParamsPortSelector OBJECT-TYPE
    SYNTAX      TFltrPortSelector
    MAX-ACCESS  read-create
    STATUS      current
    DESCRIPTION
        "This object specifies how the source-port objects
         (tIPv6FilterParamsSourcePortValue1, tIPv6FilterParamsSourcePortValue2,
         tIPv6FilterParamsSourcePortOperator, tIPv6FilterParamsSrcPortList)
         and destination-port objects (tIPv6FilterParamsDestPortValue1,
         tIPv6FilterParamsDestPortValue2, tIPv6FilterParamsDestPortOperator,
         tIPv6FilterParamsDstPortList) are combined to form the filter match
         criterion. See description of TFltrPortSelector."
    DEFVAL { and-port }
    ::= { tIPv6FilterParamsEntry 49 }

tIPv6FilterParamsSrcPortList OBJECT-TYPE
    SYNTAX      TNamedItemOrEmpty
    MAX-ACCESS  read-create
    STATUS      current
    DESCRIPTION
        "The value of this object specifies the port-list used as match
         criterion for the source port.

         The value specified for this object must correspond to a port-list
         defined in tFilterPortListTable.

         If the value of this object is empty then the values of the objects
         tIPFilterParamsSourcePortValue1, tIPFilterParamsSourcePortValue2, and
         tIPFilterParamsSourcePortOperator are used as source port match
         criterion.

         When this object is set to a non-empty value then the objects
         tIPFilterParamsSourcePortValue1, tIPFilterParamsSourcePortValue2, and
         tIPFilterParamsSourcePortOperator are reset to their default values by
         the system.

         Vice versa, when a new (non-default) value is provided for one of the
         objects tIPFilterParamsSourcePortValue1,
         tIPFilterParamsSourcePortValue2, or tIPFilterParamsSourcePortOperator
         then tIPv6FilterParamsSrcPortList is reset to its default (empty) value
         by the system.

         Setting any one of the objects tIPFilterParamsSourcePortValue1,
         tIPFilterParamsSourcePortValue2, or tIPFilterParamsSourcePortOperator
         to a non-default value in combination with a non-default value for the
         object tIPv6FilterParamsSrcPortList is rejected by the system"
    DEFVAL { ''H }
    ::= { tIPv6FilterParamsEntry 50 }

tIPv6FilterParamsDstPortList OBJECT-TYPE
    SYNTAX      TNamedItemOrEmpty
    MAX-ACCESS  read-create
    STATUS      current
    DESCRIPTION
        "The value of this object specifies the port-list used as match
         criterion for the destination port.

         The value specified for this object must correspond to a port-list
         defined in tFilterPortListTable.

         If the value of this object is empty then the values of the objects
         tIPFilterParamsDestPortValue1, tIPFilterParamsDestPortValue2, and
         tIPFilterParamsDestPortOperator are used as destination port match
         criterion.

         When this object is set to a non-empty value then the objects
         tIPFilterParamsDestPortValue1, tIPFilterParamsDestPortValue2, and
         tIPFilterParamsDestPortOperator are reset to their default values by
         the system.

         Vice versa, when a new (non-default) value is provided for one of the
         objects tIPFilterParamsDestPortValue1, tIPFilterParamsDestPortValue2,
         or tIPFilterParamsDestPortOperator then tIPv6FilterParamsDstPortList is
         reset to its default (empty) value by the system.

         Setting any one of the objects tIPFilterParamsDestPortValue1,
         tIPFilterParamsDestPortValue2, or tIPFilterParamsDestPortOperator to a
         non-default value in combination with a non-default value for the
         object tIPv6FilterParamsDstPortList is rejected by the system"
    DEFVAL { ''H }
    ::= { tIPv6FilterParamsEntry 51 }

tIPv6FilterParamsRdirAllwRadOvrd OBJECT-TYPE
    SYNTAX      TruthValue
    MAX-ACCESS  read-create
    STATUS      current
    DESCRIPTION
        "The value of this object specifies whether or not the value of
         tIPv6FilterParamsRedirectURL can be over-ridden by a Radius VSA. The
         default value is false (i.e. the URL cannot be over-ridden by Radius).
         The value of tIPv6FilterParamsRdirAllwRadOvrd is relevant only if the
         value of tIPv6FilterParamsAction is httpRedirect.

         Setting the value of tIPv6FilterParamsRdirAllwRadOvrd to true is
         ignored by the system if the value of tIPv6FilterParamsAction is not
         httpRedirect. Furthermore, the value of
         tIPv6FilterParamsRdirAllwRadOvrd is silently reset to false by the
         system if tIPv6FilterParamsAction is set to any value other than
         httpRedirect."
    DEFVAL { false }
    ::= { tIPv6FilterParamsEntry 52 }

tIPv6FilterParamsFwdRtrId OBJECT-TYPE
    SYNTAX      TmnxVRtrIDOrZero
    MAX-ACCESS  read-create
    STATUS      current
    DESCRIPTION
        "tIPv6FilterParamsFwdRtrId specifies, if different from '0',
         the router id into which the packet should be forwarded
         if it hits this filter entry.

         The action of this entry should be 'forward' in such a case."
    DEFVAL { 0 }
    ::= { tIPv6FilterParamsEntry 53 }

tIPv6FilterParamsSrcIpFullMask OBJECT-TYPE
    SYNTAX      InetAddressIPv6
    MAX-ACCESS  read-create
    STATUS      current
    DESCRIPTION
        "If different from 0, the object tIPv6FilterParamsSrcIpFullMask
         specifies the IPv6 Mask value for this policy IPv6 Filter entry.
         The mask is ANDed with the received Source IPv6 address to match
         the tIPv6FilterParamsSourceIpAddr.
         
         If the value of tIPv6FilterParamsSourceIpMask is 0, and the
         value of tIPv6FilterParamsSrcIpFullMask is non zero then the
         value of tIPv6FilterParamsSrcIpFullMask is used as a mask.

         If the value of tIPv6FilterParamsSourceIpMask is non zero,
         it will be equal to the mask expressed in the object
         tIPv6FilterParamsSrcIpFullMask.

         If both tIPv6FilterParamsSourceIpMask and
         tIPv6FilterParamsSrcIpFullMask are set to 0, no matching is done
         on the Source IPv6 address.

         If a regular mask is specified for tIPv6FilterParamsSrcIpFullMask
         then the value of tIPv6FilterParamsSourceIpMask will be changed
         to reflect this value."
    DEFVAL { '00000000000000000000000000000000'H }
    ::= { tIPv6FilterParamsEntry 54 }

tIPv6FilterParamsDstIpFullMask OBJECT-TYPE
    SYNTAX      InetAddressIPv6
    MAX-ACCESS  read-create
    STATUS      current
    DESCRIPTION
        "If different from 0, the object tIPv6FilterParamsDstIpFullMask
         specifies the IPv6 Mask value for this policy IPv6 Filter entry.
         The mask is ANDed with the received Destination IPv6 address to match
         the tIPv6FilterParamsDestinationIpAddr.
         
         If the value of tIPv6FilterParamsDestinationIpMask is 0, and the
         value of tIPv6FilterParamsDstIpFullMask is non zero then the
         value of tIPv6FilterParamsDstIpFullMask is used as a mask.

         If the value of tIPv6FilterParamsDestinationIpMask is non zero,
         it will be equal to the mask expressed in the object
         tIPv6FilterParamsDstIpFullMask.

         If both tIPv6FilterParamsDestinationIpMask and
         tIPv6FilterParamsDstIpFullMask are set to 0, no matching is done
         on the Destination IPv6 address.

         If a regular mask is specified for tIPv6FilterParamsDstIpFullMask
         then the value of tIPv6FilterParamsDestinationIpMask will be changed
         to reflect this value."
    DEFVAL { '00000000000000000000000000000000'H }
    ::= { tIPv6FilterParamsEntry 55 }

tIPv6FilterParamsNatPolicyName OBJECT-TYPE
    SYNTAX      TNamedItemOrEmpty
    MAX-ACCESS  read-create
    STATUS      current
    DESCRIPTION
        "The value of this object specifies the name of the NAT policy to be
         used when the value of tIPv6FilterParamsAction is nat. If the value is
         empty then a default policy is used. If the value is non-empty then it
         must correspond to a policy defined in tmnxNatPlcyTable.

         The value of tIPv6FilterParamsNatPolicyName is relevant only if the
         value of tIPv6FilterParamsAction is nat. Setting the value of
         tIPv6FilterParamsNatPolicyName to a non-empty string is ignored by the
         system if the value of tIPv6FilterParamsAction is not nat.

         Furthermore, the value of tIPv6FilterParamsNatPolicyName is silently
         reset to an empty string by the system if tIPv6FilterParamsAction is
         set to any value other than nat."
    DEFVAL { "" }
    ::= { tIPv6FilterParamsEntry 56 }

tIPv6FilterParamsFlowLabel OBJECT-TYPE
    SYNTAX      IPv6FlowLabel
    MAX-ACCESS  read-create
    STATUS      current
    DESCRIPTION
         "If different from -1 the value of the object
          tIPv6FilterParamsFlowLabel specifies the flow label
          to be used as a match criterion."
    DEFVAL { -1 }
    ::= { tIPv6FilterParamsEntry 57 }

tIPv6FilterParamsFlowLabelMask OBJECT-TYPE
    SYNTAX      IPv6FlowLabelMask
    MAX-ACCESS  read-create
    STATUS      current
    DESCRIPTION
         "The value of the object tIPv6FilterParamsFlowLabelMask
          specifies the flow label mask value for this policy IP Filter entry.

          The mask is ANDed with the received flow label to match
          the value of the object tIPv6FilterParamsFlowLabel.

          The value is only significant if the value of the object
          tIPv6FilterParamsFlowLabel is different from -1."
    DEFVAL { 'fffff'H }
    ::= { tIPv6FilterParamsEntry 58 }

tIPv6FilterParamsFwdLsp OBJECT-TYPE
    SYNTAX      TmnxVRtrMplsLspID
    MAX-ACCESS  read-create
    STATUS      current
    DESCRIPTION
         "If different from zero the value of the object tIPv6FilterParamsFwdLsp
          together with the value of the object tIPv6FilterParamsFwdLspRtrId
          specifies the LSP into which a packet should be forwarded if it hits
          this filter entry.

          The value of the object tIPv6FilterParamsAction of this entry
          must be 'forward' in such case. Otherwise the value of the object
          tIPv6FilterParamsFwdLsp is ignored by the system.

          The value is reset to '0' if the value of the object
          tIPv6FilterParamsAction is set to any value other than forward.

          The value of the object tIPv6FilterParamsFwdLsp cannot be set to a
          non-zero value if other destinations are already specified.

          The value has to be '0' if the value of the object
          tIPv6FilterParamsFwdLspRtrId is not set (i.e. is '0').

          If a non-zero value is set, the value of the object
          tIPv6FilterParamsFwdLspRtrId has to be set as well."
    DEFVAL { 0 }
    ::= { tIPv6FilterParamsEntry 59 }

tIPv6FilterParamsFwdLspRtrId OBJECT-TYPE
    SYNTAX      TmnxVRtrIDOrZero
    MAX-ACCESS  read-create
    STATUS      current
    DESCRIPTION
         "The value of the object tIPv6FilterParamsFwdLspRtrId specifies
          the router ID that the LSP ID defined by the value of the object
          tIPv6FilterParamsFwdLsp belongs to.

          The value of the object tIPv6FilterParamsAction of this entry
          must be 'forward' in such case. Otherwise the value of the object
          tIPv6FilterParamsFwdLspRtrId is ignored by the system.

          The value is reset to '0' if the value of the object
          tIPv6FilterParamsAction is set to any value other than forward.

          The value of this object cannot be set to a non-zero value if
          other destinations are already specified.

          The value has to be '0' if the value of the object
          tIPv6FilterParamsFwdLsp is not set (i.e. is '0').

          If a non-zero value is set, the value of the object
          tIPv6FilterParamsFwdLsp has to be set as well.

          The ID of the base router and '0' are the only allowed values with this
          version of the product."
    DEFVAL { 0 }
    ::= { tIPv6FilterParamsEntry 60 }

--
-- SNMP objects allowing to group filter entries that are inserted in a filter
-- by either radius or Credit Control.
--

tFilterGroupInsertedEntries  OBJECT IDENTIFIER ::= { tFilterObjects 20 }

tFltrGrpInsrtdEntriesFilterType OBJECT-TYPE
    SYNTAX      TFilterType
    MAX-ACCESS  read-write
    STATUS      current
    DESCRIPTION
        "tFltrGrpInsrtdEntriesFilterType specifies the type of the filter
         referred to by tFltrGrpInsrtdEntriesFilterId.
         Inserted entries can only occur in 'fltrtypeselIp' and
         'fltrtypeselIpv6'"
    DEFVAL { fltrtypeselNone }
    ::= { tFilterGroupInsertedEntries 1 }

tFltrGrpInsrtdEntriesFilterId OBJECT-TYPE
    SYNTAX      TFilterID
    MAX-ACCESS  read-write
    STATUS      current
    DESCRIPTION
        "tFltrGrpInsrtdEntriesFilterId specifies for which filter the inserted
         entries must be grouped."
    DEFVAL { 0 }
    ::= { tFilterGroupInsertedEntries 2 }

tFltrGrpInsrtdEntriesApplication OBJECT-TYPE
    SYNTAX      TFilterSubInsSpaceOwner
    MAX-ACCESS  read-write
    STATUS      current
    DESCRIPTION
        "tFltrGrpInsrtdEntriesApplication specifies for which application the
         the inserted entries must be grouped."
    DEFVAL { none }
    ::= { tFilterGroupInsertedEntries 3 }

tFltrGrpInsrtdEntriesLocation OBJECT-TYPE
    SYNTAX INTEGER {
                     none     (0),
                     top      (1),
                     bottom   (2)
                   }
    MAX-ACCESS  read-write
    STATUS      current
    DESCRIPTION
        "tFltrGrpInsrtdEntriesLocation specifies at what location the inserted
         entries must be grouped."
    DEFVAL { none }
    ::= { tFilterGroupInsertedEntries 4 }

tFltrGrpInsrtdEntriesResult OBJECT-TYPE
    SYNTAX INTEGER {
                     none     (0),
                     success  (1),
                     failure  (2)
                   }
    MAX-ACCESS  read-only
    STATUS      current
    DESCRIPTION
        "tFltrGrpInsrtdEntriesResult indicates the success or failure of the
         last requested grouping request on inserted entries."
    ::= { tFilterGroupInsertedEntries 5 }

tFltrGrpInsrtdEntriesFeedback OBJECT-TYPE
    SYNTAX      DisplayString (SIZE (0..254))
    MAX-ACCESS  read-only
    STATUS      current
    DESCRIPTION
        "tFltrGrpInsrtdEntriesFeedback may indicate additional info on the last
         inserted filter entries grouping action performed."
    ::= { tFilterGroupInsertedEntries 6 }

tFltrGrpInsrtdEntriesExecute OBJECT-TYPE
    SYNTAX      TruthValue
    MAX-ACCESS  read-write
    STATUS      current
    DESCRIPTION
        "Setting the object tFltrGrpInsrtdEntriesExecute to 'true' will cause
         the system to attempt to execute te grouping command as specified
         by the other MIB objects in the tFilterGroupInsertedEntries mibgroup.

         When read the value will always indicate 'false'. The result of the
         command can be found in tFltrGrpInsrtdEntriesResult and
         tFltrGrpInsrtdEntriesFeedback"
    DEFVAL { false }
    ::= { tFilterGroupInsertedEntries 7 }

--
-- DHCP filter table
--

tDhcpFilterTableLastChanged OBJECT-TYPE
    SYNTAX      TimeStamp
    MAX-ACCESS  read-only
    STATUS      current
    DESCRIPTION
        "The value of tDhcpFilterTableLastChanged indicates the sysUpTime
         at the time of the last modification to tDhcpFilterTable by
         adding, deleting an entry or change to a writable object in the table.

         If no changes were made to the table since the last re-initialization
         of the local network management subsystem, then this object contains a
         zero value."
    ::= { tFilterObjects 21 }

tDhcpFilterTable OBJECT-TYPE
    SYNTAX      SEQUENCE OF TDhcpFilterEntry
    MAX-ACCESS  not-accessible
    STATUS      current
    DESCRIPTION
        "Contains a list of all DHCP filters configured on this system."
    ::= { tFilterObjects 22 }

tDhcpFilterEntry OBJECT-TYPE
    SYNTAX      TDhcpFilterEntry
    MAX-ACCESS  not-accessible
    STATUS      current
    DESCRIPTION
        "Information about a particular DHCP filter. Entries are created/deleted
         by user. Entries have a presumed StorageType of nonVolatile."
    INDEX { tDhcpFilterId }
    ::= { tDhcpFilterTable 1 }

TDhcpFilterEntry ::= SEQUENCE
    {
        tDhcpFilterId           TDHCPFilterID,
        tDhcpFilterRowStatus    RowStatus,
        tDhcpFilterLastChanged  TimeStamp,
        tDhcpFilterDescription  TItemDescription
    }

tDhcpFilterId OBJECT-TYPE
    SYNTAX      TDHCPFilterID (1..65535)
    MAX-ACCESS  not-accessible
    STATUS      current
    DESCRIPTION
        "Uniquely identifies a mac filter as configures on this system."
    ::= { tDhcpFilterEntry 1 }

tDhcpFilterRowStatus OBJECT-TYPE
    SYNTAX      RowStatus
    MAX-ACCESS  read-create
    STATUS      current
    DESCRIPTION
        "This object allows entries to be created and deleted in the
         tDhcpFilterTable."
    ::= { tDhcpFilterEntry 2 }

tDhcpFilterLastChanged OBJECT-TYPE
    SYNTAX      TimeStamp
    MAX-ACCESS  read-only
    STATUS      current
    DESCRIPTION
        "The value of tDhcpFilterLastChanged indicates the timestamp of
         last change to this row in tDhcpFilterTable."
    ::= { tDhcpFilterEntry 3 }

tDhcpFilterDescription OBJECT-TYPE
    SYNTAX      TItemDescription
    MAX-ACCESS  read-create
    STATUS      current
    DESCRIPTION
        "User-provided description for this filter."
    DEFVAL { ''H }
    ::= { tDhcpFilterEntry 4 }

--
-- DHCP Filter Entry parameters
--

tDhcpFilterParamsTblLastChanged OBJECT-TYPE
    SYNTAX      TimeStamp
    MAX-ACCESS  read-only
    STATUS      current
    DESCRIPTION
        "The value of tDhcpFilterParamsTblLastChanged indicates the sysUpTime
         at the time of the last modification to tDhcpFilterParamsTable by
         adding, deleting an entry or change to a writable object in the table.

         If no changes were made to the table since the last re-initialization
         of the local network management subsystem, then this object contains a
         zero value."
    ::= { tFilterObjects 23 }

tDhcpFilterParamsTable OBJECT-TYPE
    SYNTAX      SEQUENCE OF TDhcpFilterParamsEntry
    MAX-ACCESS  not-accessible
    STATUS      current
    DESCRIPTION  "A table of all DHCP filter match entries for all DHCP filters"
    ::= { tFilterObjects 24 }

tDhcpFilterParamsEntry OBJECT-TYPE
    SYNTAX      TDhcpFilterParamsEntry
    MAX-ACCESS  not-accessible
    STATUS      current
    DESCRIPTION
        "Information about a particular DHCP filter entry.
        Every DHCP filter can have zero or more DHCP filter match entries.

        A filter entry with no match criteria set will match every
        packet, and the entry action will be taken.

        Entries are created/deleted by user.

        There is no StorageType object, entries have a presumed
        StorageType of nonVolatile."
    INDEX { tDhcpFilterId, tDhcpFilterParamsId }
    ::= { tDhcpFilterParamsTable 1 }

TDhcpFilterParamsEntry ::= SEQUENCE
    {
        tDhcpFilterParamsId              TEntryId,
        tDhcpFilterParamsRowStatus       RowStatus,
        tDhcpFilterParamsLastChanged     TimeStamp,
        tDhcpFilterParamsOptionNumber    INTEGER,
        tDhcpFilterParamsOptionMatch     TDhcpFilterMatch,
        tDhcpFilterParamsAction          TDhcpFilterAction,
        tDhcpFilterParamsOptionValue     OCTET STRING
    }

tDhcpFilterParamsId OBJECT-TYPE
    SYNTAX      TEntryId
    MAX-ACCESS  not-accessible
    STATUS      current
    DESCRIPTION
        "This is the secondary index for the entry. Every DHCP filter can have
         multiple entries, therefore every DHCP filter entry is identified by
         the tDhcpFilterId and tDhcpFilterParamsId."
    ::= { tDhcpFilterParamsEntry 1 }

tDhcpFilterParamsRowStatus OBJECT-TYPE
    SYNTAX      RowStatus
    MAX-ACCESS  read-create
    STATUS      current
    DESCRIPTION
        "This object allows entries to be created and deleted in the
         tDhcpFilterParamsTable."
    ::= { tDhcpFilterParamsEntry 2 }

tDhcpFilterParamsLastChanged OBJECT-TYPE
    SYNTAX      TimeStamp
    MAX-ACCESS  read-only
    STATUS      current
    DESCRIPTION
        "The value of tDhcpFilterParamsLastChanged indicates the timestamp of
         last change to this row in tDhcpFilterParamsTable."
    ::= { tDhcpFilterParamsEntry 3 }

tDhcpFilterParamsOptionNumber OBJECT-TYPE
    SYNTAX      INTEGER (-1|0..255)
    MAX-ACCESS  read-create
    STATUS      current
    DESCRIPTION
        "The value of tDhcpFilterParamsOptionNumber specifies the number of
         the DHCP option to filter on."
    REFERENCE
        "RFC 2132, RFC 3315, RFC 3633"
    DEFVAL { -1 }
    ::= { tDhcpFilterParamsEntry 4 }

tDhcpFilterParamsOptionMatch OBJECT-TYPE
    SYNTAX      TDhcpFilterMatch
    MAX-ACCESS  read-create
    STATUS      current
    DESCRIPTION
        "The value of tDhcpFilterParamsOptionMatch specifies the criteria that
         the DHCP option must match to trigger this filter entry.

         The value present(1) specifies that the DHCP option must be present,
         the value absent(2) specifies that the DHCP option must be absent. In
         these cases tDhcpFilterParamsOptionValue will be reset to an empty
         string.

         A value string(3), string-exact(4), string-invert(5),
         string-exact-invert(6), hex(7), hex-exact(8), hex-invert(9) or
         hex-exact-invert(10) requires an octet string to be present in
         tDhcpFilterParamsOptionValue to match against.
         "
    DEFVAL { present }
    ::= { tDhcpFilterParamsEntry 5 }

tDhcpFilterParamsAction OBJECT-TYPE
    SYNTAX      TDhcpFilterAction
    MAX-ACCESS  read-create
    STATUS      current
    DESCRIPTION
        "The action to take for DHCP host creation requests that match this
         filter entry.
         The value none(1) specifies normal host creation behaviour, the value
         bypass-host-creation(2) specifies to bypass host creation, the value
         drop(3) specifies to drop the DHCP message."
    DEFVAL { none }
    ::= { tDhcpFilterParamsEntry 6 }

tDhcpFilterParamsOptionValue OBJECT-TYPE
    SYNTAX      OCTET STRING (SIZE (0..127))
    MAX-ACCESS  read-create
    STATUS      current
    DESCRIPTION
        "The value of the object tDhcpFilterParamsOptionValue specifies
         the matching pattern for the filtered DHCP option.

         This object is mandatory at creation time. A zero length value is only
         allowed when the value of tDhcpFilterParamsOptionMatch is present(1)
         or absent(2)."
    ::= { tDhcpFilterParamsEntry 7 }

-- ----------------------
-- tMacFilterNameTable
-- ----------------------

tMacFilterNameTableLastChgd OBJECT-TYPE
    SYNTAX      TimeStamp
    MAX-ACCESS  read-only
    STATUS      current
    DESCRIPTION
        "The value of tMacFilterNameTableLastChgd indicates the
         sysUpTime at the time of the last modification
         of tMacFilterNameTable.

         If no changes were made to the entry since the last
         re-initialization of the local network management subsystem,
         then this object contains a zero value."
    ::= { tFilterObjects 25 }

tMacFilterNameTable OBJECT-TYPE
    SYNTAX      SEQUENCE OF TMacFilterNameEntry
    MAX-ACCESS  not-accessible
    STATUS      current
    DESCRIPTION
        "A table that contains MAC filter name information. Entries
         are created automatically by the system
         when tMacFilterName object is set for the MAC filter."
    ::= { tFilterObjects 26 }

tMacFilterNameEntry OBJECT-TYPE
    SYNTAX      TMacFilterNameEntry
    MAX-ACCESS  not-accessible
    STATUS      current
    DESCRIPTION
        "Basic information about a specific MAC filter name."
    INDEX           { tMacFilterName }
    ::= { tMacFilterNameTable 1 }

TMacFilterNameEntry ::=
    SEQUENCE {
        tMacFilterNameId                   TAnyFilterID,
        tMacFilterNameRowStatus            RowStatus,
        tMacFilterNameLastChanged          TimeStamp
    }

tMacFilterNameId OBJECT-TYPE
    SYNTAX      TAnyFilterID
    MAX-ACCESS  read-only
    STATUS      current
    DESCRIPTION
        "The value of the object tMacFilterNameId specifies the filter
         name associated with this MAC filter."
    ::= { tMacFilterNameEntry 1 }

tMacFilterNameRowStatus OBJECT-TYPE
    SYNTAX      RowStatus
    MAX-ACCESS  read-only
    STATUS      current
    DESCRIPTION
        "This value of the object tMacFilterNameRowStatus specifies the
         status of this row."
    ::= { tMacFilterNameEntry 2 }

tMacFilterNameLastChanged OBJECT-TYPE
    SYNTAX      TimeStamp
    MAX-ACCESS  read-only
    STATUS      current
    DESCRIPTION
        "The value of tMacFilterNameLastChanged indicates the sysUpTime at
         the time of the last modification of this entry.

         If no changes were made to the entry since the last
         re-initialization of the local network management
         subsystem, then this object contains a zero value."
    ::= { tMacFilterNameEntry 3 }

-- ----------------------
-- tIpFilterNameTable
-- ----------------------

tIpFilterNameTableLastChgd OBJECT-TYPE
    SYNTAX      TimeStamp
    MAX-ACCESS  read-only
    STATUS      current
    DESCRIPTION
        "The value of tIpFilterNameTableLastChgd indicates the
         sysUpTime at the time of the last modification
         of tIpFilterNameTable.

         If no changes were made to the entry since the last
         re-initialization of the local network management subsystem,
         then this object contains a zero value."
    ::= { tFilterObjects 27 }

tIpFilterNameTable OBJECT-TYPE
    SYNTAX      SEQUENCE OF TIpFilterNameEntry
    MAX-ACCESS  not-accessible
    STATUS       current
    DESCRIPTION
        "A table that contains IP filter name information. Entries
         are created automatically by the system
         when tIpFilterName object is set for the IP filter."
    ::= { tFilterObjects 28 }

tIpFilterNameEntry OBJECT-TYPE
    SYNTAX      TIpFilterNameEntry
    MAX-ACCESS  not-accessible
    STATUS       current
    DESCRIPTION
        "Basic information about a specific IP filter name."
    INDEX           { tIpFilterName }
    ::= { tIpFilterNameTable 1 }

TIpFilterNameEntry ::=
    SEQUENCE {
        tIpFilterNameId                   TAnyFilterID,
        tIpFilterNameRowStatus            RowStatus,
        tIpFilterNameLastChanged          TimeStamp
    }

tIpFilterNameId OBJECT-TYPE
    SYNTAX      TAnyFilterID
    MAX-ACCESS  read-only
    STATUS      current
    DESCRIPTION
        "The value of the object tIpFilterNameId specifies the filter
         name associated with this IP filter."
    ::= { tIpFilterNameEntry 1 }

tIpFilterNameRowStatus OBJECT-TYPE
    SYNTAX      RowStatus
    MAX-ACCESS  read-only
    STATUS      current
    DESCRIPTION
        "This value of the object tIpFilterNameRowStatus specifies the
         status of this row."
    ::= { tIpFilterNameEntry 2 }

tIpFilterNameLastChanged OBJECT-TYPE
    SYNTAX      TimeStamp
    MAX-ACCESS  read-only
    STATUS      current
    DESCRIPTION
        "The value of tIpFilterNameLastChanged indicates the sysUpTime at
         the time of the last modification of this entry.

         If no changes were made to the entry since the last
         re-initialization of the local network management
         subsystem, then this object contains a zero value."
    ::= { tIpFilterNameEntry 3 }

-- ----------------------
-- tIpv6FilterNameTable
-- ----------------------

tIpv6FilterNameTableLastChgd OBJECT-TYPE
    SYNTAX      TimeStamp
    MAX-ACCESS  read-only
    STATUS      current
    DESCRIPTION
        "The value of tIpv6FilterNameTableLastChgd indicates the
         sysUpTime at the time of the last modification
         of tIpv6FilterNameTable.

         If no changes were made to the entry since the last
         re-initialization of the local network management subsystem,
         then this object contains a zero value."
    ::= { tFilterObjects 29 }

tIpv6FilterNameTable OBJECT-TYPE
    SYNTAX      SEQUENCE OF TIpv6FilterNameEntry
    MAX-ACCESS  not-accessible
    STATUS      current
    DESCRIPTION
        "A table that contains IPv6 filter name information. Entries
         are created automatically by the system
         when tIpv6FilterName object is set for the IPv6 filter."
    ::= { tFilterObjects 30 }

tIpv6FilterNameEntry OBJECT-TYPE
    SYNTAX      TIpv6FilterNameEntry
    MAX-ACCESS  not-accessible
    STATUS      current
    DESCRIPTION
        "Basic information about a specific IPv6 filter name."
    INDEX           { tIpv6FilterName }
    ::= { tIpv6FilterNameTable 1 }

TIpv6FilterNameEntry ::=
    SEQUENCE {
        tIpv6FilterNameId                   TAnyFilterID,
        tIpv6FilterNameRowStatus            RowStatus,
        tIpv6FilterNameLastChanged          TimeStamp
    }

tIpv6FilterNameId OBJECT-TYPE
    SYNTAX      TAnyFilterID
    MAX-ACCESS  read-only
    STATUS      current
    DESCRIPTION
        "The value of the object tIpv6FilterNameId specifies the filter
         name associated with this IPv6 filter."
    ::= { tIpv6FilterNameEntry 1 }

tIpv6FilterNameRowStatus OBJECT-TYPE
    SYNTAX      RowStatus
    MAX-ACCESS  read-only
    STATUS      current
    DESCRIPTION
        "This value of the object tIpv6FilterNameRowStatus specifies the
         status of this row."
    ::= { tIpv6FilterNameEntry 2 }

tIpv6FilterNameLastChanged OBJECT-TYPE
    SYNTAX      TimeStamp
    MAX-ACCESS  read-only
    STATUS     current
    DESCRIPTION
        "The value of tIpv6FilterNameLastChanged indicates the sysUpTime at
         the time of the last modification of this entry.

         If no changes were made to the entry since the last
         re-initialization of the local network management
         subsystem, then this object contains a zero value."
    ::= { tIpv6FilterNameEntry 3 }

-- ------------------
--  tFilterLiObjects
-- ------------------

tFilterLiObjects  OBJECT IDENTIFIER ::= { tFilterObjects 31 }

-- ----------------------
--  tLiReservedBlockTable
-- ----------------------

tLiReservedBlockTableLastChanged OBJECT-TYPE
    SYNTAX      TimeStamp
    MAX-ACCESS  read-only
    STATUS      current
    DESCRIPTION
        "The object tLiReservedBlockTableLastChanged indicates the
         sysUpTime at the time of the last modification
         of tLiReservedBlockTable.

         If no changes were made to the entry since the last
         re-initialization of the local network management subsystem,
         then this object contains a zero value."
    ::= { tFilterLiObjects 1 }

tLiReservedBlockTable OBJECT-TYPE
    SYNTAX      SEQUENCE OF TLiReservedBlockEntry
    MAX-ACCESS  not-accessible
    STATUS      current
    DESCRIPTION
        "The table tLiReservedBlockTable describes LI reserved blocks.
         In this release this table can have at most one entry."
    ::= { tFilterLiObjects 2 }

tLiReservedBlockEntry OBJECT-TYPE
    SYNTAX      TLiReservedBlockEntry
    MAX-ACCESS  not-accessible
    STATUS      current
    DESCRIPTION
        "Information about an LI reserved block. This block can be associated
         with one or more filters to reserve a number of entries in those
         filters for LI."
    INDEX { tLiReservedBlockName }
    ::= { tLiReservedBlockTable 1 }

TLiReservedBlockEntry ::=
    SEQUENCE {
        tLiReservedBlockName            TNamedItem,
        tLiReservedBlockRowStatus       RowStatus,
        tLiReservedBlockLastChanged     TimeStamp,
        tLiReservedBlockDescription     TItemDescription,
        tLiReservedBlockStart           TEntryIdOrZero,
        tLiReservedBlockSize            TEntryIdOrZero
    }

tLiReservedBlockName OBJECT-TYPE
    SYNTAX      TNamedItem
    MAX-ACCESS  not-accessible
    STATUS      current
    DESCRIPTION
        "The object tLiReservedBlockName uniquely identifies
         an LI reserved block."
    ::= { tLiReservedBlockEntry 1 }

tLiReservedBlockRowStatus OBJECT-TYPE
    SYNTAX      RowStatus
    MAX-ACCESS  read-create
    STATUS      current
    DESCRIPTION
        "The object tLiReservedBlockRowStatus specifies the
         status of this row."
    ::= { tLiReservedBlockEntry 2 }

tLiReservedBlockLastChanged OBJECT-TYPE
    SYNTAX      TimeStamp
    MAX-ACCESS  read-only
    STATUS      current
    DESCRIPTION
        "The object tLiReservedBlockLastChanged indicates the
         sysUpTime at the time of the last modification of this entry.

         If no changes were made to the entry since the last
         re-initialization of the local network management subsystem,
         then this object contains a zero value."
    ::= { tLiReservedBlockEntry 3 }

tLiReservedBlockDescription OBJECT-TYPE
    SYNTAX      TItemDescription
    MAX-ACCESS  read-create
    STATUS      current
    DESCRIPTION
        "The object tLiReservedBlockDescription specifies a description
         for this LI reserved block."
    DEFVAL { ''H }
    ::= { tLiReservedBlockEntry 4 }

tLiReservedBlockStart OBJECT-TYPE
    SYNTAX      TEntryIdOrZero
    MAX-ACCESS  read-create
    STATUS      current
    DESCRIPTION
        "The object tLiReservedBlockStart specifies the starting entry of
         the LI reserved block.

         If set to '0' no block is reserved. In this case the value of the
         object tLiReservedBlockSize will be set to '0' by the system."
    DEFVAL { 0 }
    ::= { tLiReservedBlockEntry 5 }

tLiReservedBlockSize OBJECT-TYPE
    SYNTAX      TEntryIdOrZero (0..8192)
    MAX-ACCESS  read-create
    STATUS      current
    DESCRIPTION
        "The object tLiReservedBlockSize specifies the size of the
         LI reserved block.

         If set to '0' no block is reserved. In this case the value of the
         object tLiReservedBlockStart will be set to '0' by the system."
    DEFVAL { 0 }
    ::= { tLiReservedBlockEntry 6 }


-- --------------------------
-- tLiReservedBlockFltrTable
-- --------------------------

tLiReservedBlockFltrTableLastChg OBJECT-TYPE
    SYNTAX      TimeStamp
    MAX-ACCESS  read-only
    STATUS      current
    DESCRIPTION
        "The value of tLiReservedBlockFltrTableLastChg indicates the
         sysUpTime at the time of the last modification
         of tLiReservedBlockFltrTable.

         If no changes were made to the entry since the last
         re-initialization of the local network management subsystem,
         then this object contains a zero value."
    ::= { tFilterLiObjects 3 }

tLiReservedBlockFltrTable OBJECT-TYPE
    SYNTAX      SEQUENCE OF TLiReservedBlockFltrEntry
    MAX-ACCESS  not-accessible
    STATUS      current
    DESCRIPTION
        "The table tLiReservedBlockFltrTable contains associations between
         normal filters and LI block reservations."
    ::= { tFilterLiObjects 4 }

tLiReservedBlockFltrEntry OBJECT-TYPE
    SYNTAX      TLiReservedBlockFltrEntry
    MAX-ACCESS  not-accessible
    STATUS      current
    DESCRIPTION
        "An association of a normal filter with an LI block reservation.
         In this release MAC and IP/IPv6 filters are supported.

         Entries can be created and deleted via SNMP SET operations 
         to tLiReservedBlockFltrRowStatus."
    INDEX { tLiReservedBlockName,
            tLiReservedBlockFltrType,
            tLiReservedBlockFltrIdStart,
            tLiReservedBlockFltrIdEnd
    }
    ::= { tLiReservedBlockFltrTable 1 }

TLiReservedBlockFltrEntry ::=
    SEQUENCE {
        tLiReservedBlockFltrType         TFilterType,
        tLiReservedBlockFltrIdStart      TFilterID,
        tLiReservedBlockFltrIdEnd        TFilterID,
        tLiReservedBlockFltrRowStatus    RowStatus,
        tLiReservedBlockFltrLastChanged  TimeStamp
    }

tLiReservedBlockFltrType OBJECT-TYPE
    SYNTAX      TFilterType
    MAX-ACCESS  not-accessible
    STATUS      current
    DESCRIPTION
        "The object tLiReservedBlockFltrType specifies the type of filter
         this LI block reservation applies to.

         In this release MAC and IP/IPv6 filters are supported:
             fltrtypeselIp     (1)             
             fltrtypeselMac    (2)
             fltrtypeselIpv6   (4)"
    ::= { tLiReservedBlockFltrEntry 1 }

tLiReservedBlockFltrIdStart OBJECT-TYPE
    SYNTAX      TFilterID
    MAX-ACCESS  not-accessible
    STATUS      current
    DESCRIPTION
        "The object tLiReservedBlockFltrIdStart specifies the ID of the
         first filter to apply an LI block reservation.

         If the value of the object tLiReservedBlockFltrType is equal to 1 or 4
         (IP or IPv6 filter) then the scope of any filter (defined by the value 
         of the object tIPFilterScope or tIPv6FilterScope) inside of the range
         defined by the values of the objects tLiReservedBlockFltrIdStart and 
         tLiReservedBlockFltrIdEnd must not be equal to embedded (3).

         In this release, tLiReservedBlockFltrIdStart must be equal to
         tLiReservedBlockFltrIdEnd."
    ::= { tLiReservedBlockFltrEntry 2 }

tLiReservedBlockFltrIdEnd OBJECT-TYPE
    SYNTAX      TFilterID
    MAX-ACCESS  not-accessible
    STATUS      current
    DESCRIPTION
        "The object tLiReservedBlockFltrIdEnd specifies the ID of the
         last filter to apply an LI block reservation.

         If the value of the object tLiReservedBlockFltrType is equal to 1 or 4
         (IP or IPv6 filter) then the scope of any filter (defined by the value 
         of the object tIPFilterScope or tIPv6FilterScope) inside of the range
         defined by the values of the objects tLiReservedBlockFltrIdStart and 
         tLiReservedBlockFltrIdEnd must not be equal to embedded (3).

         In this release, tLiReservedBlockFltrIdEnd must be equal to
         tLiReservedBlockFltrIdStart."
    ::= { tLiReservedBlockFltrEntry 3 }

tLiReservedBlockFltrRowStatus OBJECT-TYPE
    SYNTAX      RowStatus
    MAX-ACCESS  read-create
    STATUS      current
    DESCRIPTION
        "The object tLiReservedBlockFltrRowStatus specifies the
         status of this row."
    ::= { tLiReservedBlockFltrEntry 4 }

tLiReservedBlockFltrLastChanged OBJECT-TYPE
    SYNTAX      TimeStamp
    MAX-ACCESS  read-only
    STATUS      current
    DESCRIPTION
        "The object tLiReservedBlockFltrLastChanged indicates the
         sysUpTime at the time of the last modification of this entry.

         If no changes were made to the entry since the last
         re-initialization of the local network management subsystem,
         then this object contains a zero value."
    ::= { tLiReservedBlockFltrEntry 5 }

-- --------------------
--  tLiFilterTable
-- --------------------

tLiFilterTableLastChanged OBJECT-TYPE
    SYNTAX      TimeStamp
    MAX-ACCESS  read-only
    STATUS      current
    DESCRIPTION
        "The object tLiFilterTableLastChanged indicates the
        sysUpTime at the time of the last modification
        of tLiFilterTable.

        If no changes were made to the entry since the last
        re-initialization of the local network management subsystem,
        then this object contains a zero value."
    ::= { tFilterLiObjects 5 }

tLiFilterTable OBJECT-TYPE
    SYNTAX      SEQUENCE OF TLiFilterEntry
    MAX-ACCESS  not-accessible
    STATUS      current
    DESCRIPTION
        "The table tLiFilterTable contains information about
         all LI filters.

         In this release MAC and IP/IPv6 filters are supported."
    ::= { tFilterLiObjects 6 }

tLiFilterEntry OBJECT-TYPE
    SYNTAX      TLiFilterEntry
    MAX-ACCESS  not-accessible
    STATUS      current
    DESCRIPTION
        "Each entry represents an LI filter. In this release MAC and IP/IPv6
         filters are supported.

         Entries can be created and deleted via SNMP SET operations 
         to tLiFilterRowStatus."
    INDEX { tLiFilterType, 
            tLiFilterName 
    }
    ::= { tLiFilterTable 1 }

TLiFilterEntry ::=
    SEQUENCE {
        tLiFilterType                 TFilterType,
        tLiFilterName                 TNamedItem,
        tLiFilterRowStatus            RowStatus,
        tLiFilterLastChanged          TimeStamp,
        tLiFilterDescription          TItemDescription
    }

tLiFilterType OBJECT-TYPE
    SYNTAX      TFilterType
    MAX-ACCESS  not-accessible
    STATUS      current
    DESCRIPTION
        "The object tLiFilterType specifies the type of this LI filter.

         In this release MAC and IP/IPv6 filters are supported."
    ::= { tLiFilterEntry 1 }

tLiFilterName OBJECT-TYPE
    SYNTAX      TNamedItem
    MAX-ACCESS  not-accessible
    STATUS      current
    DESCRIPTION
        "The object tLiFilterName indicates the unique name of this
         LI Filter."
    ::= { tLiFilterEntry 2 }

tLiFilterRowStatus OBJECT-TYPE
    SYNTAX      RowStatus
    MAX-ACCESS  read-create
    STATUS      current
    DESCRIPTION
        "The object tLiFilterRowStatus specifies the status of this row."
    ::= { tLiFilterEntry 3 }

tLiFilterLastChanged OBJECT-TYPE
    SYNTAX      TimeStamp
    MAX-ACCESS  read-only
    STATUS      current
    DESCRIPTION
        "The object tLiFilterLastChanged indicates the
         sysUpTime at the time of the last modification of this entry.

         If no changes were made to the entry since the last
         re-initialization of the local network management subsystem,
         then this object contains a zero value."
    ::= { tLiFilterEntry 4 }

tLiFilterDescription OBJECT-TYPE
    SYNTAX      TItemDescription
    MAX-ACCESS  read-create
    STATUS      current
    DESCRIPTION
        "The object tLiFilterDescription specifies a description for this
         LI filter."
    DEFVAL { ''H}
    ::= { tLiFilterEntry 5 }

-- --------------------------
--  tLiFilterAssociationTable
-- --------------------------

tLiFilterAssociationTableLastChg OBJECT-TYPE
    SYNTAX      TimeStamp
    MAX-ACCESS  read-only
    STATUS      current
    DESCRIPTION
        "The object tLiFilterAssociationTableLastChg indicates the
        sysUpTime at the time of the last modification
        of tLiFilterAssociationTable.

        If no changes were made to the entry since the last
        re-initialization of the local network management subsystem,
        then this object contains a zero value."
    ::= { tFilterLiObjects 7 }

tLiFilterAssociationTable OBJECT-TYPE
    SYNTAX      SEQUENCE OF TLiFilterAssociationEntry
    MAX-ACCESS  not-accessible
    STATUS      current
    DESCRIPTION
        "The table tLiFilterAssociationTable contains information about
         the associations between LI filters and normal filters."
    ::= { tFilterLiObjects 8 }

tLiFilterAssociationEntry OBJECT-TYPE
    SYNTAX      TLiFilterAssociationEntry
    MAX-ACCESS  not-accessible
    STATUS      current
    DESCRIPTION
        "An association between an LI filter and a normal filter."
    INDEX { tLiFilterType, tLiFilterName, tLiFilterAssociationFltrId }
    ::= { tLiFilterAssociationTable 1 }

TLiFilterAssociationEntry ::=
    SEQUENCE {
        tLiFilterAssociationFltrId    TFilterID,
        tLiFilterAssociationRowStatus RowStatus,
        tLiFilterAssociationLastChg   TimeStamp
    }

tLiFilterAssociationFltrId OBJECT-TYPE
    SYNTAX      TFilterID
    MAX-ACCESS  not-accessible
    STATUS      current
    DESCRIPTION
        "The object tLiFilterAssociationFltrId indicates the id of the normal
         filter in the association described by this entry."
    ::= { tLiFilterAssociationEntry 1 }

tLiFilterAssociationRowStatus OBJECT-TYPE
    SYNTAX      RowStatus
    MAX-ACCESS  read-create
    STATUS      current
    DESCRIPTION
        "The object tLiFilterAssociationRowStatus specifies the status of
         this row."
    ::= { tLiFilterAssociationEntry 2 }

tLiFilterAssociationLastChg OBJECT-TYPE
    SYNTAX      TimeStamp
    MAX-ACCESS  read-only
    STATUS      current
    DESCRIPTION
        "The object tLiFilterAssociationLastChg indicates the
         sysUpTime at the time of the last modification of this entry.

         If no changes were made to the entry since the last
         re-initialization of the local network management subsystem,
         then this object contains a zero value."
     ::= { tLiFilterAssociationEntry 3 }

-- ------------------------
--  tLiMacFilterEntryTable
-- ------------------------

tLiMacFilterParamsTableLastChg OBJECT-TYPE
    SYNTAX      TimeStamp
    MAX-ACCESS  read-only
    STATUS      current
    DESCRIPTION
        "The object tLiMacFilterParamsTableLastChg indicates the
        sysUpTime at the time of the last modification
        of tLiMacFilterParamsTable.

        If no changes were made to the entry since the last
        re-initialization of the local network management subsystem,
        then this object contains a zero value."
    ::= { tFilterLiObjects 9 }

tLiMacFilterParamsTable OBJECT-TYPE
    SYNTAX      SEQUENCE OF TLiMacFilterParamsEntry
    MAX-ACCESS  not-accessible
    STATUS      current
    DESCRIPTION
        "The table tLiMacFilterParamsTable contains all
         LI MAC filter match entries for all LI MAC filters."
    ::= { tFilterLiObjects 10 }

tLiMacFilterParamsEntry OBJECT-TYPE
    SYNTAX      TLiMacFilterParamsEntry
    MAX-ACCESS  not-accessible
    STATUS      current
    DESCRIPTION
        "An LI MAC filter match entry."
    INDEX { tLiFilterType, tLiFilterName, tLiMacFilterParamsId }
    ::= { tLiMacFilterParamsTable 1 }

TLiMacFilterParamsEntry ::=
    SEQUENCE {
        tLiMacFilterParamsId              TEntryId,
        tLiMacFilterParamsRowStatus       RowStatus,
        tLiMacFilterParamsLastChanged     TimeStamp,
        tLiMacFilterParamsDescription     TItemDescription,
        tLiMacFilterParamsFrameType       TFrameType,
        tLiMacFilterParamsSrcMAC          MacAddress,
        tLiMacFilterParamsSrcMACMask      MacAddress,
        tLiMacFilterParamsDstMAC          MacAddress,
        tLiMacFilterParamsDstMACMask      MacAddress,
        tLiMacFilterParamsIngrHitCount    Counter64,
        tLiMacFilterParamsEgrHitCount     Counter64,
        tLiMacFilterParamsIngrHitBytes    Counter64,
        tLiMacFilterParamsEgrHitBytes     Counter64
    }

tLiMacFilterParamsId OBJECT-TYPE
    SYNTAX      TEntryId
    MAX-ACCESS  not-accessible
    STATUS      current
    DESCRIPTION
        "The object tLiMacFilterParamsId indicates the secondary index for
         this entry. Every LI MAC filter may have multiple match entries,
         therefore every LI MAC filter match entry is identified by
         the tLiFilterName and tLiMacFilterParamsId."
    ::= { tLiMacFilterParamsEntry 1 }

tLiMacFilterParamsRowStatus OBJECT-TYPE
    SYNTAX      RowStatus
    MAX-ACCESS  read-create
    STATUS      current
    DESCRIPTION
        "The object tLiMacFilterParamsRowStatus specifies the status
         of this row."
    ::= { tLiMacFilterParamsEntry 2 }

tLiMacFilterParamsLastChanged OBJECT-TYPE
    SYNTAX      TimeStamp
    MAX-ACCESS  read-only
    STATUS      current
    DESCRIPTION
        "The object tLiMacFilterParamsLastChanged indicates the
         sysUpTime at the time of the last modification of this entry.

         If no changes were made to the entry since the last
         re-initialization of the local network management subsystem,
         then this object contains a zero value."
    ::= { tLiMacFilterParamsEntry 3 }

tLiMacFilterParamsDescription OBJECT-TYPE
    SYNTAX      TItemDescription
    MAX-ACCESS  read-create
    STATUS      current
    DESCRIPTION
        "The object tLiMacFilterParamsDescription specifies a description
         for this entry."
    DEFVAL { ''H}
    ::= { tLiMacFilterParamsEntry 4 }

tLiMacFilterParamsFrameType OBJECT-TYPE
    SYNTAX      TFrameType
    MAX-ACCESS  read-create
    STATUS      current
    DESCRIPTION
        "The object tLiMacFilterParamsFrameType specifies the type of
         mac frame for which we are defining this match criterium."
    DEFVAL { e802dot3 }
    ::= { tLiMacFilterParamsEntry 5 }

tLiMacFilterParamsSrcMAC OBJECT-TYPE
    SYNTAX      MacAddress
    MAX-ACCESS  read-create
    STATUS      current
    DESCRIPTION
        "The object tLiMacFilterParamsSrcMAC specifies the source MAC
         address to match for this LI MAC filter entry."
    DEFVAL { '000000000000'H }
    ::= { tLiMacFilterParamsEntry 6 }

tLiMacFilterParamsSrcMACMask OBJECT-TYPE
    SYNTAX      MacAddress
    MAX-ACCESS  read-create
    STATUS      current
    DESCRIPTION
        "The object tLiMacFilterParamsSrcMACMask specifies
         the source MAC mask value for this LI MAC filter match entry.
         The mask is ANDed with the MAC to match tLiMacFilterParamsSrcMAC.
         A zero bit means ignore this bit, do not match. A one bit means
         match this bit with tLiMacFilterParamsSrcMAC.
         Use the value 00-00-00-00-00-00 to disable this filter criterium.
         If set to all zero, the value of tLiMacFilterParamsSrcMAC will
         bet set to all zero by the system, and any attept to change this
         value will be ignored."
    DEFVAL { '000000000000'H }
    ::= { tLiMacFilterParamsEntry 7 }

tLiMacFilterParamsDstMAC OBJECT-TYPE
    SYNTAX      MacAddress
    MAX-ACCESS  read-create
    STATUS      current
    DESCRIPTION
        "The object tLiMacFilterParamsDstMAC specifies the destination MAC
         to match for this LI MAC filter entry."
    DEFVAL { '000000000000'H }
    ::= { tLiMacFilterParamsEntry 8 }

tLiMacFilterParamsDstMACMask OBJECT-TYPE
    SYNTAX      MacAddress
    MAX-ACCESS  read-create
    STATUS      current
    DESCRIPTION
        "The object tLiMacFilterParamsDstMACMask specifies the
         destination MAC mask value for this LI MAC filter match entry.
         The mask is ANDed with the MAC to match tLiMacFilterParamsDstMAC.
         A zero bit means ignore this bit, do not match.  a one bit means
         match this bit with tLiMacFilterParamsDstMAC.
         Use the value 00-00-00-00-00-00 to disable this filter criteria.
         If set to all zero, the value of tLiMacFilterParamsDstMAC will
         bet set to all zero by the system, and any attept to change this
         value will be ignored."
    DEFVAL { '000000000000'H }
    ::= { tLiMacFilterParamsEntry 9 }

tLiMacFilterParamsIngrHitCount OBJECT-TYPE
    SYNTAX      Counter64
    MAX-ACCESS  read-only
    STATUS      current
    DESCRIPTION
        "The object tLiMacFilterParamsIngrHitCount indicates the number of
         times an ingress packet matched this entry."
    ::= { tLiMacFilterParamsEntry 10 }

tLiMacFilterParamsEgrHitCount OBJECT-TYPE
    SYNTAX      Counter64
    MAX-ACCESS  read-only
    STATUS      current
    DESCRIPTION
        "This object tLiMacFilterParamsEgrHitCount indicates the number of
         times an egress packet matched this entry."
    ::= { tLiMacFilterParamsEntry 11 }

tLiMacFilterParamsIngrHitBytes OBJECT-TYPE
    SYNTAX      Counter64
    MAX-ACCESS  read-only
    STATUS      current
    DESCRIPTION
        "The value of tLiMacFilterParamsIngrHitBytes indicates the number
         of bytes of all ingress packets that matched this entry."
    ::= { tLiMacFilterParamsEntry 12 }

tLiMacFilterParamsEgrHitBytes OBJECT-TYPE
    SYNTAX      Counter64
    MAX-ACCESS  read-only
    STATUS      current
    DESCRIPTION
        "The value of tLiMacFilterParamsEgrHitBytes indicates the number
         of bytes of all egress packets that matched this entry."
    ::= { tLiMacFilterParamsEntry 13 }
      
-- ------------------------
--  tLiIpFilterParamsTable
-- ------------------------
  
tLiIpFilterParamsTableLastChg OBJECT-TYPE
    SYNTAX      TimeStamp
    MAX-ACCESS  read-only
    STATUS      current
    DESCRIPTION
        "The value of the object tLiIpFilterParamsTableLastChg 
         indicates the sysUpTime at the time of the last modification
         of tLiIpFilterParamsTable.
 
         If no changes were made to the table since the last
         re-initialization of the local network management subsystem,
         then this object contains a zero value."
    ::= { tFilterLiObjects 15 }    

tLiIpFilterParamsTable OBJECT-TYPE
    SYNTAX      SEQUENCE OF TLiIPFilterParamsEntry
    MAX-ACCESS  not-accessible
    STATUS      current
    DESCRIPTION
        "The table tLiIpFilterParamsTable contains information pertaining 
         to match entries of LI IP/IPv6 filters."
    ::= { tFilterLiObjects 16 }
      
tLiIpFilterParamsEntry OBJECT-TYPE
    SYNTAX      TLiIPFilterParamsEntry
    MAX-ACCESS  not-accessible
    STATUS      current
    DESCRIPTION
        "Each entry represents a configuration of an LI IP/IPv6 filter entry.
        
         Entries can be created and deleted via SNMP SET operations 
         to tLiIpFilterParamsRowStatus."
    INDEX { tLiFilterType, 
            tLiFilterName, 
            tLiIpFilterParamsId }
    ::= { tLiIpFilterParamsTable 1 }

TLiIPFilterParamsEntry ::=
    SEQUENCE {
        tLiIpFilterParamsId                 TEntryId,
        tLiIpFilterParamsLastChanged        TimeStamp,
        tLiIpFilterParamsRowStatus          RowStatus,
        tLiIpFilterParamsDescription        TItemDescription,
        tLiIpFilterParamsSrcIpAddrType      InetAddressType,
        tLiIpFilterParamsSrcIpAddr          InetAddress,
        tLiIpFilterParamsSrcIpFullMask      InetAddress,
        tLiIpFilterParamsDstIpAddrType      InetAddressType,
        tLiIpFilterParamsDstIpAddr          InetAddress,
        tLiIpFilterParamsDstIpFullMask      InetAddress,
        tLiIpFilterParamsProtocolNextHdr    TIpProtocol,
        tLiIpFilterParamsSrcPortValue1      TTcpUdpPort,
        tLiIpFilterParamsSrcPortValue2      TTcpUdpPort,
        tLiIpFilterParamsSrcPortOper        TTcpUdpPortOperator,
        tLiIpFilterParamsDstPortValue1      TTcpUdpPort,
        tLiIpFilterParamsDstPortValue2      TTcpUdpPort,
        tLiIpFilterParamsDstPortOper        TTcpUdpPortOperator
    }

tLiIpFilterParamsId OBJECT-TYPE
    SYNTAX      TEntryId
    MAX-ACCESS  not-accessible
    STATUS      current
    DESCRIPTION
        "The value of the object tLiIpFilterParamsId indicates the tertiary 
         index for tLiIpFilterParamsEntry. 
         
         Every LI IP filter may have multiple match entries 
         therefore every entry is identified by the values 
         of tLiFilterType, tLiFilterName and tLiIpFilterParamsId."
    ::= { tLiIpFilterParamsEntry 1 }

tLiIpFilterParamsLastChanged OBJECT-TYPE
    SYNTAX      TimeStamp
    MAX-ACCESS  read-only
    STATUS      current
    DESCRIPTION
        "The value of the object tLiIpFilterParamsLastChanged indicates 
         the sysUpTime at the time of the last modification of this entry.

         If no changes were made to the entry since the last
         re-initialization of the local network management subsystem,
         then this object contains a zero value."
    ::= { tLiIpFilterParamsEntry 2 }

tLiIpFilterParamsRowStatus OBJECT-TYPE
    SYNTAX      RowStatus
    MAX-ACCESS  read-create
    STATUS      current
    DESCRIPTION
        "The value of the object tLiIpFilterParamsRowStatus specifies 
         the status of this row in tLiIpFilterParamsTable."
    ::= { tLiIpFilterParamsEntry 3 }

tLiIpFilterParamsDescription OBJECT-TYPE
    SYNTAX      TItemDescription
    MAX-ACCESS  read-create
    STATUS      current
    DESCRIPTION
        "The value of the object tLiIpFilterParamsDescription specifies 
         the description for this LI IP filter entry."
    DEFVAL { ''H}
    ::= { tLiIpFilterParamsEntry 4 }

tLiIpFilterParamsSrcIpAddrType OBJECT-TYPE
    SYNTAX      InetAddressType 
    MAX-ACCESS  read-create
    STATUS      current
    DESCRIPTION
        "The value of the object tLiIpFilterParamsSrcIpAddrType specifies
         the context in which the values of the objects 
         tLiIpFilterParamsSrcIpAddr and tLiIpFilterParamsSrcIpFullMask 
         are interpreted.
        
         Only following values are supported:
            unknown(0)
            ipv4(1)
            ipv6(2)
         
         Furthermore the value must be consistent with the filter type given 
         by the value of the index object tLiFilterType.
         
         If the value of this object is set to 'unknown' then the values
         of the objects tLiIpFilterParamsSrcIpAddr and 
         tLiIpFilterParamsSrcIpFullMask are automatically set
         to their default values."
    DEFVAL { unknown }
    ::= { tLiIpFilterParamsEntry 5 }
      
tLiIpFilterParamsSrcIpAddr OBJECT-TYPE
    SYNTAX      InetAddress (SIZE (0|4|16))
    MAX-ACCESS  read-create
    STATUS      current
    DESCRIPTION
        "The value of the object tLiIpFilterParamsSrcIpAddr specifies 
         the source IP address to be matched by this LI IP filter entry.
         
         The value must be consistent with the IP version value of
         the associated tLiIpFilterParamsSrcIpAddrType object.
         
         If the value of the object tLiIpFilterParamsSrcIpAddrType is set
         to 'unknown' then the value of this object is automatically set 
         to the default value."
    DEFVAL { ''H }
    ::= { tLiIpFilterParamsEntry 6 }

tLiIpFilterParamsSrcIpFullMask OBJECT-TYPE
    SYNTAX      InetAddress (SIZE (0|4|16))
    MAX-ACCESS  read-create
    STATUS      current
    DESCRIPTION
        "The value of the object tLiIpFilterParamsSrcIpFullMask specifies 
         the IP mask value that is ANDed with the received source 
         IP address to match the value in tLiIpFilterParamsSrcIpAddr.

         The value must be consistent with the IP version value of
         the associated tLiIpFilterParamsSrcIpAddrType object 
         and must not be equal to zero. 
         
         If the value of the object tLiIpFilterParamsSrcIpAddrType is set
         to 'unknown' then the value of this object is automatically set 
         to the default value."
    DEFVAL { ''H }
    ::= { tLiIpFilterParamsEntry 7 }

  tLiIpFilterParamsDstIpAddrType OBJECT-TYPE
    SYNTAX      InetAddressType 
    MAX-ACCESS  read-create
    STATUS      current
    DESCRIPTION
        "The value of the object tLiIpFilterParamsDstIpAddrType specifies
         the context in which the values of the objects 
         tLiIpFilterParamsDstIpAddr and tLiIpFilterParamsDstIpFullMask 
         are interpreted.
         
         Only following values are supported:
            unknown(0)
            ipv4(1)
            ipv6(2)

         Furthermore the value must always be consistent with the filter type 
         given by the value of the index object tLiFilterType.
         
         If the value of this object is set to 'unknown' then the values
         of the objects tLiIpFilterParamsDstIpAddr and 
         tLiIpFilterParamsDstIpFullMask are automatically set
         to their default values."
    DEFVAL { unknown }
    ::= { tLiIpFilterParamsEntry 8 }
      
tLiIpFilterParamsDstIpAddr OBJECT-TYPE
    SYNTAX      InetAddress (SIZE (0|4|16))
    MAX-ACCESS  read-create
    STATUS      current
    DESCRIPTION
        "The value of the object tLiIpFilterParamsDstIpAddr specifies 
         the destination IP address to be matched by this LI IP filter entry.
         
         The value must be consistent with the IP version value of
         the associated tLiIpFilterParamsDstIpAddrType object.
         
         If the value of the object tLiIpFilterParamsDstIpAddrType is set
         to 'unknown' then the value of this object is automatically set 
         to the default value."
    DEFVAL { ''H }
    ::= { tLiIpFilterParamsEntry 9 }

tLiIpFilterParamsDstIpFullMask OBJECT-TYPE
    SYNTAX      InetAddress (SIZE (0|4|16))
    MAX-ACCESS  read-create
    STATUS      current
    DESCRIPTION
        "The value of the object tLiIpFilterParamsDstIpFullMask specifies 
         the IP mask value that is ANDed with the received destination 
         IP address to match the value in tLiIpFilterParamsDstIpAddr.

         The value must be consistent with the IP version value of
         the associated tLiIpFilterParamsDstIpAddrType object 
         and must not be equal to zero.
         
         If the value of the object tLiIpFilterParamsDstIpAddrType is set
         to 'unknown' then the value of this object is automatically set 
         to the default value."
    DEFVAL { ''H }
    ::= { tLiIpFilterParamsEntry 10 }

tLiIpFilterParamsProtocolNextHdr OBJECT-TYPE
    SYNTAX      TIpProtocol
    MAX-ACCESS  read-create
    STATUS      current
    DESCRIPTION
        "The value of the object tLiIpFilterParamsProtocolNextHdr specifies
         (depending on the filter type defined by the value of the object 
         tLiFilterType) the IP protocol / IPv6 next-header value to be matched 
         by this LI IP filter entry.
        
         The value must be set to -1 to disable the protocol / next-header 
         matching.
         
         Because the match criteria only pertains to the last next-header, 
         the following values are not accepted as IPv6 next-header values: 
         0, 43, 44, 50, 51, and 60."
    DEFVAL { -1 }
    ::= { tLiIpFilterParamsEntry 11 }
    
tLiIpFilterParamsSrcPortValue1 OBJECT-TYPE
    SYNTAX      TTcpUdpPort
    MAX-ACCESS  read-create
    STATUS      current
    DESCRIPTION
        "The value of the object tLiIpFilterParamsSrcPortValue1 specifies 
         the TCP/UDP source port value1. It is used as per the description 
         of tLiIpFilterParamsSrcPortOper."
    DEFVAL { 0 }
    ::= { tLiIpFilterParamsEntry 12 }

tLiIpFilterParamsSrcPortValue2 OBJECT-TYPE
    SYNTAX      TTcpUdpPort
    MAX-ACCESS  read-create
    STATUS      current
    DESCRIPTION
        "The value of the object tLiIpFilterParamsSrcPortValue2 specifies 
         the TCP/UDP source port value2. It is used as per the description 
         of tLiIpFilterParamsSrcPortOper."
    DEFVAL { 0 }
    ::= { tLiIpFilterParamsEntry 13 }

tLiIpFilterParamsSrcPortOper OBJECT-TYPE
    SYNTAX      TTcpUdpPortOperator
    MAX-ACCESS  read-create
    STATUS      current
    DESCRIPTION
        "The value of the object tLiIpFilterParamsSrcPortOper specifies
         the manner in which tLiIpFilterParamsSrcPortValue1 and 
         tLiIpFilterParamsSrcPortValue2 are to be used. The values of these 
         latter 2 objects and tLiIpFilterParamsSrcPortOper are used 
         as per the description of TTcpUdpPortOperator."
    DEFVAL { none }
    ::= { tLiIpFilterParamsEntry 14 }

tLiIpFilterParamsDstPortValue1 OBJECT-TYPE
    SYNTAX      TTcpUdpPort
    MAX-ACCESS  read-create
    STATUS      current
    DESCRIPTION
        "The value of the object tLiIpFilterParamsDstPortValue1 specifies 
         the TCP/UDP destination port value1. It is used as per the description 
         of tLiIpFilterParamsDstPortOper."
    DEFVAL { 0 }
    ::= { tLiIpFilterParamsEntry 15 }

tLiIpFilterParamsDstPortValue2 OBJECT-TYPE
    SYNTAX      TTcpUdpPort
    MAX-ACCESS  read-create
    STATUS      current
    DESCRIPTION
        "The value of the object tLiIpFilterParamsDstPortValue2 specifies 
         the TCP/UDP destination port value2. It is used as per the description 
         of tLiIpFilterParamsDstPortOper."
    DEFVAL { 0 }
    ::= { tLiIpFilterParamsEntry 16 }

tLiIpFilterParamsDstPortOper OBJECT-TYPE
    SYNTAX      TTcpUdpPortOperator
    MAX-ACCESS  read-create
    STATUS      current
    DESCRIPTION
        "The value of the object tLiIpFilterParamsDstPortOper specifies
         the manner in which tLiIpFilterParamsDstPortValue1 and 
         tLiIpFilterParamsDstPortValue2 are to be used. The values of these 
         latter 2 objects and tLiIpFilterParamsDstPortOper are used 
         as per the description in TTcpUdpPortOperator."
    DEFVAL { none }
    ::= { tLiIpFilterParamsEntry 17 }

-- ----------------------------
--  tLiIpFilterParamsInfoTable
-- ----------------------------

tLiIpFilterParamsInfoTable OBJECT-TYPE
    SYNTAX      SEQUENCE OF TLiIPFilterParamsInfoEntry
    MAX-ACCESS  not-accessible
    STATUS      current
    DESCRIPTION
        "The table tLiIpFilterParamsInfoTable contains read-only information
         pertaining to LI IP filter match entries of LI IP filters."
    ::= { tFilterLiObjects 17 }

tLiIpFilterParamsInfoEntry OBJECT-TYPE
    SYNTAX      TLiIPFilterParamsInfoEntry
    MAX-ACCESS  not-accessible
    STATUS      current
    DESCRIPTION
        "This row complements the corresponding row in the 
         tLiIpFilterParamsTable with read-only operational info.
        
         Entries are created and deleted automatically by the system 
         when a corresponding entry in tLiIpFilterParamsTable is 
         created / deleted."
    AUGMENTS {tLiIpFilterParamsEntry}
    ::= { tLiIpFilterParamsInfoTable 1 }

TLiIPFilterParamsInfoEntry ::=
    SEQUENCE {
        tLiIpFltrParamsInfIngrHitCount       Counter64,
        tLiIpFltrParamsInfEgrHitCount        Counter64,
        tLiIpFltrParamsInfIngrHitBytes       Counter64,
        tLiIpFltrParamsInfEgrHitBytes        Counter64
    }

tLiIpFltrParamsInfIngrHitCount OBJECT-TYPE
    SYNTAX      Counter64
    MAX-ACCESS  read-only
    STATUS      current
    DESCRIPTION
        "The value of the object tLiIpFltrParamsInfIngrHitCount indicates 
         the number of times an ingress packet matched this entry."
    ::= { tLiIpFilterParamsInfoEntry 1 }

tLiIpFltrParamsInfEgrHitCount OBJECT-TYPE
    SYNTAX      Counter64
    MAX-ACCESS  read-only
    STATUS      current
    DESCRIPTION
        "The value of the object tLiIpFltrParamsInfEgrHitCount indicates 
         the number of times an egress packet matched this entry."
    ::= { tLiIpFilterParamsInfoEntry 2 }

tLiIpFltrParamsInfIngrHitBytes OBJECT-TYPE
    SYNTAX      Counter64
    MAX-ACCESS  read-only
    STATUS      current
    DESCRIPTION
        "The value of the object tLiIpFltrParamsInfIngrHitBytes indicates 
         the number of bytes of all ingress packets that matched this entry."
    ::= { tLiIpFilterParamsInfoEntry 3 }

tLiIpFltrParamsInfEgrHitBytes OBJECT-TYPE
    SYNTAX      Counter64
    MAX-ACCESS  read-only
    STATUS      current
    DESCRIPTION
        "The value of the object tLiIpFltrParamsInfEgrHitBytes indicates 
         the number of bytes of all egress packets that matched this entry."
    ::= { tLiIpFilterParamsInfoEntry 4 }
     
-- ------------------------
--  tFilterPrefixListTable
-- ------------------------

tFilterPrefixListTableLstChng OBJECT-TYPE
    SYNTAX      TimeStamp
    MAX-ACCESS  read-only
    STATUS      current
    DESCRIPTION
        "The object tFilterPrefixListTableLstChng indicates the
        sysUpTime at the time of the last modification
        of tFilterPrefixListTable.

        If no changes were made to the table since the last
        re-initialization of the local network management subsystem,
        this object contains the value zero."
    ::= {  tFilterObjects 32 }

tFilterPrefixListTable OBJECT-TYPE
    SYNTAX      SEQUENCE OF TFilterPrefixListEntry
    MAX-ACCESS  not-accessible
    STATUS      current
    DESCRIPTION
        "The table tFilterPrefixListTable contains an entry
         for each prefix list defined in the filter area."
    ::= { tFilterObjects 33 }

tFilterPrefixListEntry OBJECT-TYPE
    SYNTAX      TFilterPrefixListEntry
    MAX-ACCESS  not-accessible
    STATUS      current
    DESCRIPTION
        "An entry in the tFilterPrefixListTable."
    INDEX {tFilterPrefixListType,
           IMPLIED tFilterPrefixListName }
    ::= { tFilterPrefixListTable 1 }

TFilterPrefixListEntry ::=
    SEQUENCE {
        tFilterPrefixListType            TFltrPrefixListType,
        tFilterPrefixListName            TNamedItem,
        tFilterPrefixListRowStatus       RowStatus,
        tFilterPrefixListLastChanged     TimeStamp,
        tFilterPrefixListDescription     TItemDescription
    }

tFilterPrefixListType OBJECT-TYPE
    SYNTAX      TFltrPrefixListType
    MAX-ACCESS  not-accessible
    STATUS      current
    DESCRIPTION
        "The object tFilterPrefixListType specifies the type
         of prefix list for the prefix list tFilterPrefixListName."
    ::= { tFilterPrefixListEntry 1 }

tFilterPrefixListName OBJECT-TYPE
    SYNTAX      TNamedItem
    MAX-ACCESS  not-accessible
    STATUS      current
    DESCRIPTION
        "The object tFilterPrefixListName specifies the name
         given to this prefix list."
    ::= { tFilterPrefixListEntry 2 }

tFilterPrefixListRowStatus OBJECT-TYPE
    SYNTAX      RowStatus
    MAX-ACCESS  read-create
    STATUS      current
    DESCRIPTION
        "The object tFilterPrefixListRowStatus specifies the status
         of this row."
    ::= { tFilterPrefixListEntry 3 }

tFilterPrefixListLastChanged OBJECT-TYPE
    SYNTAX      TimeStamp
    MAX-ACCESS  read-only
    STATUS      current
    DESCRIPTION
        "The object tFilterPrefixListLastChanged indicates the
         sysUpTime at the time of the last modification of this row.

         If no changes were made to the row since the last
         re-initialization of the local network management subsystem,
         then this object contains the value zero."
    ::= { tFilterPrefixListEntry 4 }

tFilterPrefixListDescription OBJECT-TYPE
    SYNTAX      TItemDescription
    MAX-ACCESS  read-create
    STATUS      current
    DESCRIPTION
        "The object tFilterPrefixListDescription specifies a description
         for this row."
    DEFVAL { ''H}
    ::= { tFilterPrefixListEntry 5 }

-- ----------------------------
--  tFilterPrefixListEntryTable
-- ----------------------------

tFilterPrefixListEntryTblLstChg OBJECT-TYPE
    SYNTAX      TimeStamp
    MAX-ACCESS  read-only
    STATUS      current
    DESCRIPTION
        "The object tFilterPrefixListEntryTblLstChg indicates the
        sysUpTime at the time of the last modification
        of tFilterPrefixListEntryTable.

        If no changes were made to the table since the last
        re-initialization of the local network management subsystem,
        this object contains the value zero."
    ::= {  tFilterObjects 34 }

tFilterPrefixListEntryTable OBJECT-TYPE
    SYNTAX      SEQUENCE OF TFilterPrefixListEntryEntry
    MAX-ACCESS  not-accessible
    STATUS      current
    DESCRIPTION
        "The table tFilterPrefixListEntryTable contains an entry
         for each prefix defined in any prefix list
         defined in the filter area."
    ::= { tFilterObjects 35 }

tFilterPrefixListEntryEntry OBJECT-TYPE
    SYNTAX      TFilterPrefixListEntryEntry
    MAX-ACCESS  not-accessible
    STATUS      current
    DESCRIPTION
        "An entry in the tFilterPrefixListEntryTable."
    INDEX {tFilterPrefixListType,
           tFilterPrefixListName,
           tFilterPrefixListEntryPrefixType,
           tFilterPrefixListEntryPrefix,
           tFilterPrefixListEntryPrefixLen}
    ::= { tFilterPrefixListEntryTable 1 }

TFilterPrefixListEntryEntry ::=
    SEQUENCE {
        tFilterPrefixListEntryPrefixType InetAddressType,
        tFilterPrefixListEntryPrefix     InetAddress,
        tFilterPrefixListEntryPrefixLen  InetAddressPrefixLength,
        tFilterPrefixListEntryRowStatus  RowStatus
    }

tFilterPrefixListEntryPrefixType OBJECT-TYPE
    SYNTAX      InetAddressType
    MAX-ACCESS  not-accessible
    STATUS      current
    DESCRIPTION
        "The object tFilterPrefixListEntryPrefixType specifies whether the
         prefix specified in tFilterPrefixListEntryPrefix is an IPv4 or IPv6
         prefix.

         The value of tFilterPrefixListEntryPrefixType must match the value
         of the object tFilterPrefixListType."
    ::= { tFilterPrefixListEntryEntry 1 }

tFilterPrefixListEntryPrefix OBJECT-TYPE
    SYNTAX      InetAddress (SIZE (4|16))
    MAX-ACCESS  not-accessible
    STATUS      current
    DESCRIPTION
        "The value of tFilterPrefixListEntryPrefix specifies
         the IP prefix of this prefix list entry."
    ::= { tFilterPrefixListEntryEntry 2 }

tFilterPrefixListEntryPrefixLen OBJECT-TYPE
    SYNTAX      InetAddressPrefixLength
    MAX-ACCESS  not-accessible
    STATUS      current
    DESCRIPTION
        "The value of tFilterPrefixListEntryPrefixLen specifiesd
         the IP prefix length of this prefix list entry."
    ::= { tFilterPrefixListEntryEntry 3 }

tFilterPrefixListEntryRowStatus OBJECT-TYPE
    SYNTAX      RowStatus
    MAX-ACCESS  read-create
    STATUS      current
    DESCRIPTION
        "The object tFilterPrefixListEntryRowStatus specifies the status
         of this row."
    ::= { tFilterPrefixListEntryEntry 4 }

-- ----------------------------
--  tFilterEmbeddedRefTable
-- ----------------------------
tFilterEmbeddedRefTableLstChg OBJECT-TYPE
    SYNTAX      TimeStamp
    MAX-ACCESS  read-only
    STATUS      current
    DESCRIPTION
        "The object tFilterEmbeddedRefTableLstChg indicates the
        sysUpTime at the time of the last modification
        of tFilterPrefixListEntryTable.

        If no changes were made to the table since the last
        re-initialization of the local network management subsystem,
        this object contains the value zero."
    ::= {  tFilterObjects 36 }

tFilterEmbeddedRefTable OBJECT-TYPE
    SYNTAX      SEQUENCE OF TFilterEmbeddedRefTableEntry
    MAX-ACCESS  not-accessible
    STATUS      current
    DESCRIPTION
        "The table tFilterEmbeddedRefTable contains an entry
         for each embedded filter inserted in a normal filter."
    ::= { tFilterObjects 37 }

tFilterEmbeddedRefTableEntry OBJECT-TYPE
    SYNTAX      TFilterEmbeddedRefTableEntry
    MAX-ACCESS  not-accessible
    STATUS      current
    DESCRIPTION
        "An entry in the tFilterPrefixListEntryTable."
    INDEX {tFilterEmbeddedRefFilterType,
           tFilterEmbeddedRefInsertFltrId,
           tFilterEmbeddedRefEmbeddedFltrId,
           tFilterEmbeddedRefOffset}
    ::= { tFilterEmbeddedRefTable 1 }

TFilterEmbeddedRefTableEntry ::=
    SEQUENCE {
        tFilterEmbeddedRefFilterType     TFilterType,
        tFilterEmbeddedRefInsertFltrId   TFilterID,
        tFilterEmbeddedRefEmbeddedFltrId TFilterID,
        tFilterEmbeddedRefOffset         Unsigned32,
        tFilterEmbeddedRefRowStatus      RowStatus,
        tFilterEmbeddedRefAdminState     INTEGER,
        tFilterEmbeddedRefOperState      TmnxEmbeddedFltrOperState
    }

tFilterEmbeddedRefFilterType OBJECT-TYPE
    SYNTAX      TFilterType
    MAX-ACCESS  not-accessible
    STATUS      current
    DESCRIPTION
        "The object tFilterEmbeddedRefFilterType specifies the type of filter
         for the filters specified by tFilterEmbeddedRefEmbeddedFltrId and
         tFilterEmbeddedRefInsertFltrId."
    ::= { tFilterEmbeddedRefTableEntry 1 }

tFilterEmbeddedRefInsertFltrId OBJECT-TYPE
    SYNTAX      TFilterID
    MAX-ACCESS  not-accessible
    STATUS      current
    DESCRIPTION
        "The value of tFilterEmbeddedRefInsertFltrId specifies the filter
         where the filter specified by tFilterEmbeddedRefEmbeddedFltrId
         is to be inserted."
    ::= { tFilterEmbeddedRefTableEntry 2 }

tFilterEmbeddedRefEmbeddedFltrId OBJECT-TYPE
    SYNTAX      TFilterID
    MAX-ACCESS  not-accessible
    STATUS      current
    DESCRIPTION
        "The value of tFilterEmbeddedRefEmbeddedFltrId specifies
         the id of the filter to be inserted in the filter specified
         by tFilterEmbeddedRefInsertFltrId."
    ::= { tFilterEmbeddedRefTableEntry 3 }

tFilterEmbeddedRefOffset OBJECT-TYPE
    SYNTAX      Unsigned32 (0..65535)
    MAX-ACCESS  not-accessible
    STATUS      current
    DESCRIPTION
        "The value of tFilterEmbeddedRefOffset specifies the offset of
         inserting entries. An entry at position x in the embedded filter will 
         be inserted at position x + offset in the embedding filter."
    DEFVAL { 0 }
    ::= { tFilterEmbeddedRefTableEntry 4 }

tFilterEmbeddedRefRowStatus OBJECT-TYPE
    SYNTAX      RowStatus
    MAX-ACCESS  read-create
    STATUS      current
    DESCRIPTION
        "The object tFilterEmbeddedRefRowStatus specifies the status
         of this row."
    ::= { tFilterEmbeddedRefTableEntry 5 }
    
tFilterEmbeddedRefAdminState OBJECT-TYPE
    SYNTAX      INTEGER {
                   inactive  (0),
                   active    (1)
                }
    MAX-ACCESS  read-create
    STATUS      current
    DESCRIPTION
        "The value of tFilterEmbeddedRefAdminState indicates the administrative
         state of the embed request defined by this row. 
         
         If an active embedding cannot be fullfilled due to dynamic events, this 
         object will be set to 'inactive' automatically by the system. In those 
         cases, the object tFilterEmbeddedRefOperState will indicate the failure
         reason."
    DEFVAL { active }
    ::= { tFilterEmbeddedRefTableEntry 6 }    

tFilterEmbeddedRefOperState OBJECT-TYPE
    SYNTAX      TmnxEmbeddedFltrOperState
    MAX-ACCESS  read-only
    STATUS      current
    DESCRIPTION
        "The value of tFilterEmbeddedRefOperState indicates the operational
         state of the embed request defined by this row."
    ::= { tFilterEmbeddedRefTableEntry 7 }

-- ------------------------
--  tFilterPortListTable
-- ------------------------

tFilterPortListTableLstChng OBJECT-TYPE
    SYNTAX      TimeStamp
    MAX-ACCESS  read-only
    STATUS      current
    DESCRIPTION
        "The object tFilterPortListTableLstChng indicates the
        sysUpTime at the time of the last modification
        of tFilterPortListTable.

        If no changes were made to the table since the last
        re-initialization of the local network management subsystem,
        this object contains the value zero."
    ::= {  tFilterObjects 38 }

tFilterPortListTable OBJECT-TYPE
    SYNTAX      SEQUENCE OF TFilterPortListEntry
    MAX-ACCESS  not-accessible
    STATUS      current
    DESCRIPTION
        "The table tFilterPortListTable contains an entry
         for each port list defined in the filter area."
    ::= { tFilterObjects 39 }

tFilterPortListEntry OBJECT-TYPE
    SYNTAX      TFilterPortListEntry
    MAX-ACCESS  not-accessible
    STATUS      current
    DESCRIPTION
        "An entry in the tFilterPortListTable."
    INDEX { IMPLIED tFilterPortListName }
    ::= { tFilterPortListTable 1 }

TFilterPortListEntry ::=
    SEQUENCE {
        tFilterPortListName            TNamedItem,
        tFilterPortListRowStatus       RowStatus,
        tFilterPortListLastChanged     TimeStamp,
        tFilterPortListDescription     TItemDescription
    }

tFilterPortListName OBJECT-TYPE
    SYNTAX      TNamedItem
    MAX-ACCESS  not-accessible
    STATUS      current
    DESCRIPTION
        "The object tFilterPortListName specifies the name
         given to this port list."
    ::= { tFilterPortListEntry 1 }

tFilterPortListRowStatus OBJECT-TYPE
    SYNTAX      RowStatus
    MAX-ACCESS  read-create
    STATUS      current
    DESCRIPTION
        "The object tFilterPortListRowStatus specifies the status
         of this row."
    ::= { tFilterPortListEntry 2 }

tFilterPortListLastChanged OBJECT-TYPE
    SYNTAX      TimeStamp
    MAX-ACCESS  read-only
    STATUS      current
    DESCRIPTION
        "The object tFilterPortListLastChanged indicates the
         sysUpTime at the time of the last modification of this row.

         If no changes were made to the row since the last
         re-initialization of the local network management subsystem,
         then this object contains the value zero."
    ::= { tFilterPortListEntry 3 }

tFilterPortListDescription OBJECT-TYPE
    SYNTAX      TItemDescription
    MAX-ACCESS  read-create
    STATUS      current
    DESCRIPTION
        "The object tFilterPortListDescription specifies a description
         for this row."
    DEFVAL { ''H}
    ::= { tFilterPortListEntry 4 }

-- ----------------------------
--  tFilterPortListEntryTable
-- ----------------------------

tFilterPortListEntryTblLstChg OBJECT-TYPE
    SYNTAX      TimeStamp
    MAX-ACCESS  read-only
    STATUS      current
    DESCRIPTION
        "The object tFilterPortListEntryTblLstChg indicates the
        sysUpTime at the time of the last modification
        of tFilterPortListEntryTable.

        If no changes were made to the table since the last
        re-initialization of the local network management subsystem,
        this object contains the value zero."
    ::= {  tFilterObjects 40 }

tFilterPortListEntryTable OBJECT-TYPE
    SYNTAX      SEQUENCE OF TFilterPortListEntryEntry
    MAX-ACCESS  not-accessible
    STATUS      current
    DESCRIPTION
        "The table tFilterPortListEntryTable contains an entry
         for each port defined in any port list
         defined in the filter area."
    ::= { tFilterObjects 41 }

tFilterPortListEntryEntry OBJECT-TYPE
    SYNTAX      TFilterPortListEntryEntry
    MAX-ACCESS  not-accessible
    STATUS      current
    DESCRIPTION
        "Specifies an entry in the tFilterPortListEntryTable.
         Two entries for the same port list must not overlap."
    INDEX { tFilterPortListName,
            tFilterPortListEntryPortLow,
            tFilterPortListEntryPortHigh }
    ::= { tFilterPortListEntryTable 1 }

TFilterPortListEntryEntry ::=
    SEQUENCE {
        tFilterPortListEntryPortLow   TTcpUdpPort,
        tFilterPortListEntryPortHigh  TTcpUdpPort,
        tFilterPortListEntryRowStatus RowStatus
    }

tFilterPortListEntryPortLow OBJECT-TYPE
    SYNTAX      TTcpUdpPort
    MAX-ACCESS  not-accessible
    STATUS      current
    DESCRIPTION
        "This object specifies the lower value for the TCP/UDP port range.
        A value assigned to this object must be less than or equal to the
        value assigned to the corresponding object
        tFilterPortListEntryPortHigh."
    DEFVAL { 0 }
    ::= { tFilterPortListEntryEntry 1 }

tFilterPortListEntryPortHigh OBJECT-TYPE
    SYNTAX      TTcpUdpPort
    MAX-ACCESS  not-accessible
    STATUS      current
    DESCRIPTION
        "This object specifies the higher value for the TCP/UDP port range.
         A value assigned to this object must be greater than or equal to the
         value assigned to the corresponding object
         tFilterPortListEntryPortLow."
    DEFVAL { 65535 }
    ::= { tFilterPortListEntryEntry 2 }

tFilterPortListEntryRowStatus OBJECT-TYPE
    SYNTAX      RowStatus
    MAX-ACCESS  read-create
    STATUS      current
    DESCRIPTION
        "The object tFilterPortListEntryRowStatus specifies the status of this
         row."
    ::= { tFilterPortListEntryEntry 3 }


-- -------------------------
--  tPrefixListApplyPathTable
-- -------------------------

tFilterApplyPathTableLstChng OBJECT-TYPE
    SYNTAX      TimeStamp
    MAX-ACCESS  read-only
    STATUS      current
    DESCRIPTION
        "The object tFilterApplyPathTableLstChng indicates the
        sysUpTime at the time of the last modification
        of tFilterApplyPathTable.

        If no changes were made to the table since the last
        re-initialization of the local network management subsystem,
        this object contains the value zero."
    ::= {  tFilterObjects 42 }

tFilterApplyPathTable OBJECT-TYPE
    SYNTAX      SEQUENCE OF TFilterApplyPathEntry
    MAX-ACCESS  not-accessible
    STATUS      current
    DESCRIPTION
        "The table tFilterApplyPathTable contains an entry
         for each apply-path rule defined in a prefix-list."
    ::= { tFilterObjects 43 }

tFilterApplyPathEntry OBJECT-TYPE
    SYNTAX      TFilterApplyPathEntry
    MAX-ACCESS  not-accessible
    STATUS      current
    DESCRIPTION
        "An entry in the tFilterApplyPathTable describing an apply-path rule.
        
         If an address or prefix configured by the source specified by 
         tFilterApplyPathSource matches the conditions specified by 
         tFilterApplyPathMatch1 and tFilterApplyPathMatch2, a prefix is 
         inserted into the prefix-list where this apply-path rule refers to."
         
    INDEX { tFilterPrefixListType,
            tFilterPrefixListName,
            tFilterApplyPathSource,
            tFilterApplyPathIndex
          }            
    ::= { tFilterApplyPathTable 1}

TFilterApplyPathEntry ::=
    SEQUENCE {
        tFilterApplyPathSource         TmnxFilterApplyPathSource,
        tFilterApplyPathIndex          Unsigned32,
        tFilterApplyPathRowStatus      RowStatus,
        tFilterApplyPathLastChanged    TimeStamp,
        tFilterApplyPathMatch1         TRegularExpression,
        tFilterApplyPathMatch2         TRegularExpression
    }
    
tFilterApplyPathSource OBJECT-TYPE
    SYNTAX      TmnxFilterApplyPathSource
    MAX-ACCESS  not-accessible
    STATUS      current
    DESCRIPTION
        "The object tFilterApplyPathSource specifies the source of the prefixes 
         that will be generated by this apply-path rule."
    DEFVAL { 0 }
    ::= { tFilterApplyPathEntry 1 }
    
tFilterApplyPathIndex OBJECT-TYPE
    SYNTAX      Unsigned32 (1..16)
    MAX-ACCESS  not-accessible
    STATUS      current
    DESCRIPTION
        "The object tFilterApplyPathIndex specifies an index for this row."
    ::= { tFilterApplyPathEntry 2 }
    
tFilterApplyPathRowStatus OBJECT-TYPE
    SYNTAX      RowStatus
    MAX-ACCESS  read-create
    STATUS      current
    DESCRIPTION
        "The object tFilterApplyPathRowStatus specifies the status of this
         row."
    ::= { tFilterApplyPathEntry 3 } 
    
tFilterApplyPathLastChanged OBJECT-TYPE
    SYNTAX      TimeStamp
    MAX-ACCESS  read-only
    STATUS      current
    DESCRIPTION
        "The object tFilterApplyPathLastChanged specifies the timestamp of 
         the last change to this row."
    ::= { tFilterApplyPathEntry 4 } 
    
tFilterApplyPathMatch1 OBJECT-TYPE
    SYNTAX      TRegularExpression
    MAX-ACCESS  read-create
    STATUS      current
    DESCRIPTION
        "The object tFilterApplyPathMatch1 specifies a regular expression. 
         The usage of this object depends on the source specified 
         by tFilterApplyPathSource. 
         
         If tFilterApplyPathSource is 'bgp-peers', this object specifies a 
         match condition on the group-name of configured bgp peers."
    DEFVAL { ''H }
    ::= { tFilterApplyPathEntry 5 } 
    
tFilterApplyPathMatch2 OBJECT-TYPE
    SYNTAX      TRegularExpression
    MAX-ACCESS  read-create
    STATUS      current
    DESCRIPTION
        "The object tFilterApplyPathMatch2 specifies a regular expression. 
         The usage of this object depends on the source specified by 
         tFilterApplyPathSource. 
         
         If tFilterApplyPathSource is 'bgp-peers', this object specifies a 
         match condition on the ip or ipv6 address of configured bgp peers."
    DEFVAL { ''H }
    ::= { tFilterApplyPathEntry 6 } 
      
-- ----------------------------
--  tFilterEmbeddedRefInfoTable
-- ----------------------------

tFilterEmbeddedRefInfoTable OBJECT-TYPE
    SYNTAX      SEQUENCE OF TFilterEmbeddedRefInfoEntry
    MAX-ACCESS  not-accessible
    STATUS      current
    DESCRIPTION
        "The table tFilterEmbeddedRefInfoTable contains an entry
         for each embedded filter inserted in a normal filter.
         
         This row complements the corresponding row in the 
         tFilterEmbeddedRefTable with read-only operational info."
    ::= { tFilterObjects 44 }

tFilterEmbeddedRefInfoEntry OBJECT-TYPE
    SYNTAX      TFilterEmbeddedRefInfoEntry
    MAX-ACCESS  not-accessible
    STATUS      current
    DESCRIPTION
        "An entry in the tFilterEmbeddedRefInfoTable."
    AUGMENTS {tFilterEmbeddedRefTableEntry}
    ::= { tFilterEmbeddedRefInfoTable 1 }

TFilterEmbeddedRefInfoEntry ::=
    SEQUENCE {
        tFltrEmbedRefInfEntryCnt         Unsigned32,
        tFltrEmbedRefInfEntryCntInsrtd   Unsigned32
    }

tFltrEmbedRefInfEntryCnt OBJECT-TYPE
    SYNTAX      Unsigned32
    MAX-ACCESS  read-only
    STATUS      current
    DESCRIPTION
        "The value of tFltrEmbedRefInfEntryCnt indicates how many entries
         are present in the embedded filter as specified in 
         tFilterEmbeddedRefEmbeddedFltrId."
    ::= { tFilterEmbeddedRefInfoEntry 1 }

tFltrEmbedRefInfEntryCntInsrtd OBJECT-TYPE
    SYNTAX      Unsigned32
    MAX-ACCESS  read-only
    STATUS      current
    DESCRIPTION
        "The value of tFltrEmbedRefInfEntryCntInsrtd indicates how many entries
         of the embedded filter (specified by tFilterEmbeddedRefEmbeddedFltrId)
         are actually placed inside the filter (specified by 
         tFilterEmbeddedRefInsertFltrId).
         
         If the object tFilterEmbeddedRefOperState is different from 'in-service'
         this object will always be zero.
         
         Else, the difference between the value of this object and the value of 
         tFltrEmbedRefInfEntryCnt indicates how many entries of the embedded
         filter were overwritten by local entries in the embedding filter."
    ::= { tFilterEmbeddedRefInfoEntry 2 }

-- ----------------------------
--  tFilterEmbeddedEntryRefInfoTable
-- ----------------------------

tFilterEmbeddedEntryRefInfoTable OBJECT-TYPE
    SYNTAX      SEQUENCE OF TFilterEmbeddedEntryRefInfoEntry
    MAX-ACCESS  not-accessible
    STATUS      current
    DESCRIPTION
        "The table tFilterEmbeddedEntryRefInfoTable contains an entry
         for each embedded filter entry inserted in a normal filter."
    ::= { tFilterObjects 45 }

tFilterEmbeddedEntryRefInfoEntry OBJECT-TYPE
    SYNTAX      TFilterEmbeddedEntryRefInfoEntry
    MAX-ACCESS  not-accessible
    STATUS      current
    DESCRIPTION
        "An entry in the tFilterEmbeddedEntryRefInfoTable.
         Rows in the tFilterEmbeddedEntryRefInfoTable are created 
         by the SYSTEM when an embedded filter is inserted into a normal
         filter. They are destroyed by the SYSTEM when an embedded filter 
         is removed from a normal filter."
    INDEX {tFltrEmbedEntryFilterType,
           tFltrEmbedEntryInsertFltrId,
           tFltrEmbedEntryEmbeddedFltrId,
           tFltrEmbedEntryEmbeddedEntryId}
    ::= { tFilterEmbeddedEntryRefInfoTable 1 }

TFilterEmbeddedEntryRefInfoEntry ::=
    SEQUENCE {
        tFltrEmbedEntryFilterType        TFilterType,
        tFltrEmbedEntryInsertFltrId      TFilterID,
        tFltrEmbedEntryEmbeddedFltrId    TFilterID,
        tFltrEmbedEntryEmbeddedEntryId   TEntryId,
        tFltrEmbedEntryInsrtEntryId      TEntryId,
        tFltrEmbedEntryRefOperState      TmnxFltrEmbeddedEntryState
    }

tFltrEmbedEntryFilterType OBJECT-TYPE
    SYNTAX      TFilterType
    MAX-ACCESS  not-accessible
    STATUS      current
    DESCRIPTION
        "The object tFltrEmbedEntryFilterType specifies a filter type
         for the filters specified by tFltrEmbedEntryInsertFltrId
         and tFltrEmbedEntryEmbeddedFltrId."
    ::= { tFilterEmbeddedEntryRefInfoEntry 1 }

tFltrEmbedEntryInsertFltrId OBJECT-TYPE
    SYNTAX      TFilterID
    MAX-ACCESS  not-accessible
    STATUS      current
    DESCRIPTION
        "The value of tFltrEmbedEntryInsertFltrId specifies the filter
         where the filter specified by tFltrEmbedEntryEmbeddedFltrId
         is inserted."
    ::= { tFilterEmbeddedEntryRefInfoEntry 2 }

tFltrEmbedEntryEmbeddedFltrId OBJECT-TYPE
    SYNTAX      TFilterID
    MAX-ACCESS  not-accessible
    STATUS      current
    DESCRIPTION
        "The value of tFltrEmbedEntryEmbeddedFltrId specifies
         the ID of the filter inserted in the filter specified
         by tFltrEmbedEntryInsertFltrId."
    ::= { tFilterEmbeddedEntryRefInfoEntry 3 }

tFltrEmbedEntryEmbeddedEntryId OBJECT-TYPE
    SYNTAX      TEntryId
    MAX-ACCESS  not-accessible
    STATUS      current
    DESCRIPTION
        "The value of tFltrEmbedEntryEmbeddedEntryId specifies 
         the ID of the entry inside of the filter specified by 
         tFltrEmbedEntryEmbeddedFltrId."
    ::= { tFilterEmbeddedEntryRefInfoEntry 4 }

tFltrEmbedEntryInsrtEntryId OBJECT-TYPE
    SYNTAX      TEntryId
    MAX-ACCESS  read-only 
    STATUS      current
    DESCRIPTION
        "The value of tFltrEmbedEntryInsrtEntryId indicates which entry
         in the filter specified by tFltrEmbedEntryInsertFltrId corresponds 
         to the entry specified by tFltrEmbedEntryEmbeddedEntryId 
         in the filter specified by tFltrEmbedEntryEmbeddedFltrId."  
    ::= { tFilterEmbeddedEntryRefInfoEntry 5 }

tFltrEmbedEntryRefOperState OBJECT-TYPE
    SYNTAX      TmnxFltrEmbeddedEntryState
    MAX-ACCESS  read-only
    STATUS      current
    DESCRIPTION
        "The value of tFltrEmbedEntryRefOperState indicates the current status
         of the entry identified by tFltrEmbedEntryEmbeddedEntryId of 
         the filter identified by tFltrEmbedEntryEmbeddedFltrId that
         is embedded into the filter identified by tFltrEmbedEntryInsertFltrId."
    ::= { tFilterEmbeddedEntryRefInfoEntry 6 }

--
-- IPv6 Filter Entry parameters Extension Table
--

tIPv6FilterParamsExtTbleLstChgd OBJECT-TYPE
    SYNTAX      TimeStamp
    MAX-ACCESS  read-only
    STATUS      current
    DESCRIPTION
        "The value of tIPv6FilterParamsExtTbleLstChgd indicates the
         sysUpTime at the time of the last modification
         of tIPv6FilterParamsExtTable.

         If no changes were made to the entry since the last
         re-initialization of the local network management subsystem,
         then this object contains a zero value."
    ::= { tFilterObjects 46 }

tIPv6FilterParamsExtTable OBJECT-TYPE
    SYNTAX      SEQUENCE OF TIPv6FilterParamsExtEntry
    MAX-ACCESS  not-accessible
    STATUS      current
    DESCRIPTION
        " The table tIPv6FilterParamsExtTable contains, together with the
          table tIPv6FilterParamsTable info about every IPv6 filter entry in
          any of the configured IPv6 filters in the system.
       
          The table tIPv6FilterParamsExtTable was introduced due to the big size
          of the tIPv6FilterParamsTable."
    ::= { tFilterObjects 47 }

tIPv6FilterParamsExtEntry OBJECT-TYPE
    SYNTAX      TIPv6FilterParamsExtEntry
    MAX-ACCESS  not-accessible
    STATUS      current
    DESCRIPTION
        "Information about a particular IPv6 Filter entry.
         Every IPv6 Filter can have zero or more IPv6 Filter match entries.

         A filter entry with no match criteria set will match every
         packet, and the entry action will be taken.

         Entries are created/deleted by user.

         Additional match criteria can be found in tIPv6FilterParamsTable."
    AUGMENTS {tIPv6FilterParamsEntry}
    ::= { tIPv6FilterParamsExtTable 1 }

TIPv6FilterParamsExtEntry ::= SEQUENCE
    {
        tIPv6FilterParamsExtLastChanged  TimeStamp,
        tIPv6FilterParamsExtAhExtHdr     TItemMatch,
        tIPv6FilterParamsExtEspExtHdr    TItemMatch,
        tIPv6FilterParamsExtNatType      TmnxNatSubscriberType
    }

tIPv6FilterParamsExtLastChanged OBJECT-TYPE
    SYNTAX      TimeStamp
    MAX-ACCESS  read-only
    STATUS      current
    DESCRIPTION
        "The value of tIPv6FilterParamsExtLastChanged indicates the timestamp of
         last change to this row in tIPv6FilterParamsExtTable."
    ::= { tIPv6FilterParamsExtEntry 1 }

tIPv6FilterParamsExtAhExtHdr OBJECT-TYPE
    SYNTAX      TItemMatch
    MAX-ACCESS  read-create
    STATUS      current
    DESCRIPTION
        "If Enabled, matches the Authentication Extension Header (51) as per
         value of the object."
    DEFVAL { off }
    ::= { tIPv6FilterParamsExtEntry 2 }

tIPv6FilterParamsExtEspExtHdr OBJECT-TYPE
    SYNTAX      TItemMatch
    MAX-ACCESS  read-create
    STATUS      current
    DESCRIPTION
        "If Enabled, matches the Encapsulation Security Payload Extension Header
         (50) as per value of the object."
    DEFVAL { off }
    ::= { tIPv6FilterParamsExtEntry 3 }

tIPv6FilterParamsExtNatType OBJECT-TYPE
    SYNTAX TmnxNatSubscriberType {
        dsliteLsnSub  (3),
        nat64LsnSub   (4) 
    }
    MAX-ACCESS read-create
    STATUS current
    DESCRIPTION
        "This object specifies the NAT type to be used when the value of the
         corresponding tIPv6FilterParamsNatPolicyName object is nat.

         The value of tIPv6FilterParamsExtNatType is relevant only if the value
         of tIPv6FilterParamsAction is nat. Setting the value of
         tIPv6FilterParamsExtNatType to a non-default value is ignored by the
         system if the value of tIPv6FilterParamsAction is not nat.

         Furthermore, the value of tIPv6FilterParamsExtNatType is silently
         reset to the default value by the system if tIPv6FilterParamsAction is
         set to any value other than nat."
    DEFVAL { dsliteLsnSub }
    ::= { tIPv6FilterParamsExtEntry 4 }

----------------------------------------
------- tIPFilterParamsExtTable --------
----------------------------------------

tIPFilterParamsExtTbleLstChgd OBJECT-TYPE
    SYNTAX      TimeStamp
    MAX-ACCESS  read-only
    STATUS      current
    DESCRIPTION
        "The value of tIPFilterParamsExtTbleLstChgd indicates the
         sysUpTime at the time of the last modification
         of tIPFilterParamsExtTable.

         If no changes were made to the entry since the last
         re-initialization of the local network management subsystem,
         then this object contains a zero value."
    ::= { tFilterObjects 52 }

tIPFilterParamsExtTable OBJECT-TYPE
    SYNTAX      SEQUENCE OF TIPFilterParamsExtEntry
    MAX-ACCESS  not-accessible
    STATUS      current
    DESCRIPTION
        "The table tIPFilterParamsExtTable contains, together with the
         table tIPFilterParamsTable info about every IP filter entry in
         any of the configured IP filters in the system.

         The table tIPFilterParamsExtTable was introduced due to the big size
         of the tIPFilterParamsTable."
    ::= { tFilterObjects 53 }

tIPFilterParamsExtEntry OBJECT-TYPE
    SYNTAX      TIPFilterParamsExtEntry
    MAX-ACCESS  not-accessible
    STATUS      current
    DESCRIPTION
        "Information about a particular IP Filter entry.
         Every IP Filter can have zero or more IP Filter match entries.

         A filter entry with no match criteria set will match every
         packet, and the entry action will be taken.

         Entries are created/deleted by the system when a corresponding
         tIPFilterParamsEntry is created/deleted.

         Additional match criteria can be found in tIPFilterParamsTable."
    AUGMENTS {tIPFilterParamsEntry}
    ::= { tIPFilterParamsExtTable 1 }

TIPFilterParamsExtEntry ::= SEQUENCE
    {
        tIPFilterParamsExtLastChanged         TimeStamp,
        tIPFilterParamsExtPktLenVal1          TFilterPacketLength,
        tIPFilterParamsExtPktLenVal2          TFilterPacketLength,
        tIPFilterParamsExtPktLenOper          TOperator
    }

tIPFilterParamsExtLastChanged OBJECT-TYPE
    SYNTAX      TimeStamp
    MAX-ACCESS  read-only
    STATUS      current
    DESCRIPTION
        "The value of the object tIPFilterParamsExtLastChanged indicates
         the timestamp of last change of this row in tIPFilterParamsExtTable."
    ::= { tIPFilterParamsExtEntry 1 }

tIPFilterParamsExtPktLenVal1 OBJECT-TYPE
    SYNTAX      TFilterPacketLength
    MAX-ACCESS  read-create
    STATUS      current
    DESCRIPTION
        "The value of the object tIPFilterParamsExtPktLenVal1 specifies
         the packet length value1 to be compared to the value of the Total
         Length field of an IP packet header that has hit this filter's entry.

         The way how the value of this object is used depends on the value
         of the object tIPFilterParamsExtPktLenOper.

         The value of this object can be set to a non-default value only
         if the value of the object tIPFilterParamsExtPktLenOper is other
         than 'none (0)'.

         If the value of tIPFilterParamsExtPktLenOper is 'range (2)' then
         the value of this object must be less than the value
         of tIPFilterParamsExtPktLenVal2.

         If the value of tIPFilterParamsExtPktLenOper is 'lt (3)' then
         the value of this object can be set in range 1..65535.

         If the value of tIPFilterParamsExtPktLenOper is 'gt (4)' then
         the value of this object can be set in range 0..65534.

         If both the values of the objects tIPFilterParamsExtPktLenOper and
         tIPFilterParamsExtPktLenVal1 need to be changed then it must be
         done in the same SET SNMP request.

         Note that the value of this object is silently cleared by the system
         if tIPFilterParamsAction is set to value other than 'drop (1)' or
         if tIPFilterParamsExtPktLenOper is set to 'none (0)'."
    DEFVAL { 0 }
    ::= { tIPFilterParamsExtEntry 2 }

tIPFilterParamsExtPktLenVal2 OBJECT-TYPE
    SYNTAX      TFilterPacketLength
    MAX-ACCESS  read-create
    STATUS      current
    DESCRIPTION
        "The value of the object tIPFilterParamsExtPktLenVal2 specifies
         the packet length value2 to be compared to the value of the Total
         Length field of an IP packet header that has hit this filter's entry.

         The way how the value of this object is used depends on the value
         of the object tIPFilterParamsExtPktLenOper.

         The value of this object can be set to a non-default value only
         if the value of the object tIPFilterParamsExtPktLenOper is 'range (2)'.
         
         The value of this object must be greater than the value
         of tIPFilterParamsExtPktLenVal1.

         If both the values of the objects tIPFilterParamsExtPktLenOper and
         tIPFilterParamsExtPktLenVal2 need to be changed then it must be
         done in the same SET SNMP request.

         Note that the value of this object is silently cleared by the system
         if tIPFilterParamsAction is set to value other than 'drop (1)' or
         if tIPFilterParamsExtPktLenOper is set to value other than
         'range (2)'."
    DEFVAL { 0 }
    ::= { tIPFilterParamsExtEntry 3 }

tIPFilterParamsExtPktLenOper OBJECT-TYPE
    SYNTAX      TOperator
    MAX-ACCESS  read-create
    STATUS      current
    DESCRIPTION
        "The value of the object tIPFilterParamsExtPktLenOper specifies the way
         how the values of the objects tIPFilterParamsExtPktLenVal1 and
         tIPFilterParamsExtPktLenVal2 are used to form a condition that must
         be fulfilled in order to execute the action specified by the value
         of tIPFilterParamsAction. Otherwise the opposite action is executed.

         The value of this object can be set to a non-default value only if
         the value of the object tIPFilterParamsAction is 'drop (1)'.

         If the value of this object is being changed from the default value
         to any non-default value the values of the objects
         tIPFilterParamsExtPktLenVal1 and tIPFilterParamsExtPktLenVal2
         (if applicable) must be sent in the same SET SNMP request.

         If the value of this object is 'none (0)' than the values of
         the objects tIPFilterParamsExtPktLenVal1 and
         tIPFilterParamsExtPktLenVal2 are ignored and TRUE case action is
         always executed (see table below).

         If the value of this object is 'eq (1)' then the value of the Total
         Length field of the IP header of the packet that has matched this
         filter's entry must be equal to the value of the object
         tIPFilterParamsExtPktLenVal1 in order to execute the TRUE case action
         (see table below). Otherwise the FALSE case action is executed.
         The value of the object tIPFilterParamsExtPktLenVal2 is ignored.

         If the value of this object is 'range (2)' then the value of the Total
         Length field of the IP header of the packet that has matched this
         filter's entry must be greater than or equal to the value of the object
         tIPFilterParamsExtPktLenVal1 and less than or equal to the value
         of the object tIPFilterParamsExtPktLenVal2 in order to execute
         the TRUE case action (see table below). Otherwise the FALSE case action
         is executed.

         If the value of this object is 'lt (3)' then the value of the Total
         Length field of the IP header of the packet that has matched this
         filter's entry must be less than the value of the object
         tIPFilterParamsExtPktLenVal1 in order to execute the TRUE case action
         (see table below). Otherwise the FALSE case action is executed.
         The value of the object tIPFilterParamsExtPktLenVal2 is ignored.

         If the value of this object is 'gt (4)' then the value of the Total
         Length field of the IP header of the packet that has matched this
         filter's entry must be greater than the value of the object
         tIPFilterParamsExtPktLenVal1 in order to execute the TRUE case action
         (see table below). Otherwise the FALSE case action is executed.
         The value of the object tIPFilterParamsExtPktLenVal2 is ignored.


         tIPFilterParamsAction   |   TRUE case action  |  FALSE case action
         ------------------------------------------------------------------
         drop                    |      drop           |      forward


         Allowed ranges for the values of tIPFilterParamsExtPktLenVal1 and
         tIPFilterParamsExtPktLenVal2 are:

         Operator                |Packet Length Value 1|Packet Length Value 2
         --------------------------------------------------------------------
         none (0)                |      N/A            |      N/A
         eq(1)                   |    0..65535         |      N/A
         range(2)                |    0..65534         | (Value1 + 1)..65535
         lt(3)                   |    1..65535         |      N/A
         gt(4)                   |    0..65534         |      N/A


         The values of the objects tIPFilterParamsExtPktLenVal1 and
         tIPFilterParamsExtPktLenVal2 are silently cleared if the value of this
         object is set to default.

         Note that the value of this object is silently cleared by the system
         if tIPFilterParamsAction is set to value other than 'drop (1)'."
    DEFVAL { none }
    ::= { tIPFilterParamsExtEntry 4 }

-- ----------------------------
--  tFilterEmbedOpenflowTable
-- ----------------------------
tFilterEmbedOpenflowTableLstChg OBJECT-TYPE
    SYNTAX      TimeStamp
    MAX-ACCESS  read-only
    STATUS      current
    DESCRIPTION
        "The object tFilterEmbedOpenflowTableLstChg indicates the
        sysUpTime at the time of the last modification
        of tFilterPrefixListEntryTable.

        If no changes were made to the table since the last
        re-initialization of the local network management subsystem,
        this object contains the value zero."
    ::= {  tFilterObjects 48 }

tFilterEmbedOpenflowTable OBJECT-TYPE
    SYNTAX      SEQUENCE OF TFilterEmbedOpenflowEntry
    MAX-ACCESS  not-accessible
    STATUS      current
    DESCRIPTION
        "The table tFilterEmbedOpenflowTable contains an entry
         for each open-flow flowtable embedded in a normal filter."
    ::= { tFilterObjects 49 }

tFilterEmbedOpenflowEntry OBJECT-TYPE
    SYNTAX      TFilterEmbedOpenflowEntry
    MAX-ACCESS  not-accessible
    STATUS      current
    DESCRIPTION
        "An entry in the tFilterPrefixListEntryTable."
    INDEX {tFilterEmbedOpenflowOfsName,
           tFilterEmbedOpenflowFilterType,
           tFilterEmbedOpenflowInsertFltrId,
           tFilterEmbedOpenflowOffset}
    ::= { tFilterEmbedOpenflowTable 1 }

TFilterEmbedOpenflowEntry ::=
    SEQUENCE {
        tFilterEmbedOpenflowOfsName      TNamedItem,
        tFilterEmbedOpenflowFilterType   TFilterType,
        tFilterEmbedOpenflowInsertFltrId TFilterID,
        tFilterEmbedOpenflowOffset       Unsigned32,
        tFilterEmbedOpenflowRowStatus    RowStatus,
        tFilterEmbedOpenflowAdminState   INTEGER,
        tFilterEmbedOpenflowOperState    TmnxEmbeddedFltrOperState
    }

tFilterEmbedOpenflowOfsName OBJECT-TYPE
    SYNTAX      TNamedItem
    MAX-ACCESS  not-accessible
    STATUS      current
    DESCRIPTION
        "The value of tFilterEmbedOpenflowOfsName specifies the name
         of the open-flow switch which contains the flowtable to be inserted in 
         the filter specified by tFilterEmbedOpenflowInsertFltrId."
    ::= { tFilterEmbedOpenflowEntry 1 }

tFilterEmbedOpenflowFilterType OBJECT-TYPE
    SYNTAX      TFilterType
    MAX-ACCESS  not-accessible
    STATUS      current
    DESCRIPTION
        "The object tFilterEmbedOpenflowFilterType specifies the type of filter
         for the filter specified by tFilterEmbedOpenflowInsertFltrId."
    ::= { tFilterEmbedOpenflowEntry 2 }

tFilterEmbedOpenflowInsertFltrId OBJECT-TYPE
    SYNTAX      TFilterID
    MAX-ACCESS  not-accessible
    STATUS      current
    DESCRIPTION
        "The value of tFilterEmbedOpenflowInsertFltrId specifies the filter
         where the open-flow switch specified by tFilterEmbedOpenflowOfsName 
         is to be embedded."
    ::= { tFilterEmbedOpenflowEntry 3 }

tFilterEmbedOpenflowOffset OBJECT-TYPE
    SYNTAX      Unsigned32 (0..65535)
    MAX-ACCESS  not-accessible
    STATUS      current
    DESCRIPTION
        "The value of tFilterEmbedOpenflowOffset specifies the offset of
         inserting entries. A flowrule with priority x will 
         be inserted at position x + offset into the inserting filter."
    DEFVAL { 0 }
    ::= { tFilterEmbedOpenflowEntry 4 }

tFilterEmbedOpenflowRowStatus OBJECT-TYPE
    SYNTAX      RowStatus
    MAX-ACCESS  read-create
    STATUS      current
    DESCRIPTION
        "The object tFilterEmbedOpenflowRowStatus specifies the status
         of this row."
    ::= { tFilterEmbedOpenflowEntry 5 }
    
tFilterEmbedOpenflowAdminState OBJECT-TYPE
    SYNTAX      INTEGER {
                   inactive  (0),
                   active    (1)
                }
    MAX-ACCESS  read-create
    STATUS      current
    DESCRIPTION
        "The value of tFilterEmbedOpenflowAdminState indicates the administrative
         state of the embed request defined by this row. 
         
         If an active embedding cannot be fullfilled due to dynamic events, this 
         object will be set to 'inactive' automatically by the system. In those 
         cases, the object tFilterEmbedOpenflowOperState will indicate the failure
         reason."
    DEFVAL { active }
    ::= { tFilterEmbedOpenflowEntry 6 }    

tFilterEmbedOpenflowOperState OBJECT-TYPE
    SYNTAX      TmnxEmbeddedFltrOperState
    MAX-ACCESS  read-only
    STATUS      current
    DESCRIPTION
        "The value of tFilterEmbedOpenflowOperState indicates the operational
         state of the embed request defined by this row."
    ::= { tFilterEmbedOpenflowEntry 7 }

-- ------------------------------
--  tFilterEmbedOpenflowInfoTable
-- ------------------------------

tFilterEmbedOpenflowInfoTable OBJECT-TYPE
    SYNTAX      SEQUENCE OF TFilterEmbedOpenflowInfoEntry
    MAX-ACCESS  not-accessible
    STATUS      current
    DESCRIPTION
        "The table tFilterEmbedOpenflowInfoTable contains an entry
         for each open-flow switch embedded in a filter.
         
         This row complements the corresponding row in the 
         tFilterEmbedOpenflowTable with read-only operational info."
    ::= { tFilterObjects 50 }

tFilterEmbedOpenflowInfoEntry OBJECT-TYPE
    SYNTAX      TFilterEmbedOpenflowInfoEntry
    MAX-ACCESS  not-accessible
    STATUS      current
    DESCRIPTION
        "An entry in the tFilterEmbedOpenflowInfoTable."
    AUGMENTS {tFilterEmbedOpenflowEntry}
    ::= { tFilterEmbedOpenflowInfoTable 1 }

TFilterEmbedOpenflowInfoEntry ::=
    SEQUENCE {
        tFltrEmbedOfInfoEntryCnt         Unsigned32,
        tFltrEmbedOfInfoEntryCntInsrtd   Unsigned32
    }

tFltrEmbedOfInfoEntryCnt OBJECT-TYPE
    SYNTAX      Unsigned32
    MAX-ACCESS  read-only
    STATUS      current
    DESCRIPTION
        "The value of tFltrEmbedOfInfoEntryCnt indicates how many entries
         are egligable for embedding from the open-flow switch specified by 
         tFilterEmbedOpenflowOfsName."
    ::= { tFilterEmbedOpenflowInfoEntry 1 }

tFltrEmbedOfInfoEntryCntInsrtd OBJECT-TYPE
    SYNTAX      Unsigned32
    MAX-ACCESS  read-only
    STATUS      current
    DESCRIPTION
        "The value of tFltrEmbedOfInfoEntryCntInsrtd indicates how many entries
         are actually placed inside the filter by the open-flow switch specified
         by tFilterEmbedOpenflowOfsName.
         
         If the object tFilterEmbedOpenflowOperState is different from 
         'in-service' this object will always be zero.
         
         Else, the difference between the value of this object and the value of 
         tFltrEmbedOfInfoEntryCnt indicates how many entries were overwritten 
         by local entries in the embedding filter."
    ::= { tFilterEmbedOpenflowInfoEntry 2 }

-- ----------------------------
-- tFilterOpenflowEntryInfoTable
-- ----------------------------

tFilterOpenflowEntryInfoTable OBJECT-TYPE
    SYNTAX      SEQUENCE OF TFilterOpenflowEntryInfoEntry
    MAX-ACCESS  not-accessible
    STATUS      current
    DESCRIPTION
        "The table tFilterOpenflowEntryInfoTable contains an entry
         for each open-flow filter entry inserted in a normal filter."
    ::= { tFilterObjects 51 }

tFilterOpenflowEntryInfoEntry OBJECT-TYPE
    SYNTAX      TFilterOpenflowEntryInfoEntry
    MAX-ACCESS  not-accessible
    STATUS      current
    DESCRIPTION
        "An entry in the tFilterOpenflowEntryInfoTable.
         Rows in the tFilterOpenflowEntryInfoTable are created 
         by the SYSTEM when an open-flow switch is embedded into a filter. 
         They are destroyed by the SYSTEM when an open-flow switch embedding 
         is removed from a filter."
    INDEX {tFltrEmbedOfEntryOfsName,
           tFltrEmbedOfEntryFilterType,
           tFltrEmbedOfEntryInsertFltrId,
           tFltrEmbedOfEntryOfEntryId}
    ::= { tFilterOpenflowEntryInfoTable 1 }

TFilterOpenflowEntryInfoEntry ::=
    SEQUENCE {
        tFltrEmbedOfEntryOfsName         TNamedItem,
        tFltrEmbedOfEntryFilterType      TFilterType,
        tFltrEmbedOfEntryInsertFltrId    TFilterID,
        tFltrEmbedOfEntryOfEntryId       TEntryId,
        tFltrEmbedOfEntryInsrtEntryId    TEntryId,
        tFltrEmbedOfEntryInsrtEntryState TmnxFltrEmbeddedEntryState
    }

tFltrEmbedOfEntryOfsName OBJECT-TYPE
    SYNTAX      TNamedItem
    MAX-ACCESS  not-accessible
    STATUS      current
    DESCRIPTION
        "The value of tFltrEmbedOfEntryOfsName specifies the name
         of the open-flow switch which contains the flowtable to be inserted in 
         the filter specified by tFltrEmbedOfEntryInsertFltrId."
    ::= { tFilterOpenflowEntryInfoEntry 1 }

tFltrEmbedOfEntryFilterType OBJECT-TYPE
    SYNTAX      TFilterType
    MAX-ACCESS  not-accessible
    STATUS      current
    DESCRIPTION
        "The object tFltrEmbedOfEntryFilterType specifies the type of filter
         for the filter specified by tFltrEmbedOfEntryInsertFltrId."
    ::= { tFilterOpenflowEntryInfoEntry 2 }

tFltrEmbedOfEntryInsertFltrId OBJECT-TYPE
    SYNTAX      TFilterID
    MAX-ACCESS  not-accessible
    STATUS      current
    DESCRIPTION
        "The value of tFltrEmbedOfEntryInsertFltrId specifies the filter
         where the open-flow switch specified by tFltrEmbedOfEntryOfsName 
         is to be embedded."
    ::= { tFilterOpenflowEntryInfoEntry 3 }
    
tFltrEmbedOfEntryOfEntryId OBJECT-TYPE
    SYNTAX      TEntryId
    MAX-ACCESS  not-accessible
    STATUS      current
    DESCRIPTION
        "The value of tFltrEmbedOfEntryOfEntryId specifies the base ID of the 
         entry as determined by the priority of the corresponding flow-rule in
         the open-flow switch specified by tFltrEmbedOfEntryOfsName."
    ::= { tFilterOpenflowEntryInfoEntry 4 }

tFltrEmbedOfEntryInsrtEntryId OBJECT-TYPE
    SYNTAX      TEntryId
    MAX-ACCESS  read-only 
    STATUS      current
    DESCRIPTION
        "The value of tFltrEmbedOfEntryInsrtEntryId indicates the position 
         of the filter entry in the filter specified by 
         tFltrEmbedOfEntryInsertFltrId."  
    ::= { tFilterOpenflowEntryInfoEntry 5 }

tFltrEmbedOfEntryInsrtEntryState OBJECT-TYPE
    SYNTAX      TmnxFltrEmbeddedEntryState
    MAX-ACCESS  read-only
    STATUS      current
    DESCRIPTION
        "The value of tFltrEmbedOfEntryInsrtEntryState indicates the current 
         status of the embedding of the entry identified by 
         tFltrEmbedOfEntryOfEntryId from the open-flow switch identified by 
         tFltrEmbedOfEntryOfsName that is embedded into the filter 
         identified by tFltrEmbedOfEntryInsertFltrId."
    ::= { tFilterOpenflowEntryInfoEntry 6 }

--
-- Filter Notification Objects
--

tFilterPBRDropReason OBJECT-TYPE
    SYNTAX      INTEGER {
                invalidInterface (0),
                interfaceDown    (1)
            }
    MAX-ACCESS  accessible-for-notify
    STATUS      current
    DESCRIPTION
        "Used by tIPFilterPBRPacketsDrop to report the failure reason code."
    ::= { tFilterNotificationObjects 1 }

tFilterParmRow OBJECT-TYPE
    SYNTAX      RowPointer
    MAX-ACCESS  accessible-for-notify
    STATUS      current
    DESCRIPTION
        "The value of the object tFilterParmRow indicates the OID of the row
         status of the applicable filter parameter table. This can be a row from
         either one of the following tables:
         - tIPFilterParamsTable;
         - tMacFilterParamsTable; or
         - tIPv6FilterParamsTable"
    ::= { tFilterNotificationObjects 2 }

tFilterAlarmDescription OBJECT-TYPE
    SYNTAX      DisplayString
    MAX-ACCESS  accessible-for-notify
    STATUS      current
    DESCRIPTION
        "The value of the object tFilterAlarmDescription is a printable
         character string which contains information about the cause of the
         problem."
    ::= { tFilterNotificationObjects 3 }

tFilterId OBJECT-TYPE
    SYNTAX      TFilterID
    MAX-ACCESS  accessible-for-notify
    STATUS      current
    DESCRIPTION
        "The value of the object tFilterId, together with the object
         tFilterType uniquely defines the filter for which this notification is
         generated."
    ::= { tFilterNotificationObjects 4 }

tFilterType OBJECT-TYPE
    SYNTAX      TFilterType
    MAX-ACCESS  accessible-for-notify
    STATUS      current
    DESCRIPTION
        "The value of the object tFilterType, together with the object
         tFilterId uniquely defines the filter for which this notification is
         generated."
    ::= { tFilterNotificationObjects 5 }

tFilterSubInsSpaceOwner OBJECT-TYPE
    SYNTAX      TFilterSubInsSpaceOwner
    MAX-ACCESS  accessible-for-notify
    STATUS      current
    DESCRIPTION
        "The value of the object tFilterSubInsSpaceOwner, specifies for
         which application, capable of inserting filter entries,
         this notification is generated."
    ::= { tFilterNotificationObjects 6 }

tFilterThresholdReached OBJECT-TYPE
    SYNTAX      INTEGER
    MAX-ACCESS  accessible-for-notify
    STATUS      current
    DESCRIPTION
        "The value of the object tFilterThresholdReached, specifies
         the threshold reached at the moment this notificastion was
         generated."
    ::= { tFilterNotificationObjects 7 }

tFltrFlowSpecProblem OBJECT-TYPE
    SYNTAX      INTEGER {
                nlriDecodeProblem           (0),
                maxNbrFlowSpecEntriesReached(1),
                fltrResourceProblem         (2),
                other                       (3)}
    MAX-ACCESS  accessible-for-notify
    STATUS      current
    DESCRIPTION
        "The value of the object tFltrFlowSpecProblem, indicates
         which problem has occured while processing a BGP flowspec
         NLRI in the filter module."
    ::= { tFilterNotificationObjects 8 }

tFltrFlowSpecProblemDescription OBJECT-TYPE
    SYNTAX      DisplayString
    MAX-ACCESS  accessible-for-notify
    STATUS      current
     DESCRIPTION
         "The value of the object tFltrFlowSpecProblem may contain
          a more detailed problem description then as given by
          tFltrFlowSpecProblem."
    ::= { tFilterNotificationObjects 9 }

tFltrFLowSpecNLRI OBJECT-TYPE
    SYNTAX      OCTET STRING
    MAX-ACCESS  accessible-for-notify
    STATUS      current
    DESCRIPTION
        "The value of the object tFltrFLowSpecNLRI contains
         at most the first 30 octets of the NLRI causing the problem."
    ::= { tFilterNotificationObjects 10 }

tFltrFlowSpecVrtrId OBJECT-TYPE
    SYNTAX      Unsigned32
    MAX-ACCESS  accessible-for-notify
    STATUS      current
     DESCRIPTION
         "The value of the object tFltrFlowSpecVrtrId indicates
          the virtual router Id to which the NLRI belongs."
    ::= { tFilterNotificationObjects 11 }
    
tFltrPrefixListType OBJECT-TYPE
    SYNTAX      TFltrPrefixListType
    MAX-ACCESS  accessible-for-notify
    STATUS      current
    DESCRIPTION
         "The value of the object tFltrPrefixListType indicates
          the type of prefix-list."
    ::= { tFilterNotificationObjects 12 }
    
tFltrPrefixListName OBJECT-TYPE
    SYNTAX      TNamedItem
    MAX-ACCESS  accessible-for-notify
    STATUS      current
    DESCRIPTION
         "The value of the object tFltrPrefixListName indicates
          the name of the prefix-list."
    ::= { tFilterNotificationObjects 13 }    
    
tFltrApplyPathSource OBJECT-TYPE
    SYNTAX      TmnxFilterApplyPathSource
    MAX-ACCESS  accessible-for-notify
    STATUS      current
    DESCRIPTION
        "The value of tFltrApplyPathSource indicates the source of the
         apply-path rule."
    ::= { tFilterNotificationObjects 14 }    

tFltrApplyPathIndex OBJECT-TYPE
    SYNTAX      Unsigned32
    MAX-ACCESS  accessible-for-notify
    STATUS      current
    DESCRIPTION
        "The value of tFltrApplyPathIndex indicates the index of the
         apply-path rule."
    ::= { tFilterNotificationObjects 15 } 
    
tFltrNotifDescription OBJECT-TYPE
    SYNTAX      DisplayString
    MAX-ACCESS  accessible-for-notify
    STATUS      current
     DESCRIPTION
         "The value of the object tFltrNotifDescription may contain
          a description text."
    ::= { tFilterNotificationObjects 16 }   

tFltrMdaId OBJECT-TYPE
    SYNTAX      TmnxPortID
    MAX-ACCESS  accessible-for-notify
    STATUS      current
     DESCRIPTION
         "The value of the object tFltrMdaId contains the MDA-id
          of the mda on which an filter event is being reported."
    ::= { tFilterNotificationObjects 17 }   

tIPFilterPBRPacketsDrop NOTIFICATION-TYPE
    OBJECTS {
        tIPFilterParamsForwardNHInterface,
        tFilterPBRDropReason
    }
    STATUS      current
    DESCRIPTION
        "The tIPFilterPBRPacketsDrop event is generated either
         when the configuration of a forwarding action refers to an
         invalid/unconfigured next-hop or if the active interface goes down
         operationally in the process of active filtering."
    ::= { tFilterNotifications 1 }

tFilterEntryActivationFailed NOTIFICATION-TYPE
    OBJECTS {
        tFilterParmRow,
        tFilterAlarmDescription
    }
    STATUS      current
    DESCRIPTION
        "The tFilterEntryActivationFailed event can only be
         generated for entries that are controlled by a tmnxTimeRangeEntry.
         If the tmnxTimeRangeEntry becomes active the indicated entry must be
         installed.
         The event is generated when this installation failed because
         of resource problems."
    ::= { tFilterNotifications 2 }

tFilterEntryActivationRestored NOTIFICATION-TYPE
    OBJECTS {
        tFilterParmRow,
        tFilterAlarmDescription
    }
    STATUS      current
    DESCRIPTION
        "The tFilterEntryActivationRestored event can only be
         generated for entries that are controlled by a tmnxTimeRangeEntry.
         If the tmnxTimeRangeEntry becomes active the indicated entry must be
         installed.
         The event tFilterEntryActivationFailed is generated when
         this installation originally failed because of resources
         problems,
         The notification tFilterEntryActivationRestored is sent
         when either the time range associated with the filter is no
         longer active, or when the filter entry
         was installed due to the availability of new resources."
    ::= { tFilterNotifications 3 }

tFilterSubInsSpaceAlarmRaised NOTIFICATION-TYPE
    OBJECTS {
        tFilterType,
        tFilterId,
        tFilterSubInsSpaceOwner,
        tFilterThresholdReached
    }
    STATUS      current
    DESCRIPTION
        "The tFilterSubInsSpaceAlarmRaised notification is
         generated when the utilization of a filter entry
         range that was reserved for filter entry insertion
         increases to the configured high watermark for his filter"
    ::= { tFilterNotifications 4 }

tFilterSubInsSpaceAlarmCleared NOTIFICATION-TYPE
    OBJECTS {
        tFilterType,
        tFilterId,
        tFilterSubInsSpaceOwner,
        tFilterThresholdReached
    }
    STATUS      current
    DESCRIPTION
        "The tFilterSubInsSpaceAlarmCleared notification is
         generated when the utilization of a filter entry
         range that was reserved for filter entry insertion
         dropped below to the configured low watermark for his filter."
    ::= { tFilterNotifications 5 }

tFilterSubInsFltrEntryDropped NOTIFICATION-TYPE
    OBJECTS {
        tFilterType,
        tFilterId,
        tFilterSubInsSpaceOwner,
        tFilterAlarmDescription
    }
    STATUS      current
    DESCRIPTION
        "The tFilterSubInsFltrEntryDropped notification is
         generated when a request to insert a filter entry
         was not successful."
    ::= { tFilterNotifications 6 }

tFilterBgpFlowSpecProblem NOTIFICATION-TYPE
    OBJECTS {
        tFilterType,
        tFltrFlowSpecVrtrId,
        tFltrFlowSpecProblem,
        tFltrFlowSpecProblemDescription,
        tFltrFLowSpecNLRI
    }
    STATUS      current
    DESCRIPTION
        "The tFilterBgpFlowSpecProblem notification is
         generated when a BGP flowspec NLRI is received in
         the filter module that cannot be treated - i.e. for
         which no filter entry is installed in the system,
         or when there is a problem inserting (new) or
         reshuffling (existing) flowspec or merged filter entries."
    ::= { tFilterNotifications 7 }

tFilterApplyPathProblem NOTIFICATION-TYPE
    OBJECTS {
        tFltrPrefixListType,
        tFltrPrefixListName,
        tFltrApplyPathSource,
        tFltrApplyPathIndex,
        tFilterAlarmDescription
    }
    STATUS     current
    DESCRIPTION
        "The tFilterApplyPathProblem notification is generated when 
         when a problem is encountered for a configured apply-path rule."
    ::= { tFilterNotifications 8 }

tFilterRadSharedFltrAlarmRaised  NOTIFICATION-TYPE
    OBJECTS {
        tFilterType,
        tFilterId,
        tFilterThresholdReached
    }
    STATUS      current
    DESCRIPTION
        "The tFilterRadSharedFltrAlarmRaised notification is
         generated when the number of Radius Shared Filters that are
         dynamically created in the system increases to the
         configured high watermark for the indicated filter."
    ::= { tFilterNotifications 9 }

tFilterRadSharedFltrAlarmClear   NOTIFICATION-TYPE
    OBJECTS {
        tFilterType,
        tFilterId,
        tFilterThresholdReached
    }
    STATUS      current
    DESCRIPTION
        "The tFilterRadSharedFltrAlarmClear notification is generated
         when the number of Radius Shared Filters that are
         dynamically created in the system dropped below to the
         configured low watermark for the indicated filter."
    ::= { tFilterNotifications 10 }

tFilterEmbeddingOperStateChange   NOTIFICATION-TYPE
    OBJECTS {
        tFilterEmbeddedRefOperState,
        tFltrNotifDescription
    }
    STATUS      current
    DESCRIPTION
        "The tFilterEmbeddingOperStateChange notification is generated
         when the operational status of an embedded filter has changed.
         
         [CAUSE] This notification may be triggered for the following reasons:
         
         1) An attempt to embed an embedded filter into embedding filter was done.
         2) An attempt to recover an embedding that is operationally down 
            was done.
         3) An attempt to change the admin state of an embedding was done.
         4) The operational state of an embedding has changed to inactive 
            due to lack of resources.
            
         [EFFECT] The effect depends on the new state. If the new state is 'active',
         the embedding of the filter was successful. 
         
         If the new state is 'embedFailedNoResources' the embedding was not successful 
         due to lack of resources.

         If the new state is 'inactive' and the previous state was 'active' then 
         the embedded entries were removed. Otherwise the embedding filter was 
         not changed.
         
         [RECOVERY] If the new state is 'active' or 'inactive', no action is required. 
         
         If the new state is 'embedFailedNoResources', an attempt to recover the operational 
         state can be done by removal and reapplication of the embedding."
    ::= { tFilterNotifications 11 }

tFilterEmbedOpenflowOperStateChg   NOTIFICATION-TYPE
    OBJECTS {
        tFilterEmbedOpenflowOperState,
        tFltrNotifDescription
    }
    STATUS      current
    DESCRIPTION
        "The tFilterEmbedOpenflowOperStateChg notification is generated
         when the operational state of an open-flow switch embedded 
         in a normal filter has changed.
         
         [CAUSE] This notification may be triggered for the following reasons:
         
         1) An attempt to embed an open-flow switch into an embedding filter 
            was done.
         2) An attempt to recover an open-flow embedding that is operationally 
            down was done.
         3) An attempt to change the admin state of an open-flow embedding 
            was done.
         4) The operational state of an open-flow embedding has changed 
            to inactive due to lack of resources.
            
         [EFFECT] The effect depends on the new state. If the new state 
         is 'active', the embedding of an open-flow switch was successful. 
         
         If the new state is 'embedFailedNoResources' the embedding was not 
         successful due to lack of resources.

         If the new state is 'inactive' and the previous state was 'active' then 
         the open-flow switch entries were removed. 
         Otherwise the embedding filter was not changed.
         
         [RECOVERY] If the new state is 'active' or 'inactive', no action 
         is required. 
         
         If the new state is 'embedFailedNoResources', an attempt to recover 
         the operational state can be done by removal and reapplication of 
         the open-flow embedding."
    ::= { tFilterNotifications 12 }

tFilterTmsEvent  NOTIFICATION-TYPE
    OBJECTS {
        tFltrMdaId,
        tFltrNotifDescription
    }
    STATUS      current
    DESCRIPTION
        "The tFilterTmsEvent notification is generated by the systems filter
         module to report an event related to the
         Threat Management System (TMS).
         
         Receiving the tFilterTmsEvent notification is an indication that
         the TMS system may not be fully operational."
    ::= { tFilterNotifications 13 }

--
-- Conformance Information
--

tFilterMIBCompliances OBJECT IDENTIFIER ::= { tFilterMIBConformance 1 }
tFilterMIBGroups      OBJECT IDENTIFIER ::= { tFilterMIBConformance 2 }

--
-- Compliance Statements
--

-- tFilterMIBCompliance MODULE-COMPLIANCE
--    ::= { tFilterMIBCompliances 1 }

-- tFilterR2r1MIBCompliance MODULE-COMPLIANCE
--    ::= { tFilterMIBCompliances 2 }

-- tFilterV3v0MIBCompliance MODULE-COMPLIANCE
--    ::= { tFilterMIBCompliances 3 }

tFilter7450V4v0Compliance MODULE-COMPLIANCE
    STATUS  obsolete
    DESCRIPTION
        "The compliance statement for management of Filter features
         on Alcatel 7450 ESS series systems release R4.0."
    MODULE  -- this module
        MANDATORY-GROUPS {
            tFilterScalarGroup,
            tIPFilterV4v0Group,
            tMacFilterV4v0Group,
            tFilterLogGroup,
            tFilterRedirectPolicyGroup,
            tFilterNotificationsGroup
            -- tIPv6FilterV4v0Group
            -- tTodPoliciesV4v0Group
        }
    ::= { tFilterMIBCompliances 4 }

tFilter7750V4v0Compliance MODULE-COMPLIANCE
    STATUS  obsolete
    DESCRIPTION
        "The compliance statement for management of Filter features
         on Alcatel 7750 SR series systems release R4.0."
    MODULE  -- this module
        MANDATORY-GROUPS {
            tFilterScalarGroup,
            tIPFilterV4v0Group,
            tMacFilterV4v0Group,
            tFilterLogGroup,
            tFilterRedirectPolicyGroup,
            tFilterNotificationsGroup,
            tIPv6FilterV4v0Group
            -- tTodPoliciesV4v0Group
        }
    ::= { tFilterMIBCompliances 5 }

tFilter7450V5v0Compliance MODULE-COMPLIANCE
    STATUS  obsolete
    DESCRIPTION
        "The compliance statement for management of Filter features
         on Alcatel 7450 ESS series systems release R5.0."
    MODULE  -- this module
        MANDATORY-GROUPS {
            tFilterScalarGroup,
            tIPFilterV5v0Group,
            tMacFilterV4v0Group,
            tFilterLogGroup,
            tFilterRedirectPolicyGroup,
            tFilterNotificationsGroup,
            -- tIPv6FilterV4v0Group
            tTodPolicies77450V5v0Group,
            tToDPoliciesV5v0NotifyGroup,
            tFilterLogV5v0Group
        }
    ::= { tFilterMIBCompliances 6 }

tFilter77x0V5v0Compliance MODULE-COMPLIANCE
    STATUS  obsolete
    DESCRIPTION
        "The compliance statement for management of Filter features
         on Alcatel 77x0 SPR/SR series systems release R5.0."
    MODULE  -- this module
        MANDATORY-GROUPS {
            tFilterScalarGroup,
            tIPFilterV5v0Group,
            tMacFilterV4v0Group,
            tFilterLogGroup,
            tFilterRedirectPolicyGroup,
            tFilterNotificationsGroup,
            tIPv6FilterV4v0Group,
            tTodPolicies77x0V5v0Group,
            tToDPoliciesV5v0NotifyGroup,
            tFilterLogV5v0Group
        }
    ::= { tFilterMIBCompliances 7 }

tFilter7450V6v0Compliance MODULE-COMPLIANCE
    STATUS  obsolete
    DESCRIPTION
        "The compliance statement for management of Filter features
         on Alcatel 7450 ESS series systems release R5.0."
    MODULE  -- this module
        MANDATORY-GROUPS {
            tFilterScalarGroup,
            tIPFilterV6v0Group,
            tMacFilterV6v0Group,
            tFilterLogGroup,
            tFilterRedirectPolicyGroup,
            tFilterNotificationsGroup,
            -- tIPv6FilterV6v0Group
            tTodPolicies77450V5v0Group,
            tToDPoliciesV5v0NotifyGroup,
            tFilterLogV5v0Group
        }
    ::= { tFilterMIBCompliances 8 }

tFilter77x0V6v0Compliance MODULE-COMPLIANCE
    STATUS  obsolete
    DESCRIPTION
        "The compliance statement for management of Filter features
         on Alcatel 77x0 SPR/SR series systems release R5.0."
    MODULE  -- this module
        MANDATORY-GROUPS {
            tFilterScalarGroup,
            tIPFilterV6v0Group,
            tMacFilterV6v0Group,
            tFilterLogGroup,
            tFilterRedirectPolicyGroup,
            tFilterNotificationsGroup,
            tIPv6FilterV6v0Group,
            tTodPolicies77x0V5v0Group,
            tToDPoliciesV5v0NotifyGroup,
            tFilterLogV5v0Group
        }
    ::= { tFilterMIBCompliances 9 }

tFilter7450V8v0Compliance MODULE-COMPLIANCE
    STATUS  obsolete
    DESCRIPTION
        "The compliance statement for management of Filter features
         on Alcatel 7450 ESS series systems release R8.0."
    MODULE  -- this module
        MANDATORY-GROUPS {
            tFilterScalarGroup,
            tIPFilterV8v0Group,
            tFilterLogGroup,
            tFilterLogV5v0Group,
            tFilterRedirectPolicyGroup,
            tFilterNotificationsV8v0Group,
            tFilterNotificationObjV8v0Group,
            -- tIPv6FilterV8v0Group
            tTodPolicies77450V5v0Group,
            -- tTodPolicies77x0V5v0Group,
            tToDPoliciesV5v0NotifyGroup
        }
    ::= { tFilterMIBCompliances 10 }

tFilter77x0V8v0Compliance MODULE-COMPLIANCE
    STATUS  obsolete
    DESCRIPTION
        "The compliance statement for management of Filter features
         on Alcatel 77x0 SPR/SR series systems release R8.0."
    MODULE  -- this module
        MANDATORY-GROUPS {
            tFilterScalarGroup,
            tIPFilterV8v0Group,
            tMacFilterV8v0Group,
            tFilterLogGroup,
            tFilterLogV5v0Group,
            tFilterRedirectPolicyGroup,
            tFilterNotificationsV8v0Group,
            tFilterNotificationObjV8v0Group,
            tIPv6FilterV8v0Group,
            -- tTodPolicies77450V5v0Group,
            tTodPolicies77x0V5v0Group,
            tToDPoliciesV5v0NotifyGroup
        }
    ::= { tFilterMIBCompliances 11 }

tFilter7xxxV9v0Compliance MODULE-COMPLIANCE
    STATUS  obsolete
    DESCRIPTION
        "The compliance statement for management of Filter features
         on Alcatel 77x0 SPR/SR series systems release R9.0."
    MODULE  -- this module
        MANDATORY-GROUPS {
            tFilterScalarGroup,
            tIPFilterV9v0Group,
            tMacFilterV8v0Group,
            tFilterLogGroup,
            tFilterLogV5v0Group,
            tFilterRedirectPolicyGroup,
            tFilterNotificationsV9v0Group,
            tFilterNotificationObjV9v0Group,
            tIPv6FilterV8v0Group,
            tTodPolicies77x0V5v0Group,
            tToDPoliciesV5v0NotifyGroup,
            tMacFilterVidFilteringV9v0Group,
            tDhcpFilterV9v0Group
        }
    ::= { tFilterMIBCompliances 12 }

tFilter7xxxV10v0Compliance MODULE-COMPLIANCE
    STATUS  obsolete
    DESCRIPTION
        "The compliance statement for management of Filter features
         on Alcatel 77x0 SPR/SR series systems release R10.0."
    MODULE  -- this module
        MANDATORY-GROUPS {
            tFilterScalarGroup,
            tIPFilterV9v0Group,
            tMacFilterV8v0Group,
            tFilterLogGroup,
            tFilterLogV5v0Group,
            tFilterRedirectPolicyGroup,
            tFilterNotificationsV9v0Group,
            tFilterNotificationObjV9v0Group,
            tIPv6FilterV10v0Group,
            tTodPolicies77x0V5v0Group,
            tToDPoliciesV5v0NotifyGroup,
            tMacFilterVidFilteringV9v0Group,
            tDhcpFilterV10v0Group,
            tFilterNameV10v0Group,
            tLiFilterV10v0Group,
            tFilterPrefixListV10v0Group
        }
    ::= { tFilterMIBCompliances 13 }

tFilter7xxxV11v0Compliance MODULE-COMPLIANCE
    STATUS obsolete
    DESCRIPTION
        "The compliance statement for management of Filter features
         on Alcatel 77x0 SPR/SR series systems release R11.0."
    MODULE  -- this module
        MANDATORY-GROUPS {
            tFilterScalarGroup,
            tIPFilterV11v0Group,
            tMacFilterV8v0Group,
            tFilterLogGroup,
            tFilterLogV5v0Group,
            tFilterRedirectPolicyGroup,
            tFilterNotificationsV11v0Group,
            tFilterNotificationObjV11v0Group,
            tIPv6FilterV11v0Group,
            tTodPolicies77x0V5v0Group,
            tToDPoliciesV5v0NotifyGroup,
            tMacFilterVidFilteringV9v0Group,
            tDhcpFilterV10v0Group,
            tFilterNameV10v0Group,
            tLiFilterV10v0Group,
            tFilterPrefixListV11v0Group,
            tFilterEmbeddedInsertV11v0Group,
            tFilterPortListV11v0Group
        }
    ::= { tFilterMIBCompliances 14 }

tFilter7xxxV12v0Compliance MODULE-COMPLIANCE
    STATUS  current
    DESCRIPTION
        "The compliance statement for management of Filter features
         on Alcatel 77x0 SPR/SR series systems release R12.0."
    MODULE  -- this module
        MANDATORY-GROUPS {
            tFilterScalarGroup,
            tIPFilterV12v0Group,
            tMacFilterV8v0Group,
            tFilterLogGroup,
            tFilterLogV5v0Group,
            tFilterRedirectPolicyGroup,
            tFilterNotificationsV11v0Group,
            tFilterNotificationsV12v0Group,
            tFilterNotificationObjV12v0Group,
            tIPv6FilterV12v0Group,
            tTodPolicies77x0V5v0Group,
            tToDPoliciesV5v0NotifyGroup,
            tMacFilterVidFilteringV9v0Group,
            tDhcpFilterV10v0Group,
            tFilterNameV10v0Group,
            tLiFilterV12v0Group,
            tFilterPrefixListV11v0Group,
            tFilterEmbeddedInsertV11v0Group,
            tFilterEmbeddedInsertV12v0Group,
            tFilterPortListV11v0Group
        }
    ::= { tFilterMIBCompliances 15 }

--
-- Units of conformance
--

-- tIPFilterGroup OBJECT-GROUP
--    ::= { tFilterMIBGroups 1 }

-- tMacFilterGroup OBJECT-GROUP
--    ::= { tFilterMIBGroups 2 }

tFilterLogGroup OBJECT-GROUP
    OBJECTS {
                tFilterLogRowStatus,
                tFilterLogDestination,
                tFilterLogDescription,
                tFilterLogMaxNumEntries,
                tFilterLogSysLogId,
                tFilterLogFileId,
                tFilterLogStopOnFull,
                tFilterLogEnabled,
                tFilterLogMaxInstances,
                tFilterLogInstances,
                tFilterLogBindings
            }
    STATUS    current
    DESCRIPTION
        "The group of objects supporting management of filter log objects
        on Alcatel-Lucent SROS series systems."
    ::= { tFilterMIBGroups 3 }

tFilterRedirectPolicyGroup OBJECT-GROUP
    OBJECTS {
                tFilterRPRowStatus,
                tFilterRPDescription,
                tFilterRPAdminState,
                tFilterRPActiveDest,

                tFilterRDRowStatus,
                tFilterRDDescription,
                tFilterRDAdminPriority,
                tFilterRDOperPriority,
                tFilterRDAdminState,
                tFilterRDOperState,

                tFilterRSTRowStatus,
                tFilterRSTOID,
                tFilterRSTCommunity,
                tFilterRSTSNMPVersion,
                tFilterRSTInterval,
                tFilterRSTTimeout,
                tFilterRSTDropCount,
                tFilterRSTHoldDown,
                tFilterRSTHoldDownRemain,
                tFilterRSTLastActionTime,
                tFilterRSTLastOID,
                tFilterRSTLastType,
                tFilterRSTLastCounter32Val,
                tFilterRSTLastUnsigned32Val,
                tFilterRSTLastTimeTicksVal,
                tFilterRSTLastInt32Val,
                tFilterRSTLastOctetStringVal,
                tFilterRSTLastIpAddressVal,
                tFilterRSTLastOidVal,
                tFilterRSTLastCounter64Val,
                tFilterRSTLastOpaqueVal,
                tFilterRSTLastAction,
                tFilterRSTLastPrioChange,
                tFilterRSTNextRespIndex,

                tFilterRSTRespRowStatus,
                tFilterRSTRespAction,
                tFilterRSTRespPrioChange,
                tFilterRSTRespOID,
                tFilterRSTRespType,
                tFilterRSTCounter32Val,
                tFilterRSTUnsigned32Val,
                tFilterRSTTimeTicksVal,
                tFilterRSTInt32Val,
                tFilterRSTOctetStringVal,
                tFilterRSTIpAddressVal,
                tFilterRSTOidVal,
                tFilterRSTCounter64Val,
                tFilterRSTOpaqueVal,

                tFilterRUTRowStatus,
                tFilterRUTURL,
                tFilterRUTHTTPVersion,
                tFilterRUTInterval,
                tFilterRUTTimeout,
                tFilterRUTDropCount,
                tFilterRUTHoldDown,
                tFilterRUTHoldDownRemain,
                tFilterRUTLastActionTime,
                tFilterRUTLastRetCode,
                tFilterRUTLastAction,
                tFilterRUTLastPrioChange,

                tFilterRUTRespRowStatus,
                tFilterRUTRespAction,
                tFilterRUTRespPrioChange,

                tFilterRPTRowStatus,
                tFilterRPTInterval,
                tFilterRPTTimeout,
                tFilterRPTDropCount,
                tFilterRPTHoldDown,
                tFilterRPTHoldDownRemain,
                tFilterRPTLastActionTime,
                tFilterRPTLastAction
            }
    STATUS    current
    DESCRIPTION
        "The group of objects supporting management of filter redirect policy
         objects on Alcatel-Lucent SROS series systems."
    ::= { tFilterMIBGroups 4 }

tFilterScalarGroup OBJECT-GROUP
    OBJECTS {
                tFilterDomainLastChanged
            }
    STATUS    current
    DESCRIPTION
        "The group of objects supporting management of filter scalar
         objects on Alcatel-Lucent SROS series systems."
    ::= { tFilterMIBGroups 7 }

tFilterNotificationObjGroup OBJECT-GROUP
    OBJECTS {
                tFilterPBRDropReason
            }
    STATUS    obsolete
    DESCRIPTION
         "The group of objects supporting management of filter
          notification objects on Alcatel-Lucent SROS series systems."
    ::= { tFilterMIBGroups 8 }

tFilterNotificationsGroup NOTIFICATION-GROUP
     NOTIFICATIONS {
                 tIPFilterPBRPacketsDrop
                   }
     STATUS obsolete
     DESCRIPTION
         "The group of notifications supporting management of
          filter notifications on Alcatel-Lucent SROS series systems."
     ::= { tFilterMIBGroups 9 }

-- tAutoIPFilterR2r1Group OBJECT-GROUP
--    ::= { tFilterMIBGroups 10 }

tIPv6FilterV4v0Group OBJECT-GROUP
    OBJECTS {
                tIPv6FilterRowStatus,
                tIPv6FilterScope,
                tIPv6FilterDescription,
                tIPv6FilterDefaultAction,
                tIPv6FilterParamsRowStatus,
                tIPv6FilterParamsLogId,
                tIPv6FilterParamsDescription,
                tIPv6FilterParamsAction,
                tIPv6FilterParamsForwardNH,
                tIPv6FilterParamsForwardNHIndirect,
                tIPv6FilterParamsRemarkDSCP,
                tIPv6FilterParamsRemarkDSCPMask,
                tIPv6FilterParamsRemarkDot1p,
                tIPv6FilterParamsSourceIpAddr,
                tIPv6FilterParamsSourceIpMask,
                tIPv6FilterParamsDestinationIpAddr,
                tIPv6FilterParamsDestinationIpMask,
                tIPv6FilterParamsNextHeader,
                tIPv6FilterParamsSourcePortValue1,
                tIPv6FilterParamsSourcePortValue2,
                tIPv6FilterParamsSourcePortOperator,
                tIPv6FilterParamsDestPortValue1,
                tIPv6FilterParamsDestPortValue2,
                tIPv6FilterParamsDestPortOperator,
                tIPv6FilterParamsDSCP,
                tIPv6FilterParamsTcpSyn,
                tIPv6FilterParamsTcpAck,
                tIPv6FilterParamsIcmpCode,
                tIPv6FilterParamsIcmpType,
                tIPv6FilterParamsCflowdSample,
                tIPv6FilterParamsCflowdIfSample,
                tIPv6FilterParamsForwardNHInterface,
                tIPv6FilterParamsIngressHitCount,
                tIPv6FilterParamsEgressHitCount,
                tIPv6FilterParamsLogInstantiated,
                tIPv6FilterParamsForwardRedPlcy,
                tIPv6FilterParamsActiveDest
            }
    STATUS obsolete
    DESCRIPTION
        "The group of objects supporting management of IPv6 filter objects
         on Alcatel-Lucent SROS series systems."
    ::= { tFilterMIBGroups 11 }

tIPFilterV4v0Group OBJECT-GROUP
    OBJECTS {
                tIPFilterRowStatus,
                tIPFilterScope,
                tIPFilterDescription,
                tIPFilterDefaultAction,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL
            }
    STATUS obsolete
    DESCRIPTION
        "The group of objects supporting IP Filters
         on Alcatel 7x50 ESS/SR series systems 4.0 release."
    ::= { tFilterMIBGroups 12 }

tMacFilterV4v0Group OBJECT-GROUP
    OBJECTS {
                tMacFilterRowStatus,
                tMacFilterScope,
                tMacFilterDescription,
                tMacFilterDefaultAction,
                tMacFilterParamsRowStatus,
                tMacFilterParamsLogId,
                tMacFilterParamsDescription,
                tMacFilterParamsAction,
                tMacFilterParamsFrameType,
                tMacFilterParamsSrcMAC,
                tMacFilterParamsSrcMACMask,
                tMacFilterParamsDstMAC,
                tMacFilterParamsDstMACMask,
                tMacFilterParamsDot1pValue,
                tMacFilterParamsDot1pMask,
                tMacFilterParamsEtherType,
                tMacFilterParamsDsap,
                tMacFilterParamsDsapMask,
                tMacFilterParamsSsap,
                tMacFilterParamsSsapMask,
                tMacFilterParamsSnapPid,
                tMacFilterParamsSnapOui,
                tMacFilterParamsIngressHitCount,
                tMacFilterParamsEgressHitCount,
                tMacFilterParamsLogInstantiated,
                tMacFilterParamsFwdSvcId,
                tMacFilterParamsFwdSapPortId,
                tMacFilterParamsFwdSapEncapVal,
                tMacFilterParamsFwdSdpBind,
                tMacFilterParamsRedirectURL
            }
    STATUS obsolete
    DESCRIPTION
        "The group of objects supporting management of mac filter objects
         on Alcatel-Lucent SROS series systems 4.0 release."
    ::= { tFilterMIBGroups 13 }

tTodPoliciesV4v0Group OBJECT-GROUP
    OBJECTS {
                tIPFilterParamsTimeRangeName,
                tIPFilterParamsTimeRangeState,
                tMacFilterParamsTimeRangeName,
                tMacFilterParamsTimeRangeState,
                tIPv6FilterParamsTimeRangeName,
                tIPv6FilterParamsTimeRangeState
            }
    STATUS obsolete
    DESCRIPTION
        "The group of objects supporting management of time of day policy
         related objects on Alcatel-Lucent SROS series systems 4.0 release."
    ::= { tFilterMIBGroups 14 }

tmnxFilterObsoleteGroup OBJECT-GROUP
    OBJECTS {
                tAutoIPFilterEntrySourceIpMask
            }
    STATUS current
    DESCRIPTION
        "The group of objects in TIMETRA-FILTER-MIB which are obsoleted."
    ::= { tFilterMIBGroups 15 }

tToDPoliciesV5v0NotifyGroup NOTIFICATION-GROUP
     NOTIFICATIONS {
                 tFilterEntryActivationFailed,
                 tFilterEntryActivationRestored
            }
     STATUS current
     DESCRIPTION
        "The group of notifications generated by the time of time of day
         policy feature on Alcatel-Lucent SROS series systems 5.0 release."
     ::= { tFilterMIBGroups 16 }

tIPFilterV5v0Group OBJECT-GROUP
    OBJECTS {
                tIPFilterRowStatus,
                tIPFilterScope,
                tIPFilterDescription,
                tIPFilterDefaultAction,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL,
                tIPFilterParamsSrcIpFullMask,
                tIPFilterParamsDestIpFullMask
            }
    STATUS obsolete
    DESCRIPTION
        "The group of objects supporting IP Filters
         on Alcatel 7x50 ESS/SR series systems 5.0 release."
    ::= { tFilterMIBGroups 17 }

tFilterLogV5v0Group OBJECT-GROUP
    OBJECTS {
                tFilterLogSummaryEnabled,
                tFilterLogSummaryCrit1
            }
    STATUS current
    DESCRIPTION
        "The group of objects supporting Filter Log Summarization
         on Alcatel 7x50 ESS/SR series systems 5.0 release."
    ::= { tFilterMIBGroups 18 }

tTodPolicies77450V5v0Group OBJECT-GROUP
    OBJECTS {
                tIPFilterParamsTimeRangeName,
                tIPFilterParamsTimeRangeState,
                tMacFilterParamsTimeRangeName,
                tMacFilterParamsTimeRangeState
            }
    STATUS obsolete
    DESCRIPTION
        "The group of objects supporting management of time of day policy
         related objects on Alcatel 7450 ESS series systems 5.0 release.

        This group was made obsolete for Alcatel SROS Release 9.0."
    ::= { tFilterMIBGroups 19 }

tTodPolicies77x0V5v0Group OBJECT-GROUP
    OBJECTS {
                tIPFilterParamsTimeRangeName,
                tIPFilterParamsTimeRangeState,
                tMacFilterParamsTimeRangeName,
                tMacFilterParamsTimeRangeState,
                tIPv6FilterParamsTimeRangeName,
                tIPv6FilterParamsTimeRangeState
            }
    STATUS current
    DESCRIPTION
        "The group of objects supporting management of time of day policy
         related objects on Alcatel 77x0 series systems 5.0 release."
    ::= { tFilterMIBGroups 20 }

tFilterNotificationObjV5v0Group OBJECT-GROUP
    OBJECTS {
                tFilterPBRDropReason,
                tFilterParmRow,
                tFilterAlarmDescription
            }
    STATUS obsolete
    DESCRIPTION
         "The group of objects supporting management of filter
          notification objects on Alcatel-Lucent SROS series systems."
    ::= { tFilterMIBGroups 21 }

tIPFilterV6v0Group OBJECT-GROUP
    OBJECTS {
                tIPFilterRowStatus,
                tIPFilterScope,
                tIPFilterDescription,
                tIPFilterDefaultAction,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL,
                tIPFilterParamsSrcIpFullMask,
                tIPFilterParamsDestIpFullMask,
                tIPFilterParamsIngrHitByteCount,
                tIPFilterParamsEgrHitByteCount
            }
    STATUS obsolete
    DESCRIPTION
        "The group of objects supporting IP Filters
         on Alcatel 7x50 ESS/SR series systems 6.0 release."
    ::= { tFilterMIBGroups 22 }

tMacFilterV6v0Group OBJECT-GROUP
    OBJECTS {
                tMacFilterRowStatus,
                tMacFilterScope,
                tMacFilterDescription,
                tMacFilterDefaultAction,
                tMacFilterParamsRowStatus,
                tMacFilterParamsLogId,
                tMacFilterParamsDescription,
                tMacFilterParamsAction,
                tMacFilterParamsFrameType,
                tMacFilterParamsSrcMAC,
                tMacFilterParamsSrcMACMask,
                tMacFilterParamsDstMAC,
                tMacFilterParamsDstMACMask,
                tMacFilterParamsDot1pValue,
                tMacFilterParamsDot1pMask,
                tMacFilterParamsEtherType,
                tMacFilterParamsDsap,
                tMacFilterParamsDsapMask,
                tMacFilterParamsSsap,
                tMacFilterParamsSsapMask,
                tMacFilterParamsSnapPid,
                tMacFilterParamsSnapOui,
                tMacFilterParamsIngressHitCount,
                tMacFilterParamsEgressHitCount,
                tMacFilterParamsLogInstantiated,
                tMacFilterParamsFwdSvcId,
                tMacFilterParamsFwdSapPortId,
                tMacFilterParamsFwdSapEncapVal,
                tMacFilterParamsFwdSdpBind,
                tMacFilterParamsRedirectURL,
                tMacFilterParamsIngrHitByteCount,
                tMacFilterParamsEgrHitByteCount
            }
    STATUS obsolete
    DESCRIPTION
        "The group of objects supporting management of mac filter objects
         on Alcatel-Lucent SROS series systems 6.0 release."
    ::= { tFilterMIBGroups 23 }

tIPv6FilterV6v0Group OBJECT-GROUP
    OBJECTS {
                tIPv6FilterRowStatus,
                tIPv6FilterScope,
                tIPv6FilterDescription,
                tIPv6FilterDefaultAction,
                tIPv6FilterParamsRowStatus,
                tIPv6FilterParamsLogId,
                tIPv6FilterParamsDescription,
                tIPv6FilterParamsAction,
                tIPv6FilterParamsForwardNH,
                tIPv6FilterParamsForwardNHIndirect,
                tIPv6FilterParamsRemarkDSCP,
                tIPv6FilterParamsRemarkDSCPMask,
                tIPv6FilterParamsRemarkDot1p,
                tIPv6FilterParamsSourceIpAddr,
                tIPv6FilterParamsSourceIpMask,
                tIPv6FilterParamsDestinationIpAddr,
                tIPv6FilterParamsDestinationIpMask,
                tIPv6FilterParamsNextHeader,
                tIPv6FilterParamsSourcePortValue1,
                tIPv6FilterParamsSourcePortValue2,
                tIPv6FilterParamsSourcePortOperator,
                tIPv6FilterParamsDestPortValue1,
                tIPv6FilterParamsDestPortValue2,
                tIPv6FilterParamsDestPortOperator,
                tIPv6FilterParamsDSCP,
                tIPv6FilterParamsTcpSyn,
                tIPv6FilterParamsTcpAck,
                tIPv6FilterParamsIcmpCode,
                tIPv6FilterParamsIcmpType,
                tIPv6FilterParamsCflowdSample,
                tIPv6FilterParamsCflowdIfSample,
                tIPv6FilterParamsForwardNHInterface,
                tIPv6FilterParamsIngressHitCount,
                tIPv6FilterParamsEgressHitCount,
                tIPv6FilterParamsLogInstantiated,
                tIPv6FilterParamsForwardRedPlcy,
                tIPv6FilterParamsActiveDest,
                tIPv6FilterParamsIngrHitByteCount,
                tIPv6FilterParamsEgrHitByteCount
            }
    STATUS obsolete
    DESCRIPTION
        "The group of objects supporting management of IPv6 filter objects
         on Alcatel-Lucent SROS series systems."
    ::= { tFilterMIBGroups 24 }

tIPFilterV8v0Group OBJECT-GROUP
    OBJECTS {
                tIPFilterRowStatus,
                tIPFilterScope,
                tIPFilterDescription,
                tIPFilterDefaultAction,
                tIPFilterRadiusInsertPt,
                tIPFilterRadiusInsertSize,
                tIPFilterCreditCntrlInsertPt,
                tIPFilterCreditCntrlInsertSize,
                tIPFilterSubInsertHighWmark,
                tIPFilterSubInsertLowWmark,
                tIpFilterCreditCntrlNbrInsertd,
                tIpFilterRadiusNbrInsertd,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL,
                tIPFilterParamsSrcIpFullMask,
                tIPFilterParamsDestIpFullMask,
                tIPFilterParamsIngrHitByteCount,
                tIPFilterParamsEgrHitByteCount,
                tFltrGrpInsrtdEntriesFilterType,
                tFltrGrpInsrtdEntriesFilterId,
                tFltrGrpInsrtdEntriesApplication,
                tFltrGrpInsrtdEntriesLocation,
                tFltrGrpInsrtdEntriesResult,
                tFltrGrpInsrtdEntriesFeedback,
                tFltrGrpInsrtdEntriesExecute
            }
    STATUS obsolete
    DESCRIPTION
        "The group of objects supporting IP Filters
         on Alcatel 7x50 ESS/SR series systems 8.0 release."
    ::= { tFilterMIBGroups 25 }

tIPv6FilterV8v0Group OBJECT-GROUP
    OBJECTS {
                tIPv6FilterRowStatus,
                tIPv6FilterScope,
                tIPv6FilterDescription,
                tIPv6FilterDefaultAction,
                tIPv6FilterRadiusInsertPt,
                tIPv6FilterRadiusInsertSize,
                tIPv6FilterCreditCntrlInsertPt,
                tIPv6FilterCreditCntrlInsertSize,
                tIPv6FilterSubInsertHighWmark,
                tIPv6FilterSubInsertLowWmark,
                tIpv6FilterCreditCntrlNbrInsertd,
                tIpv6FilterRadiusNbrInsertd,
                tIPv6FilterParamsRowStatus,
                tIPv6FilterParamsLogId,
                tIPv6FilterParamsDescription,
                tIPv6FilterParamsAction,
                tIPv6FilterParamsForwardNH,
                tIPv6FilterParamsForwardNHIndirect,
                tIPv6FilterParamsRemarkDSCP,
                tIPv6FilterParamsRemarkDSCPMask,
                tIPv6FilterParamsRemarkDot1p,
                tIPv6FilterParamsSourceIpAddr,
                tIPv6FilterParamsSourceIpMask,
                tIPv6FilterParamsDestinationIpAddr,
                tIPv6FilterParamsDestinationIpMask,
                tIPv6FilterParamsNextHeader,
                tIPv6FilterParamsSourcePortValue1,
                tIPv6FilterParamsSourcePortValue2,
                tIPv6FilterParamsSourcePortOperator,
                tIPv6FilterParamsDestPortValue1,
                tIPv6FilterParamsDestPortValue2,
                tIPv6FilterParamsDestPortOperator,
                tIPv6FilterParamsDSCP,
                tIPv6FilterParamsTcpSyn,
                tIPv6FilterParamsTcpAck,
                tIPv6FilterParamsIcmpCode,
                tIPv6FilterParamsIcmpType,
                tIPv6FilterParamsCflowdSample,
                tIPv6FilterParamsCflowdIfSample,
                tIPv6FilterParamsForwardNHInterface,
                tIPv6FilterParamsIngressHitCount,
                tIPv6FilterParamsEgressHitCount,
                tIPv6FilterParamsLogInstantiated,
                tIPv6FilterParamsForwardRedPlcy,
                tIPv6FilterParamsActiveDest,
                tIPv6FilterParamsIngrHitByteCount,
                tIPv6FilterParamsEgrHitByteCount
            }
    STATUS obsolete
    DESCRIPTION
        "The group of objects supporting management of IPv6 filter objects
         on Alcatel-Lucent SROS series systems."
    ::= { tFilterMIBGroups 26 }

tFilterNotificationObjV8v0Group OBJECT-GROUP
    OBJECTS {
                tFilterPBRDropReason,
                tFilterParmRow,
                tFilterAlarmDescription,
                tFilterId,
                tFilterType,
                tFilterSubInsSpaceOwner,
                tFilterThresholdReached
            }
    STATUS obsolete
    DESCRIPTION
         "The group of objects supporting management of filter
          notification objects on Alcatel-Lucent SROS series systems."
    ::= { tFilterMIBGroups 27 }

tFilterNotificationsV8v0Group NOTIFICATION-GROUP
     NOTIFICATIONS {
                 tIPFilterPBRPacketsDrop,
                 tFilterSubInsSpaceAlarmRaised,
                 tFilterSubInsSpaceAlarmCleared,
                 tFilterSubInsFltrEntryDropped
            }
     STATUS obsolete
     DESCRIPTION
         "The group of notifications supporting management of
          filter notifications on Alcatel-Lucent SROS series systems."
     ::= { tFilterMIBGroups 28 }

tMacFilterV8v0Group OBJECT-GROUP
    OBJECTS {
                tMacFilterRowStatus,
                tMacFilterScope,
                tMacFilterDescription,
                tMacFilterDefaultAction,
                tMacFilterParamsRowStatus,
                tMacFilterParamsLogId,
                tMacFilterParamsDescription,
                tMacFilterParamsAction,
                tMacFilterParamsFrameType,
                tMacFilterParamsSrcMAC,
                tMacFilterParamsSrcMACMask,
                tMacFilterParamsDstMAC,
                tMacFilterParamsDstMACMask,
                tMacFilterParamsDot1pValue,
                tMacFilterParamsDot1pMask,
                tMacFilterParamsEtherType,
                tMacFilterParamsDsap,
                tMacFilterParamsDsapMask,
                tMacFilterParamsSsap,
                tMacFilterParamsSsapMask,
                tMacFilterParamsSnapPid,
                tMacFilterParamsSnapOui,
                tMacFilterParamsIngressHitCount,
                tMacFilterParamsEgressHitCount,
                tMacFilterParamsLogInstantiated,
                tMacFilterParamsFwdSvcId,
                tMacFilterParamsFwdSapPortId,
                tMacFilterParamsFwdSapEncapVal,
                tMacFilterParamsFwdSdpBind,
                tMacFilterParamsRedirectURL,
                tMacFilterParamsIngrHitByteCount,
                tMacFilterParamsEgrHitByteCount,
                tMacFilterParamsLowISID,
                tMacFilterParamsHighISID,
                tMacFilterType
            }
    STATUS current
    DESCRIPTION
     "The group of objects supporting management of mac filter objects
     on Alcatel-Lucent SROS series systems 8.0 release."
    ::= { tFilterMIBGroups 29 }

tMacFilterVidFilteringV9v0Group OBJECT-GROUP
    OBJECTS {
                tMacFilterParamsInnerTagValue,
                tMacFilterParamsInnerTagMask,
                tMacFilterParamsOuterTagValue,
                tMacFilterParamsOuterTagMask
            }
    STATUS current
    DESCRIPTION
     "The group of objects supporting management of mac VID filtering objects
      on Alcatel-Lucent SROS series systems 9.0 release."
    ::= { tFilterMIBGroups 30 }

tIPFilterV9v0Group OBJECT-GROUP
    OBJECTS {
                tIPFilterRowStatus,
                tIPFilterScope,
                tIPFilterDescription,
                tIPFilterDefaultAction,
                tIPFilterRadiusInsertPt,
                tIPFilterRadiusInsertSize,
                tIPFilterCreditCntrlInsertPt,
                tIPFilterCreditCntrlInsertSize,
                tIPFilterSubInsertHighWmark,
                tIPFilterSubInsertLowWmark,
                tIpFilterCreditCntrlNbrInsertd,
                tIpFilterRadiusNbrInsertd,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL,
                tIPFilterParamsSrcIpFullMask,
                tIPFilterParamsDestIpFullMask,
                tIPFilterParamsIngrHitByteCount,
                tIPFilterParamsEgrHitByteCount,
                tFltrGrpInsrtdEntriesFilterType,
                tFltrGrpInsrtdEntriesFilterId,
                tFltrGrpInsrtdEntriesApplication,
                tFltrGrpInsrtdEntriesLocation,
                tFltrGrpInsrtdEntriesResult,
                tFltrGrpInsrtdEntriesFeedback,
                tFltrGrpInsrtdEntriesExecute,
                tIPFilterParamsFwdRtrId,
                tIPFilterParamsSrcRouteOption
            }
    STATUS obsolete
    DESCRIPTION
        "The group of objects supporting IP Filters
         on Alcatel 7x50 ESS/SR series systems 9.0 release."
    ::= { tFilterMIBGroups 31 }

tFilterNotificationsV9v0Group NOTIFICATION-GROUP
     NOTIFICATIONS {
                 tIPFilterPBRPacketsDrop,
                 tFilterSubInsSpaceAlarmRaised,
                 tFilterSubInsSpaceAlarmCleared,
                 tFilterSubInsFltrEntryDropped,
                 tFilterBgpFlowSpecProblem
            }
     STATUS obsolete
     DESCRIPTION
         "The group of notifications supporting management of
          filter notifications on Alcatel-Lucent SROS series systems."
     ::= { tFilterMIBGroups 32 }

tFilterNotificationObjV9v0Group OBJECT-GROUP
    OBJECTS {
                tFilterPBRDropReason,
                tFilterParmRow,
                tFilterAlarmDescription,
                tFilterId,
                tFilterType,
                tFilterSubInsSpaceOwner,
                tFilterThresholdReached,
                tFltrFlowSpecProblem,
                tFltrFlowSpecProblemDescription,
                tFltrFLowSpecNLRI,
                tFltrFlowSpecVrtrId
            }
    STATUS    obsolete
    DESCRIPTION
         "The group of objects supporting management of filter
          notification objects on Alcatel-Lucent SROS series systems."
    ::= { tFilterMIBGroups 33 }

tDhcpFilterV9v0Group OBJECT-GROUP
    OBJECTS {
                tDhcpFilterTableLastChanged,
                tDhcpFilterRowStatus,
                tDhcpFilterLastChanged,
                tDhcpFilterDescription,
                tDhcpFilterParamsTblLastChanged,
                tDhcpFilterParamsRowStatus,
                tDhcpFilterParamsLastChanged,
                tDhcpFilterParamsOptionNumber,
                tDhcpFilterParamsOptionMatch,
                tDhcpFilterParamsAction
            }
    STATUS    obsolete
    DESCRIPTION
        "The group of objects supporting DHCP Filters
         on Alcatel 7x50 ESS/SR series systems 9.0 release."
    ::= { tFilterMIBGroups 34 }

tIPv6FilterV10v0Group OBJECT-GROUP
    OBJECTS {
                tIPv6FilterRowStatus,
                tIPv6FilterScope,
                tIPv6FilterDescription,
                tIPv6FilterDefaultAction,
                tIPv6FilterRadiusInsertPt,
                tIPv6FilterRadiusInsertSize,
                tIPv6FilterCreditCntrlInsertPt,
                tIPv6FilterCreditCntrlInsertSize,
                tIPv6FilterSubInsertHighWmark,
                tIPv6FilterSubInsertLowWmark,
                tIpv6FilterCreditCntrlNbrInsertd,
                tIpv6FilterRadiusNbrInsertd,
                tIPv6FilterParamsRowStatus,
                tIPv6FilterParamsLogId,
                tIPv6FilterParamsDescription,
                tIPv6FilterParamsAction,
                tIPv6FilterParamsForwardNH,
                tIPv6FilterParamsForwardNHIndirect,
                tIPv6FilterParamsRemarkDSCP,
                tIPv6FilterParamsRemarkDSCPMask,
                tIPv6FilterParamsRemarkDot1p,
                tIPv6FilterParamsSourceIpAddr,
                tIPv6FilterParamsSourceIpMask,
                tIPv6FilterParamsDestinationIpAddr,
                tIPv6FilterParamsDestinationIpMask,
                tIPv6FilterParamsNextHeader,
                tIPv6FilterParamsSourcePortValue1,
                tIPv6FilterParamsSourcePortValue2,
                tIPv6FilterParamsSourcePortOperator,
                tIPv6FilterParamsDestPortValue1,
                tIPv6FilterParamsDestPortValue2,
                tIPv6FilterParamsDestPortOperator,
                tIPv6FilterParamsDSCP,
                tIPv6FilterParamsTcpSyn,
                tIPv6FilterParamsTcpAck,
                tIPv6FilterParamsIcmpCode,
                tIPv6FilterParamsIcmpType,
                tIPv6FilterParamsCflowdSample,
                tIPv6FilterParamsCflowdIfSample,
                tIPv6FilterParamsForwardNHInterface,
                tIPv6FilterParamsIngressHitCount,
                tIPv6FilterParamsEgressHitCount,
                tIPv6FilterParamsLogInstantiated,
                tIPv6FilterParamsForwardRedPlcy,
                tIPv6FilterParamsActiveDest,
                tIPv6FilterParamsIngrHitByteCount,
                tIPv6FilterParamsEgrHitByteCount,
                tIPv6FilterParamsFwdSvcId,
                tIPv6FilterParamsFwdSapPortId,
                tIPv6FilterParamsFwdSapEncapVal,
                tIPv6FilterParamsFwdSdpBind
            }
    STATUS obsolete
    DESCRIPTION
        "The group of objects supporting management of IPv6 filter objects
         on Alcatel-Lucent SROS series systems."
    ::= { tFilterMIBGroups 35 }

tFilterNameV10v0Group OBJECT-GROUP
    OBJECTS {
         tIpFilterName,
         tIpFilterNameId,
         tIpFilterNameLastChanged,
         tIpFilterNameRowStatus,
         tIpFilterNameTableLastChgd,
         tIpv6FilterName,
         tIpv6FilterNameId,
         tIpv6FilterNameLastChanged,
         tIpv6FilterNameRowStatus,
         tIpv6FilterNameTableLastChgd,
         tMacFilterName,
         tMacFilterNameId,
         tMacFilterNameLastChanged,
         tMacFilterNameRowStatus,
         tMacFilterNameTableLastChgd
    }
    STATUS  current
    DESCRIPTION
        "The group of objects supporting management of filter-name objects
         on Alcatel-Lucent SROS series systems."
    ::= { tFilterMIBGroups 36 }

tDhcpFilterV10v0Group OBJECT-GROUP
    OBJECTS {
                tDhcpFilterTableLastChanged,
                tDhcpFilterRowStatus,
                tDhcpFilterLastChanged,
                tDhcpFilterDescription,
                tDhcpFilterParamsTblLastChanged,
                tDhcpFilterParamsRowStatus,
                tDhcpFilterParamsLastChanged,
                tDhcpFilterParamsOptionNumber,
                tDhcpFilterParamsOptionMatch,
                tDhcpFilterParamsAction,
                tDhcpFilterParamsOptionValue
            }
    STATUS    current
    DESCRIPTION
        "The group of objects supporting DHCP Filters
         on Alcatel 7x50 ESS/SR series systems 10.0 release."
    ::= { tFilterMIBGroups 37 }

tLiFilterV10v0Group OBJECT-GROUP
    OBJECTS {
        tLiReservedBlockRowStatus,
        tLiReservedBlockDescription,
        tLiReservedBlockStart,
        tLiReservedBlockSize,
        tLiReservedBlockLastChanged,
        tLiReservedBlockTableLastChanged,
        tLiReservedBlockFltrRowStatus,
        tLiReservedBlockFltrLastChanged,
        tLiReservedBlockFltrTableLastChg,
        tLiFilterDescription,
        tLiFilterRowStatus,
        tLiFilterLastChanged,
        tLiFilterTableLastChanged,
        tLiFilterAssociationRowStatus,
        tLiFilterAssociationLastChg,
        tLiFilterAssociationTableLastChg,
        tLiMacFilterParamsDescription,
        tLiMacFilterParamsDstMAC,
        tLiMacFilterParamsDstMACMask,
        tLiMacFilterParamsFrameType,
        tLiMacFilterParamsRowStatus,
        tLiMacFilterParamsSrcMAC,
        tLiMacFilterParamsSrcMACMask,
        tLiMacFilterParamsLastChanged,
        tLiMacFilterParamsTableLastChg,
        tLiMacFilterParamsIngrHitCount,
        tLiMacFilterParamsEgrHitCount,
        tLiMacFilterParamsIngrHitBytes,
        tLiMacFilterParamsEgrHitBytes
    }
    STATUS    obsolete
    DESCRIPTION
        "The group of objects supporting management of LI filter entries
         on Alcatel-Lucent SROS series systems 10.0 release."
    ::= { tFilterMIBGroups 38 }

tFilterPrefixListV10v0Group OBJECT-GROUP
    OBJECTS {
        tFilterPrefixListTableLstChng,
        tFilterPrefixListRowStatus,
        tFilterPrefixListLastChanged,
        tFilterPrefixListDescription,
        tFilterPrefixListEntryTblLstChg,
        tFilterPrefixListEntryRowStatus,
        tIPFilterParamsSrcIpPrefixList,
        tIPFilterParamsDstIpPrefixList
    }
    STATUS    obsolete
    DESCRIPTION
        "The group of objects supporting management of IP prefix lists
        in IP filters on Alcatel-Lucent SROS series systems
        10.0 release."
    ::= { tFilterMIBGroups 39 }

tIPv6FilterV11v0Group OBJECT-GROUP
    OBJECTS {
        tIPv6FilterRowStatus,
        tIPv6FilterScope,
        tIPv6FilterDescription,
        tIPv6FilterDefaultAction,
        tIPv6FilterRadiusInsertPt,
        tIPv6FilterRadiusInsertSize,
        tIPv6FilterCreditCntrlInsertPt,
        tIPv6FilterCreditCntrlInsertSize,
        tIPv6FilterSubInsertHighWmark,
        tIPv6FilterSubInsertLowWmark,
        tIpv6FilterCreditCntrlNbrInsertd,
        tIpv6FilterRadiusNbrInsertd,
        tIPv6FilterHostSharedInsertPt,
        tIPv6FilterHostSharedInsertSize,
        tIpv6FilterHostSharedNbrInsertd,
        tIPv6FilterHostSharedHighWmark,
        tIPv6FilterHostSharedLowWmark,
        tIPv6FilterNbrHostSharedFltrs,
        tIPv6FilterParamsRowStatus,
        tIPv6FilterParamsLogId,
        tIPv6FilterParamsDescription,
        tIPv6FilterParamsAction,
        tIPv6FilterParamsForwardNH,
        tIPv6FilterParamsForwardNHIndirect,
        tIPv6FilterParamsRemarkDSCP,
        tIPv6FilterParamsRemarkDSCPMask,
        tIPv6FilterParamsRemarkDot1p,
        tIPv6FilterParamsSourceIpAddr,
        tIPv6FilterParamsSourceIpMask,
        tIPv6FilterParamsDestinationIpAddr,
        tIPv6FilterParamsDestinationIpMask,
        tIPv6FilterParamsNextHeader,
        tIPv6FilterParamsSourcePortValue1,
        tIPv6FilterParamsSourcePortValue2,
        tIPv6FilterParamsSourcePortOperator,
        tIPv6FilterParamsDestPortValue1,
        tIPv6FilterParamsDestPortValue2,
        tIPv6FilterParamsDestPortOperator,
        tIPv6FilterParamsDSCP,
        tIPv6FilterParamsTcpSyn,
        tIPv6FilterParamsTcpAck,
        tIPv6FilterParamsIcmpCode,
        tIPv6FilterParamsIcmpType,
        tIPv6FilterParamsCflowdSample,
        tIPv6FilterParamsCflowdIfSample,
        tIPv6FilterParamsForwardNHInterface,
        tIPv6FilterParamsIngressHitCount,
        tIPv6FilterParamsEgressHitCount,
        tIPv6FilterParamsLogInstantiated,
        tIPv6FilterParamsForwardRedPlcy,
        tIPv6FilterParamsActiveDest,
        tIPv6FilterParamsIngrHitByteCount,
        tIPv6FilterParamsEgrHitByteCount,
        tIPv6FilterParamsFwdSvcId,
        tIPv6FilterParamsFwdSapPortId,
        tIPv6FilterParamsFwdSapEncapVal,
        tIPv6FilterParamsFwdSdpBind,
        tIPv6FilterParamsRedirectURL,
        tIPv6FilterParamsSrcIpPrefixList,
        tIPv6FilterParamsDstIpPrefixList,
        tIPv6FilterParamsFragment,
        tIPv6FilterParamsHopByHopOpt,
        tIPv6FilterParamsRoutingType0,
        tIPv6FilterParamsPortSelector,
        tIPv6FilterParamsSrcPortList,
        tIPv6FilterParamsDstPortList,
        tIPv6FilterParamsFwdRtrId
    }
    STATUS    obsolete
    DESCRIPTION
        "The group of objects supporting management of IPv6 filter objects
        on Alcatel-Lucent SROS series systems."
    ::= { tFilterMIBGroups 40 }

tFilterEmbeddedInsertV11v0Group OBJECT-GROUP
    OBJECTS {
        tFilterEmbeddedRefRowStatus      ,
        tFilterEmbeddedRefTableLstChg    ,
        tFilterEmbeddedRefOperState      ,
        tFilterEmbeddedRefAdminState     ,
        tFltrEmbedRefInfEntryCnt         ,
        tFltrEmbedRefInfEntryCntInsrtd   ,
        tFltrEmbedEntryInsrtEntryId      ,
        tFltrEmbedEntryRefOperState
    }
    STATUS current
    DESCRIPTION
        "The group of objects supporting the creation of embedded filters
         for Alcatel-Lucent SROS systems 11.0 release."
    ::= { tFilterMIBGroups 41 }

tFilterPortListV11v0Group OBJECT-GROUP
    OBJECTS {
        tFilterPortListTableLstChng,
        tFilterPortListRowStatus,
        tFilterPortListLastChanged,
        tFilterPortListDescription,
        tFilterPortListEntryTblLstChg,
        tFilterPortListEntryRowStatus
    }
    STATUS    current
    DESCRIPTION
        "The group of objects supporting the management of port lists
         for filters on Alcatel-Lucent SROS series systems 11.0 release."
    ::= { tFilterMIBGroups 42 }

tFilterPrefixListV11v0Group OBJECT-GROUP
    OBJECTS {
        tFilterPrefixListTableLstChng,
        tFilterPrefixListRowStatus,
        tFilterPrefixListLastChanged,
        tFilterPrefixListDescription,
        tFilterPrefixListEntryTblLstChg,
        tFilterPrefixListEntryRowStatus,
        tIPFilterParamsSrcIpPrefixList,
        tIPFilterParamsDstIpPrefixList,
        tFilterApplyPathTableLstChng,
        tFilterApplyPathRowStatus,
        tFilterApplyPathLastChanged,
        tFilterApplyPathMatch1,
        tFilterApplyPathMatch2
    }
    STATUS    current
    DESCRIPTION
        "The group of objects supporting management of IP prefix lists
        in IP filters on Alcatel-Lucent SROS series systems
        11.0 release."
    ::= { tFilterMIBGroups 43 }

tIPFilterV11v0Group OBJECT-GROUP
    OBJECTS {
                tIPFilterRowStatus,
                tIPFilterScope,
                tIPFilterDescription,
                tIPFilterDefaultAction,
                tIPFilterRadiusInsertPt,
                tIPFilterRadiusInsertSize,
                tIPFilterCreditCntrlInsertPt,
                tIPFilterCreditCntrlInsertSize,
                tIPFilterSubInsertHighWmark,
                tIPFilterSubInsertLowWmark,
                tIpFilterCreditCntrlNbrInsertd,
                tIpFilterRadiusNbrInsertd,
                tIPFilterHostSharedInsertPt,
                tIPFilterHostSharedInsertSize,
                tIpFilterHostSharedNbrInsertd,
                tIPFilterHostSharedHighWmark,
                tIPFilterHostSharedLowWmark,
                tIPFilterNbrHostSharedFltrs,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL,
                tIPFilterParamsSrcIpFullMask,
                tIPFilterParamsDestIpFullMask,
                tIPFilterParamsIngrHitByteCount,
                tIPFilterParamsEgrHitByteCount,
                tFltrGrpInsrtdEntriesFilterType,
                tFltrGrpInsrtdEntriesFilterId,
                tFltrGrpInsrtdEntriesApplication,
                tFltrGrpInsrtdEntriesLocation,
                tFltrGrpInsrtdEntriesResult,
                tFltrGrpInsrtdEntriesFeedback,
                tFltrGrpInsrtdEntriesExecute,
                tIPFilterParamsFwdRtrId,
                tIPFilterParamsSrcRouteOption,
                tIPFilterParamsPortSelector,
                tIPFilterParamsSrcPortList,
                tIPFilterParamsDstPortList,
                tIPFilterParamsExtTbleLstChgd,
                tIPFilterParamsExtLastChanged,
                tIPFilterParamsExtPktLenVal1,
                tIPFilterParamsExtPktLenVal2,
                tIPFilterParamsExtPktLenOper
            }
    STATUS    obsolete
    DESCRIPTION
        "The group of objects supporting IP Filters
         on Alcatel 7x50 ESS/SR series systems 11.0 release."
    ::= { tFilterMIBGroups 44 }

tFilterNotificationsV11v0Group NOTIFICATION-GROUP
     NOTIFICATIONS {
                 tIPFilterPBRPacketsDrop,
                 tFilterSubInsSpaceAlarmRaised,
                 tFilterSubInsSpaceAlarmCleared,
                 tFilterSubInsFltrEntryDropped,
                 tFilterBgpFlowSpecProblem,
                 tFilterApplyPathProblem,
                 tFilterRadSharedFltrAlarmRaised,
                 tFilterRadSharedFltrAlarmClear,
                 tFilterEmbeddingOperStateChange
            }
     STATUS current
     DESCRIPTION
         "The group of notifications supporting management of
          filter notifications on Alcatel-Lucent SROS series systems."
     ::= { tFilterMIBGroups 45 }

tFilterNotificationObjV11v0Group OBJECT-GROUP
    OBJECTS {
                tFilterPBRDropReason,
                tFilterParmRow,
                tFilterAlarmDescription,
                tFilterId,
                tFilterType,
                tFilterSubInsSpaceOwner,
                tFilterThresholdReached,
                tFltrFlowSpecProblem,
                tFltrFlowSpecProblemDescription,
                tFltrFLowSpecNLRI,
                tFltrFlowSpecVrtrId,
                tFltrPrefixListType,
                tFltrPrefixListName,
                tFltrApplyPathSource,
                tFltrApplyPathIndex,
                tFltrNotifDescription
            }
    STATUS    obsolete
    DESCRIPTION
         "The group of objects supporting management of filter
         notification objects on Alcatel-Lucent SROS series systems."
    ::= { tFilterMIBGroups 46 }

tIPFilterV12v0Group OBJECT-GROUP
    OBJECTS {
                tIPFilterRowStatus,
                tIPFilterScope,
                tIPFilterDescription,
                tIPFilterDefaultAction,
                tIPFilterRadiusInsertPt,
                tIPFilterRadiusInsertSize,
                tIPFilterCreditCntrlInsertPt,
                tIPFilterCreditCntrlInsertSize,
                tIPFilterSubInsertHighWmark,
                tIPFilterSubInsertLowWmark,
                tIpFilterCreditCntrlNbrInsertd,
                tIpFilterRadiusNbrInsertd,
                tIPFilterHostSharedInsertPt,
                tIPFilterHostSharedInsertSize,
                tIpFilterHostSharedNbrInsertd,
                tIPFilterHostSharedHighWmark,
                tIPFilterHostSharedLowWmark,
                tIPFilterNbrHostSharedFltrs,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL,
                tIPFilterParamsSrcIpFullMask,
                tIPFilterParamsDestIpFullMask,
                tIPFilterParamsIngrHitByteCount,
                tIPFilterParamsEgrHitByteCount,
                tFltrGrpInsrtdEntriesFilterType,
                tFltrGrpInsrtdEntriesFilterId,
                tFltrGrpInsrtdEntriesApplication,
                tFltrGrpInsrtdEntriesLocation,
                tFltrGrpInsrtdEntriesResult,
                tFltrGrpInsrtdEntriesFeedback,
                tFltrGrpInsrtdEntriesExecute,
                tIPFilterParamsFwdRtrId,
                tIPFilterParamsSrcRouteOption,
                tIPFilterParamsPortSelector,
                tIPFilterParamsSrcPortList,
                tIPFilterParamsDstPortList,
                tIPFilterParamsExtTbleLstChgd,
                tIPFilterParamsExtLastChanged,
                tIPFilterParamsExtPktLenVal1,
                tIPFilterParamsExtPktLenVal2,
                tIPFilterParamsExtPktLenOper,
                tIPFilterParamsRdirAllwRadOvrd,
                tIPFilterParamsNatPolicyName,
                tIPFilterParamsFwdLsp,
                tIPFilterParamsFwdLspRtrId
            }
    STATUS    current
    DESCRIPTION
        "The group of objects supporting IP Filters
         on Alcatel 7x50 ESS/SR series systems 12.0 release."
    ::= { tFilterMIBGroups 47 }

tIPv6FilterV12v0Group OBJECT-GROUP
    OBJECTS {
        tIPv6FilterRowStatus,
        tIPv6FilterScope,
        tIPv6FilterDescription,
        tIPv6FilterDefaultAction,
        tIPv6FilterRadiusInsertPt,
        tIPv6FilterRadiusInsertSize,
        tIPv6FilterCreditCntrlInsertPt,
        tIPv6FilterCreditCntrlInsertSize,
        tIPv6FilterSubInsertHighWmark,
        tIPv6FilterSubInsertLowWmark,
        tIpv6FilterCreditCntrlNbrInsertd,
        tIpv6FilterRadiusNbrInsertd,
        tIPv6FilterHostSharedInsertPt,
        tIPv6FilterHostSharedInsertSize,
        tIpv6FilterHostSharedNbrInsertd,
        tIPv6FilterHostSharedHighWmark,
        tIPv6FilterHostSharedLowWmark,
        tIPv6FilterNbrHostSharedFltrs,
        tIPv6FilterParamsRowStatus,
        tIPv6FilterParamsLogId,
        tIPv6FilterParamsDescription,
        tIPv6FilterParamsAction,
        tIPv6FilterParamsForwardNH,
        tIPv6FilterParamsForwardNHIndirect,
        tIPv6FilterParamsRemarkDSCP,
        tIPv6FilterParamsRemarkDSCPMask,
        tIPv6FilterParamsRemarkDot1p,
        tIPv6FilterParamsSourceIpAddr,
        tIPv6FilterParamsSourceIpMask,
        tIPv6FilterParamsDestinationIpAddr,
        tIPv6FilterParamsDestinationIpMask,
        tIPv6FilterParamsNextHeader,
        tIPv6FilterParamsSourcePortValue1,
        tIPv6FilterParamsSourcePortValue2,
        tIPv6FilterParamsSourcePortOperator,
        tIPv6FilterParamsDestPortValue1,
        tIPv6FilterParamsDestPortValue2,
        tIPv6FilterParamsDestPortOperator,
        tIPv6FilterParamsDSCP,
        tIPv6FilterParamsTcpSyn,
        tIPv6FilterParamsTcpAck,
        tIPv6FilterParamsIcmpCode,
        tIPv6FilterParamsIcmpType,
        tIPv6FilterParamsCflowdSample,
        tIPv6FilterParamsCflowdIfSample,
        tIPv6FilterParamsForwardNHInterface,
        tIPv6FilterParamsIngressHitCount,
        tIPv6FilterParamsEgressHitCount,
        tIPv6FilterParamsLogInstantiated,
        tIPv6FilterParamsForwardRedPlcy,
        tIPv6FilterParamsActiveDest,
        tIPv6FilterParamsIngrHitByteCount,
        tIPv6FilterParamsEgrHitByteCount,
        tIPv6FilterParamsFwdSvcId,
        tIPv6FilterParamsFwdSapPortId,
        tIPv6FilterParamsFwdSapEncapVal,
        tIPv6FilterParamsFwdSdpBind,
        tIPv6FilterParamsRedirectURL,
        tIPv6FilterParamsSrcIpPrefixList,
        tIPv6FilterParamsDstIpPrefixList,
        tIPv6FilterParamsFragment,
        tIPv6FilterParamsHopByHopOpt,
        tIPv6FilterParamsRoutingType0,
        tIPv6FilterParamsPortSelector,
        tIPv6FilterParamsSrcPortList,
        tIPv6FilterParamsDstPortList,
        tIPv6FilterParamsRdirAllwRadOvrd,
        tIPv6FilterParamsFwdRtrId,
        tIPv6FilterParamsSrcIpFullMask,
        tIPv6FilterParamsDstIpFullMask,
        tIPv6FilterParamsNatPolicyName,
        tIPv6FilterParamsFlowLabel,
        tIPv6FilterParamsFlowLabelMask,
        tIPv6FilterParamsFwdLspRtrId,
        tIPv6FilterParamsFwdLsp
        ,tIPv6FilterParamsExtTbleLstChgd
        ,tIPv6FilterParamsExtLastChanged
        ,tIPv6FilterParamsExtAhExtHdr
        ,tIPv6FilterParamsExtEspExtHdr
        ,tIPv6FilterParamsExtNatType
    }
    STATUS    current
    DESCRIPTION
        "The group of objects supporting management of IPv6 filter objects
         on Alcatel 7x50 ESS/SR series systems 12.0 release."
    ::= { tFilterMIBGroups 48 }
         
tLiFilterV12v0Group OBJECT-GROUP
    OBJECTS {
        tLiReservedBlockRowStatus,
        tLiReservedBlockDescription,
        tLiReservedBlockStart,
        tLiReservedBlockSize,
        tLiReservedBlockLastChanged,
        tLiReservedBlockTableLastChanged,
        tLiReservedBlockFltrRowStatus,
        tLiReservedBlockFltrLastChanged,
        tLiReservedBlockFltrTableLastChg,
        tLiFilterDescription,
        tLiFilterRowStatus,
        tLiFilterLastChanged,
        tLiFilterTableLastChanged,
        tLiFilterAssociationRowStatus,
        tLiFilterAssociationLastChg,
        tLiFilterAssociationTableLastChg,
        tLiMacFilterParamsDescription,
        tLiMacFilterParamsDstMAC,
        tLiMacFilterParamsDstMACMask,
        tLiMacFilterParamsFrameType,
        tLiMacFilterParamsRowStatus,
        tLiMacFilterParamsSrcMAC,
        tLiMacFilterParamsSrcMACMask,
        tLiMacFilterParamsLastChanged,
        tLiMacFilterParamsTableLastChg,
        tLiMacFilterParamsIngrHitCount,
        tLiMacFilterParamsEgrHitCount,
        tLiMacFilterParamsIngrHitBytes,
        tLiMacFilterParamsEgrHitBytes,
        tLiIpFilterParamsTableLastChg,
        tLiIpFilterParamsLastChanged,
        tLiIpFilterParamsRowStatus,
        tLiIpFilterParamsDescription,
        tLiIpFilterParamsSrcIpAddrType,
        tLiIpFilterParamsSrcIpAddr,
        tLiIpFilterParamsSrcIpFullMask,
        tLiIpFilterParamsDstIpAddrType,
        tLiIpFilterParamsDstIpAddr,
        tLiIpFilterParamsDstIpFullMask,
        tLiIpFilterParamsProtocolNextHdr,
        tLiIpFilterParamsSrcPortValue1,
        tLiIpFilterParamsSrcPortValue2,
        tLiIpFilterParamsSrcPortOper,
        tLiIpFilterParamsDstPortValue1,
        tLiIpFilterParamsDstPortValue2,
        tLiIpFilterParamsDstPortOper,
        tLiIpFltrParamsInfIngrHitCount,
        tLiIpFltrParamsInfEgrHitCount,
        tLiIpFltrParamsInfIngrHitBytes,
        tLiIpFltrParamsInfEgrHitBytes
    }
    STATUS    current
    DESCRIPTION
        "The group of objects supporting management of LI filter entries
         on Alcatel-Lucent SROS series systems 12.0 release."
    ::= { tFilterMIBGroups 49 }
    
tFilterEmbeddedInsertV12v0Group OBJECT-GROUP
    OBJECTS {
        tFilterEmbedOpenflowRowStatus    ,
        tFilterEmbedOpenflowTableLstChg  ,
        tFilterEmbedOpenflowOperState    ,
        tFilterEmbedOpenflowAdminState   ,
        tFltrEmbedOfInfoEntryCnt         ,
        tFltrEmbedOfInfoEntryCntInsrtd   ,
        tFltrEmbedOfEntryInsrtEntryId    ,
        tFltrEmbedOfEntryInsrtEntryState  
    }
    STATUS current
    DESCRIPTION
        "The group of new objects supporting the creation of embedded filters
         for Alcatel-Lucent SROS systems 12.0 release."
    ::= { tFilterMIBGroups 50 }
         
tFilterNotificationsV12v0Group NOTIFICATION-GROUP
    NOTIFICATIONS {
        tFilterEmbedOpenflowOperStateChg,
        tFilterTmsEvent
    }
    STATUS current
    DESCRIPTION
        "The group of notifications supporting management of
         filter notifications on Alcatel-Lucent SROS series systems."
    ::= { tFilterMIBGroups 51 }

tFilterNotificationObjV12v0Group OBJECT-GROUP
    OBJECTS {
                tFilterPBRDropReason,
                tFilterParmRow,
                tFilterAlarmDescription,
                tFilterId,
                tFilterType,
                tFilterSubInsSpaceOwner,
                tFilterThresholdReached,
                tFltrFlowSpecProblem,
                tFltrFlowSpecProblemDescription,
                tFltrFLowSpecNLRI,
                tFltrFlowSpecVrtrId,
                tFltrPrefixListType,
                tFltrPrefixListName,
                tFltrApplyPathSource,
                tFltrApplyPathIndex,
                tFltrNotifDescription,
                tFltrMdaId
            }
    STATUS    current
    DESCRIPTION
         "The group of objects supporting management of filter
         notification objects on Alcatel-Lucent SROS series systems."
    ::= { tFilterMIBGroups 53 }

END
