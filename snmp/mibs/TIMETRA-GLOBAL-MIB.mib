TIMETRA-GLOBAL-MIB DEFINITIONS ::= BEGIN

IMPORTS
    MODULE-IDENTITY, OBJECT-IDENTITY,
    enterprises                             FROM SNMPv2-SMI;

timetraGlobalMIBModule  MODULE-IDENTITY
        LAST-UPDATED "201401010000Z"
        ORGANIZATION "Alcatel-Lucent"
        CONTACT-INFO
            "Alcatel-Lucent SROS Support
             Web: http://support.alcatel-lucent.com"
    DESCRIPTION
        "This  document  is the SNMP MIB module for central registration
        of object identifiers defined under the Alcatel-Lucent 'timetra' branch
        for the Alcatel-Lucent SROS series SNMP MIBs.

        Copyright  2003-2014  Alcatel-Lucent. All rights reserved.
        Reproduction of this document is authorized on the condition that
        the foregoing copyright notice is included.

        This SNMP MIB module (Specification) embodies Alcatel-Lucent's
        proprietary intellectual property.  Alcatel-Lucent retains
        all title and ownership in the Specification, including any
        revisions.

        Alcatel-Lucent grants all interested parties a non-exclusive
        license to use and distribute an unmodified copy of this
        Specification in connection with management of Alcatel-Lucent
        products, and without fee, provided this copyright notice and
        license appear on all copies.

        This Specification is supplied 'as is', and Alcatel-Lucent
        makes no warranty, either express or implied, as to the use,
        operation, condition, or performance of the Specification."
--
--  Revision History
--
        REVISION        "201401010000Z"
        DESCRIPTION     "Rev 12.0                1 Jan 2014 00:00
                         12.0 release of the TIMETRA-GLOBAL-MIB."

        REVISION        "201208010000Z"
        DESCRIPTION     "Rev 11.0                1 Aug 2012 00:00
                         11.0 release of the TIMETRA-GLOBAL-MIB."

        REVISION        "201102010000Z"
        DESCRIPTION     "Rev 9.0                1 Feb 2011 00:00
                         9.0 release of the TIMETRA-GLOBAL-MIB."

        REVISION        "201002280000Z"
        DESCRIPTION     "Rev 8.0                28 Feb 2010 00:00
                         8.0 release of the TIMETRA-GLOBAL-MIB."

        REVISION        "200902280000Z"
        DESCRIPTION     "Rev 7.0                28 Feb 2009 00:00
                         7.0 release of the TIMETRA-GLOBAL-MIB."

        REVISION        "200902010000Z"
        DESCRIPTION     "Rev 7.0                01 Feb 2009 00:00
                         7.0 release of the TIMETRA-GLOBAL-MIB."

        REVISION        "200807010000Z"
        DESCRIPTION     "Rev 6.1                01 Jul 2008 00:00
                         6.1 release of the TIMETRA-GLOBAL-MIB."

        REVISION        "200801010000Z"
        DESCRIPTION     "Rev 6.0                01 Jan 2008 00:00
                         6.0 release of the TIMETRA-GLOBAL-MIB."

        REVISION        "200701010000Z"
        DESCRIPTION     "Rev 5.0                01 Jan 2007 00:00
                         5.0 release of the TIMETRA-GLOBAL-MIB."

        REVISION        "200508310000Z"   
        DESCRIPTION     "Rev 3.0                31 Aug 2005 00:00
                         3.0 release of the TIMETRA-GLOBAL-MIB."

        REVISION        "200501240000Z"   
        DESCRIPTION     "Rev 2.1                24 Jan 2005 00:00
                         2.1 release of the TIMETRA-GLOBAL-MIB."

        REVISION        "200401150000Z"
        DESCRIPTION     "Rev 2.0                15 Jan 2004 00:00
                         2.0 release of the TIMETRA-GLOBAL-MIB."

        REVISION        "200301200000Z"
        DESCRIPTION     "Rev 1.0                20 Jan 2003 00:00
                This is the 1.0 release of the TIMETRA-GLOBAL-MIB."

        REVISION        "200008140000Z"   
        DESCRIPTION     "Rev 0.1                14 Aug 2000 00:00
                This is the initial version of the TIMETRA-GLOBAL-MIB."
        ::= { timetraModules 1 }

--
-- ----------------------------------------------------------------------------
-- timetra
-- ----------------------------------------------------------------------------
--  The Private Enterprise Number 6527 was assigned to TiMetra Inc.,
--  previously known as Panthera Networks, by the IANA on July 14, 2000.
--
--  TiMetra, Inc. was acquired by Alcatel on July 18, 2003 and has
--  had the timetra enterprise number, 6527, registered to Alcatel.
--
timetra OBJECT IDENTIFIER ::= { enterprises 6527 }

--
-- ----------------------------------------------------------------------------
-- timetra 1  : timetra registry
-- ----------------------------------------------------------------------------
--  Sub-tree for registrations
timetraReg      OBJECT IDENTIFIER ::= { timetra 1 }

--
-- ----------------------------------------------
-- timetra-reg 1  : Modules
-- ----------------------------------------------
--  Note:
--    The timetraESSMIBModules and alcatelCommonMIBModules have become
--    deprecated. Henceforward, all new MIB modules will be placed
--    under timetraModules. 
--
    timetraModules  OBJECT IDENTIFIER ::= { timetraReg 1 }
--      timetraGlobalMIBModule           OBJECT IDENTIFIER ::= { timetraModules 1 }
--      timetraTCMIBModule               OBJECT IDENTIFIER ::= { timetraModules 2 }
        timetraSRMIBModules              OBJECT IDENTIFIER ::= { timetraModules 3 }
--          timetraSysMIBModule              OBJECT IDENTIFIER ::= { timetraSRMIBModules 1 }
--          tmnxChassisMIBModule             OBJECT IDENTIFIER ::= { timetraSRMIBModules 2 }
--          timetraVRtrMIBModule             OBJECT IDENTIFIER ::= { timetraSRMIBModules 3 }
--          timetraServicesMIBModule         OBJECT IDENTIFIER ::= { timetraSRMIBModules 4 }
--          timetraOspfMIBModule             OBJECT IDENTIFIER ::= { timetraSRMIBModules 5 }
--          timetraMplsMIBModule             OBJECT IDENTIFIER ::= { timetraSRMIBModules 6 }
--          timetraRsvpMIBModule             OBJECT IDENTIFIER ::= { timetraSRMIBModules 7 }
--          timetraLdpMIBModule              OBJECT IDENTIFIER ::= { timetraSRMIBModules 8 }
--          timetraRipMIBModule              OBJECT IDENTIFIER ::= { timetraSRMIBModules 9 }
--          timetraIsisMIBModule             OBJECT IDENTIFIER ::= { timetraSRMIBModules 10 }
--          timetraOamTestMIBModule          OBJECT IDENTIFIER ::= { timetraSRMIBModules 11 }
--          timetraLogMIBModule              OBJECT IDENTIFIER ::= { timetraSRMIBModules 12 }
--          timetraClearMIBModule            OBJECT IDENTIFIER ::= { timetraSRMIBModules 13 }
--          timetraBgpMIBModule              OBJECT IDENTIFIER ::= { timetraSRMIBModules 14 }
--          timetraLagMIBModule              OBJECT IDENTIFIER ::= { timetraSRMIBModules 15 }
--          timetraQosMIBModule              OBJECT IDENTIFIER ::= { timetraSRMIBModules 16 }
--          timetraRoutePolicyMIBModule      OBJECT IDENTIFIER ::= { timetraSRMIBModules 17 }
--          timetraMirrorMIBModule           OBJECT IDENTIFIER ::= { timetraSRMIBModules 18 }
--          timetraCflowdMIBModule           OBJECT IDENTIFIER ::= { timetraSRMIBModules 19 }
--          timetraVrrpMIBModule             OBJECT IDENTIFIER ::= { timetraSRMIBModules 20 }
--          timetraFilterMIBModule           OBJECT IDENTIFIER ::= { timetraSRMIBModules 21 }
--          timetraSecurityMIBModule         OBJECT IDENTIFIER ::= { timetraSRMIBModules 22 }
--          timetraIgmpMIBModule             OBJECT IDENTIFIER ::= { timetraSRMIBModules 23 )
--          timetraPimMIBModule              OBJECT IDENTIFIER ::= { timetraSRMIBModules 24 }
--          tmnxPortMIBModule                OBJECT IDENTIFIER ::= { timetraSRMIBModules 25 }
--          tmnxPppMIBModule                 OBJECT IDENTIFIER ::= { timetraSRMIBModules 26 }
--          timetraATMMIBModule              OBJECT IDENTIFIER ::= { timetraSRMIBModules 27 }
--          timetraAgentCapabilityModule     OBJECT IDENTIFIER ::= { timetraSRMIBModules 28 }
--          timetraAPSMIBModule              OBJECT IDENTIFIER ::= { timetraSRMIBModules 29 }
--          timetraGmplsMIBModule            OBJECT IDENTIFIER ::= { timetraSRMIBModules 30 }
--          timetraGmplsRsvpMIBModule        OBJECT IDENTIFIER ::= { timetraSRMIBModules 31 }
--          timetraGmplsLmpMIBModule         OBJECT IDENTIFIER ::= { timetraSRMIBModules 32 }
--          tmnxSubMgmtMIBModule             OBJECT IDENTIFIER ::= { timetraSRMIBModules 33 }
--          timetraNgBgpMIBModule            OBJECT IDENTIFIER ::= { timetraSRMIBModules 34 }
--          not used. (formerly used by timetraOspfv3MIBModule)
--          timetraOspfNgMIBModule           OBJECT IDENTIFIER ::= { timetraSRMIBModules 36 }
--          tmnxSchedulerMIBModule           OBJECT IDENTIFIER ::= { timetraSRMIBModules 37 }
--          timetraNtpMIBModule              OBJECT IDENTIFIER ::= { timetraSRMIBModules 38 }
--          tmnxGsmpMIBModule                OBJECT IDENTIFIER ::= { timetraSRMIBModules 39 }
--          timetraMcRedundancyMIBModule     OBJECT IDENTIFIER ::= { timetraSRMIBModules 40 }
--          timetraMcastCacMIBModule         OBJECT IDENTIFIER ::= { timetraSRMIBModules 41 }
--          timetraDOT3OAMMIBModule          OBJECT IDENTIFIER ::= { timetraSRMIBModules 42 }
--          timetraMsdpMIBModule             OBJECT IDENTIFIER ::= { timetraSRMIBModules 43 }
--          not used. (formerly used by tmnxBsxMIBModule)
--          timetraMldSnoopingMIBModule      OBJECT IDENTIFIER ::= { timetraSRMIBModules 45 }
--          timetraMldMIBModule              OBJECT IDENTIFIER ::= { timetraSRMIBModules 46 }
--          timetraDhcpServerMIBModule       OBJECT IDENTIFIER ::= { timetraSRMIBModules 47 }
--          timetraIPsecMIBModule            OBJECT IDENTIFIER ::= { timetraSRMIBModules 48 }
--          timetraPppoeMIBModule            OBJECT IDENTIFIER ::= { timetraSRMIBModules 49 }
--          timetraPimNgMIBModule            OBJECT IDENTIFIER ::= { timetraSRMIBModules 50 }
--          timetraLocalUserDbMIBModule      OBJECT IDENTIFIER ::= { timetraSRMIBModules 51 }
--          timetraIEEE8021CfmMIBModule      OBJECT IDENTIFIER ::= { timetraSRMIBModules 52 }
--          timetraPimSnoopingMIBModule      OBJECT IDENTIFIER ::= { timetraSRMIBModules 53 }
--          timetraMcastPathMgmtMIBModule    OBJECT IDENTIFIER ::= { timetraSRMIBModules 54 }
--          timetraSvcSapMIBModule           OBJECT IDENTIFIER ::= { timetraSRMIBModules 55 }
--          timetraServicesSdpMIBModule      OBJECT IDENTIFIER ::= { timetraSRMIBModules 56 }
--          timetraVrrpV3MibModule           OBJECT IDENTIFIER ::= { timetraSRMIBModules 57 }
--          timetraDiameterMIBModule         OBJECT IDENTIFIER ::= { timetraSRMIBModules 58 }
--          timetraLLDPMIBModule             OBJECT IDENTIFIER ::= { timetraSRMIBModules 59 }
--          timetraL2tpMIBModule             OBJECT IDENTIFIER ::= { timetraSRMIBModules 60 }
--          timetraVideoMIBModule            OBJECT IDENTIFIER ::= { timetraSRMIBModules 61 }
--          timetraOtuMIBModule              OBJECT IDENTIFIER ::= { timetraSRMIBModules 62 }
--          tmnxBsxNgMIBModule               OBJECT IDENTIFIER ::= { timetraSRMIBModules 63 }
--          timetraEthTunnelMIBModule        OBJECT IDENTIFIER ::= { timetraSRMIBModules 64 }
--          timetraNatMIBModule              OBJECT IDENTIFIER ::= { timetraSRMIBModules 65 }
--          timetraMobServingMIBModule       OBJECT IDENTIFIER ::= { timetraSRMIBModules 66 }
--          timetraMobProfileMIBModule       OBJECT IDENTIFIER ::= { timetraSRMIBModules 67 }
--          timetraElmiMIBModule             OBJECT IDENTIFIER ::= { timetraSRMIBModules 68 }
--          timetraIfGroupMIBModule          OBJECT IDENTIFIER ::= { timetraSRMIBModules 69 }
--          timetraMobGatewayMIBModule       OBJECT IDENTIFIER ::= { timetraSRMIBModules 70 }
--          timetraMobPdnMIBModule           OBJECT IDENTIFIER ::= { timetraSRMIBModules 71 }
--          timetraEthRingMIBModule          OBJECT IDENTIFIER ::= { timetraSRMIBModules 72 }
--          timetraIPsecStaticSAMIBModule    OBJECT IDENTIFIER ::= { timetraSRMIBModules 73 }
--          timetraPTPMIBModule              OBJECT IDENTIFIER ::= { timetraSRMIBModules 74 }
--          timetraConnProfMIBModule         OBJECT IDENTIFIER ::= { timetraSRMIBModules 75 }
--          timetraTwampMIBModule            OBJECT IDENTIFIER ::= { timetraSRMIBModules 76 }
--          timetraAlarmMIBModule            OBJECT IDENTIFIER ::= { timetraSRMIBModules 77 }
--          timetraIpfixMIBModule            OBJECT IDENTIFIER ::= { timetraSRMIBModules 78 }
--          timetraRadiusMIBModule           OBJECT IDENTIFIER ::= { timetraSRMIBModules 79 }
--          timetraWppMIBModule              OBJECT IDENTIFIER ::= { timetraSRMIBModules 80 }
--          timetraWlanGwMIBModule           OBJECT IDENTIFIER ::= { timetraSRMIBModules 81 }
--          timetraDaMIBModule               OBJECT IDENTIFIER ::= { timetraSRMIBModules 82 }
--          timetraMplsTpModule              OBJECT IDENTIFIER ::= { timetraSRMIBModules 83 }
--          timetraDynSrvModule              OBJECT IDENTIFIER ::= { timetraSRMIBModules 84 }
--          timetraBfdMIBModule              OBJECT IDENTIFIER ::= { timetraSRMIBModules 85 }
--          timetraDCvSwitchMIBModule        OBJECT IDENTIFIER ::= { timetraSRMIBModules 86 }
--          timetraPythonMIBModule           OBJECT IDENTIFIER ::= { timetraSRMIBModules 87 }
--          timetraIsisNgMIBModule           OBJECT IDENTIFIER ::= { timetraSRMIBModules 88 }
--          timetraRipNgMIBModule            OBJECT IDENTIFIER ::= { timetraSRMIBModules 89 }
--          timetraRouteNextHopTemplateMIBModule OBJECT IDENTIFIER ::= { timetraSRMIBModules 90 }
--          timetraLdpNgMIBModule            OBJECT IDENTIFIER ::= { timetraSRMIBModules 91 }
--          timetraOamPmMibModule            OBJECT IDENTIFIER ::= { timetraSRMIBModules 92 }
--          timetraOpenFlowMIBModule         OBJECT IDENTIFIER ::= { timetraSRMIBModules 93 }
--          timetraChassisInterconMIBModule  OBJECT IDENTIFIER ::= { timetraSRMIBModules 94 },
--          timetraSflowMIBModule            OBJECT IDENTIFIER ::= { timetraSRMIBModules 95 },
--         timetraRpkiModule    OBJECT IDENTIFIER ::= { timetraSRMIBModules 96 },
--
--
--      Capability MIB modules
          timetraCapabilityModule          OBJECT IDENTIFIER ::= { timetraModules 4 }

            timetra7750CapModule             OBJECT IDENTIFIER ::= { timetraCapabilityModule 1 }
--              timetra7750V3v0CapModule         OBJECT IDENTIFIER ::= { timetra7750CapModule 1 }
--              timetra7750V4v0CapModule         OBJECT IDENTIFIER ::= { timetra7750CapModule 2 }
--              timetra7750V5v0CapModule         OBJECT IDENTIFIER ::= { timetra7750CapModule 3 }
--              timetra7750V6v0CapModule         OBJECT IDENTIFIER ::= { timetra7750CapModule 4 }
--              timetra7750V6v1CapModule         OBJECT IDENTIFIER ::= { timetra7750CapModule 5 }
--              timetra7750V7v0CapModule         OBJECT IDENTIFIER ::= { timetra7750CapModule 6 }
--              timetra7750V8v0CapModule         OBJECT IDENTIFIER ::= { timetra7750CapModule 7 }

            timetra7450CapModule             OBJECT IDENTIFIER ::= { timetraCapabilityModule 2 }
--              timetra7450V3v0CapModule         OBJECT IDENTIFIER ::= { timetra7450CapModule 1 }
--              timetra7450V4v0CapModule         OBJECT IDENTIFIER ::= { timetra7450CapModule 2 }
--              timetra7450V5v0CapModule         OBJECT IDENTIFIER ::= { timetra7450CapModule 3 }
--              timetra7450V6v0CapModule         OBJECT IDENTIFIER ::= { timetra7450CapModule 4 }
--              timetra7450V6v1CapModule         OBJECT IDENTIFIER ::= { timetra7450CapModule 5 }
--              timetra7450V7v0CapModule         OBJECT IDENTIFIER ::= { timetra7450CapModule 6 }
--              timetra7450V8v0CapModule         OBJECT IDENTIFIER ::= { timetra7450CapModule 7 }

            timetra7710CapModule             OBJECT IDENTIFIER ::= { timetraCapabilityModule 3 }
--              timetra7710V3v0CapModule         OBJECT IDENTIFIER ::= { timetra7710CapModule 1 }
--              timetra7710V4v0CapModule         OBJECT IDENTIFIER ::= { timetra7710CapModule 2 }
--              timetra7710V6v0CapModule         OBJECT IDENTIFIER ::= { timetra7710CapModule 3 }
--              timetra7710V6v1CapModule         OBJECT IDENTIFIER ::= { timetra7710CapModule 4 }
--              timetra7710V7v0CapModule         OBJECT IDENTIFIER ::= { timetra7710CapModule 5 }
--              timetra7710V8v0CapModule         OBJECT IDENTIFIER ::= { timetra7710CapModule 6 }

            timetra7750MGCapModule           OBJECT IDENTIFIER ::= { timetraCapabilityModule 4 }
--              timetra7750MGV1v0CapModule       OBJECT IDENTIFIER ::= { timetra7750MGCapModule 1 }
--              timetra7750MGV2v0CapModule       OBJECT IDENTIFIER ::= { timetra7750MGCapModule 2 }
--              timetra7750MGV3v0CapModule       OBJECT IDENTIFIER ::= { timetra7750MGCapModule 3 }
--              timetra7750MGV4v0CapModule       OBJECT IDENTIFIER ::= { timetra7750MGCapModule 4 }
--              timetra7750MGV5v0CapModule       OBJECT IDENTIFIER ::= { timetra7750MGCapModule 5 }
--              timetra7750MGV6v0CapModule       OBJECT IDENTIFIER ::= { timetra7750MGCapModule 6 }

            timetraSROSCapModule             OBJECT IDENTIFIER ::= { timetraCapabilityModule 5 }
--              timetraSROSV8v0CapModule         OBJECT IDENTIFIER ::= { timetraSROSCapModule 6 }
--              timetraSROSV9v0CapModule         OBJECT IDENTIFIER ::= { timetraSROSCapModule 7 }

            timetraMGCapModule           OBJECT IDENTIFIER ::= { timetraCapabilityModule 7 }
--              timetraMGV7v0CapModule       OBJECT IDENTIFIER ::= { timetra7750MGCapModule 1 }

        alcatelCommonMIBModules          OBJECT IDENTIFIER ::= { timetraModules 5 }
--          alcatelGlobalMIBModule           OBJECT IDENTIFIER ::= { alcatelCommonMIBModules 1 }

--
-- ----------------------------------------------
-- timetra-reg 3  : 7750 SR hardware products
-- ----------------------------------------------
--  Sub-trees for registration of Alcatel-Lucent SROS series hardware products
--
    timetraServiceRouters   OBJECT IDENTIFIER ::= { timetraReg 3 }
        tmnxModelSR1Reg         OBJECT-IDENTITY
            STATUS  current
            DESCRIPTION
                "This objectId is to be used as the mib-2 sysObjectID to
                identify the Alcatel-Lucent 7750 SR-1 device."
        ::= { timetraServiceRouters 1 }

        tmnxModelSR4Reg         OBJECT-IDENTITY
            STATUS  current
            DESCRIPTION
                "This objectId is to be used as the mib-2 sysObjectID to
                 identify the Alcatel-Lucent 7750 SR-4 device."
        ::= { timetraServiceRouters 2 }

        tmnxModelSR12Reg         OBJECT-IDENTITY
            STATUS  current
            DESCRIPTION
                "This objectId is to be used as the mib-2 sysObjectID to
                 identify the Alcatel-Lucent 7750 SR-12 device."
        ::= { timetraServiceRouters 3 }

        tmnxModelSR7Reg         OBJECT-IDENTITY
            STATUS  current
            DESCRIPTION
                "This objectId is to be used as the mib-2 sysObjectID to
                 identify the Alcatel-Lucent 7750 SR-7 device."
        ::= { timetraServiceRouters 4 }

        tmnxModelSR6Reg         OBJECT-IDENTITY
            STATUS  current
            DESCRIPTION
                "This objectId is to be used as the mib-2 sysObjectID to
                 identify the Alcatel-Lucent 7750 SR-6 device."
        ::= { timetraServiceRouters 5 }

        tmnxModelSRc12Reg       OBJECT-IDENTITY
            STATUS  current
            DESCRIPTION
                "This objectId is to be used as the mib-2 sysObjectID to
                 identify the Alcatel-Lucent 7750 SR-c12 device."
        ::= { timetraServiceRouters 6 }

        tmnxModelSRc4Reg        OBJECT-IDENTITY
            STATUS  current
            DESCRIPTION
                "This objectId is to be used as the mib-2 sysObjectID to
                 identify the Alcatel-Lucent 7750 SR-c4 device."
        ::= { timetraServiceRouters 7 }

        tmnxModelSR12EReg       OBJECT-IDENTITY
            STATUS  current
            DESCRIPTION
                "This objectID is to be used as the mib-2 sysObjectID to
                 identify the Alcatel-Lucent 7750 SR-12E device."
        ::= { timetraServiceRouters 8 }

        tmnxModelSRa4Reg        OBJECT-IDENTITY
            STATUS  current
            DESCRIPTION
                "This objectId is to be used as the mib-2 sysObjectID to
                 identify the Alcatel-Lucent 7750 SR-a4 device."
        ::= { timetraServiceRouters 9 }

        tmnxModelSRa8Reg        OBJECT-IDENTITY
            STATUS  current
            DESCRIPTION
                "This objectId is to be used as the mib-2 sysObjectID to
                 identify the Alcatel-Lucent 7750 SR-a8 device."
        ::= { timetraServiceRouters 10 }

--
-- ----------------------------------------------
-- timetra-reg 6  : 7450 ESS hardware products
-- ----------------------------------------------
--  Sub-tree for registration of Alcatel-Lucent 7450 ESS series hardware
--  products
--
timetraServiceSwitches    OBJECT IDENTIFIER ::= { timetraReg 6 }
        tmnxModelESS1Reg         OBJECT-IDENTITY
            STATUS  current
            DESCRIPTION
                "This objectId is to be used as the mib-2 sysObjectID to
                 identify the Alcatel-Lucent 7450 ESS-1 device."
        ::= { timetraServiceSwitches 1 }

        tmnxModelESS4Reg         OBJECT-IDENTITY
            STATUS  current
            DESCRIPTION
                "This objectId is to be used as the mib-2 sysObjectID to
                 identify the Alcatel-Lucent 7450 ESS-4 device."
        ::= { timetraServiceSwitches 2 }

        tmnxModelESS7Reg         OBJECT-IDENTITY
            STATUS  current
            DESCRIPTION
                "This objectId is to be used as the mib-2 sysObjectID to
                 identify the Alcatel-Lucent 7450 ESS-7 device."
        ::= { timetraServiceSwitches 3 }

         tmnxModelESS12Reg        OBJECT-IDENTITY
            STATUS  current
            DESCRIPTION
                "This objectId is to be used as the mib-2 sysObjectID to
                 identify the Alcatel-Lucent 7450 ESS-12 device."
        ::= { timetraServiceSwitches 4 }

         tmnxModelESS6Reg        OBJECT-IDENTITY
            STATUS  current
            DESCRIPTION
                "This objectId is to be used as the mib-2 sysObjectID to
                 identify the Alcatel-Lucent 7450 ESS-6 device."
        ::= { timetraServiceSwitches 5 }

         tmnxModelESS6vReg       OBJECT-IDENTITY
            STATUS  current
            DESCRIPTION
                "This objectId is to be used as the mib-2 sysObjectID to
                 identify the Alcatel-Lucent 7450 ESS-6V device."
        ::= { timetraServiceSwitches 6 }

--
-- ----------------------------------------------
-- timetra-reg 9  : 7710 SR hardware products
-- ----------------------------------------------
--  Sub-trees for registration of Alcatel-Lucent 7710 SR series hardware
--  products
--
    alcatel7710ServiceRouters   OBJECT IDENTIFIER ::= { timetraReg 9 }
        tmnxModel7710SRc12Reg    OBJECT-IDENTITY
            STATUS  current
            DESCRIPTION
                "This objectId is to be used as the mib-2 sysObjectID to
                 identify the Alcatel-Lucent 7710 SR-c12 (12 Compact MDA slots)
                 device."
        ::= { alcatel7710ServiceRouters 1 }

        tmnxModel7710SRc4Reg    OBJECT-IDENTITY
            STATUS  current
            DESCRIPTION
                "This objectId is to be used as the mib-2 sysObjectID to
                 identify the Alcatel-Lucent 7710 SR-c4 (4 Compact MDA slots)
                 device."
        ::= { alcatel7710ServiceRouters 2 }

--
-- ----------------------------------------------
-- timetra-reg 12  : 7750-MG SR hardware products
-- ----------------------------------------------
--  Sub-trees for registration of Alcatel-Lucent 7750-MG SR series hardware
--  products
--
    alcatel7750MobileGateways   OBJECT IDENTIFIER ::= { timetraReg 12 }

        tmnxModel7750MGSR7Reg         OBJECT-IDENTITY
            STATUS  current
            DESCRIPTION
                "This objectId is to be used as the mib-2 sysObjectID to
                 identify the Alcatel-Lucent 7750-MG SR-7 device."
        ::= { alcatel7750MobileGateways 1 }

        tmnxModel7750MGSR12Reg         OBJECT-IDENTITY
            STATUS  current
            DESCRIPTION
                "This objectId is to be used as the mib-2 sysObjectID to
                 identify the Alcatel-Lucent 7750-MG SR-12 device."
        ::= { alcatel7750MobileGateways 2 }

--
-- ----------------------------------------------
-- timetra-reg 15  : 7950 XRS hardware products
-- ----------------------------------------------
--  Sub-trees for registration of Alcatel-Lucent 7950 XRS series hardware
--  products
--
    alcatel7950ExtRoutingSystems OBJECT IDENTIFIER ::= { timetraReg 15 }

        tmnxModel7950XRS20Reg         OBJECT-IDENTITY
            STATUS  current
            DESCRIPTION
                "This objectId is to be used as the mib-2 sysObjectID to
                 identify the Alcatel-Lucent 7950 XRS-20 device."
        ::= { alcatel7950ExtRoutingSystems 1 }

        tmnxModel7950XRS16Reg         OBJECT-IDENTITY
            STATUS  current
            DESCRIPTION
                "This objectId is to be used as the mib-2 sysObjectID to
                 identify the Alcatel-Lucent 7950 XRS-16 device."
        ::= { alcatel7950ExtRoutingSystems 2 }



--
-- ----------------------------------------------------------------------------
-- timetra 2  : tree for company-wide common objects
-- ----------------------------------------------------------------------------
--      Sub-tree for company-wide objects and events
--
timetraGeneric  OBJECT IDENTIFIER ::= { timetra 2 }

--
-- ----------------------------------------------------------------------------
-- timetra 3  : product specific objects
-- ----------------------------------------------------------------------------
-- Sub-tree for product-specific objects and events.
-- Note: 
--   3 products were originally defined:
--   - SR     : objects for the 7750
--   - ESS    : objects for the 7450
--   - Common : objects common to both products
--   Both the ESS and Common branch are now deprecated.
--   All MIB modules are placed under tmnxSRMIB node.
--
timetraProducts         OBJECT IDENTIFIER ::= { timetra 3 }

--
-- ----------------------------------------------
-- timetra-products 1  : 7750 objects
-- ----------------------------------------------
--  Sub-tree for Service Router MIBs
    tmnxSRMIB           OBJECT IDENTIFIER ::= { timetraProducts 1 }
--      Sub-tree for Service Router conformace
        tmnxSRConfs          OBJECT IDENTIFIER ::= { tmnxSRMIB 1 }
--      Sub-tree for Service Router Objects
        tmnxSRObjs           OBJECT IDENTIFIER ::= { tmnxSRMIB 2 }
--      Sub-tree for Service Router Notifications (events)
        tmnxSRNotifyPrefix   OBJECT IDENTIFIER ::= { tmnxSRMIB 3 }

--
-- ----------------------------------------------
-- timetra-products 2  : 7450 objects
-- ----------------------------------------------
--  Sub-tree for Service switch Router MIBs
    tmnxESSMIB          OBJECT IDENTIFIER ::= { timetraProducts 2 }
--      Sub-tree for Service Switch conformace
        tmnxESSConfs         OBJECT IDENTIFIER ::= { tmnxESSMIB 1 }
--      Sub-tree for Service Switch Objects
        tmnxESSObjs          OBJECT IDENTIFIER ::= { tmnxESSMIB 2 }
--      Sub-tree for Service Switch Notifications (events)
        tmnxESSNotifyPrefix  OBJECT IDENTIFIER ::= { tmnxESSMIB 3 }

--
-- ----------------------------------------------
-- timetra-products 3  : Alcatel-Lucent objects
-- ----------------------------------------------
--  Sub-tree for Common MIBs
    alcatelCommonMIB    OBJECT IDENTIFIER ::= { timetraProducts 3 }
--      Sub-tree for Service Switch conformace
        alcatelConformance   OBJECT IDENTIFIER ::= { alcatelCommonMIB 1 }
--      Sub-tree for Service Switch Objects
        alcatelObjects       OBJECT IDENTIFIER ::= { alcatelCommonMIB 2 }
--      Sub-tree for Service Switch Notifications (events)
        alcatelNotifyPrefix  OBJECT IDENTIFIER ::= { alcatelCommonMIB 3 }

--
-- ----------------------------------------------
-- timetra-products 4  : 7750MG objects
-- ----------------------------------------------
--  Sub-tree for Mobile Gateway MIBs
    tmnxMGMIB           OBJECT IDENTIFIER ::= { timetraProducts 4 }
--      Sub-tree for Mobile Gateway conformace
        tmnxMGConfs          OBJECT IDENTIFIER ::= { tmnxMGMIB 1 }
--      Sub-tree for Mobile Gateway Objects
        tmnxMGObjs           OBJECT IDENTIFIER ::= { tmnxMGMIB 2 }
--      Sub-tree for Mobile Gateway Notifications (events)
        tmnxMGNotifyPrefix   OBJECT IDENTIFIER ::= { tmnxMGMIB 3 }

--
-- ----------------------------------------------------------------------------
-- timetra 4  : Agent Capabilities
-- This capability branch is now obsolete and replaced with the { timetra 5 }
-- product capabilities branch.
-- ----------------------------------------------------------------------------
--
tmnxAgentCapability        OBJECT IDENTIFIER ::= { timetra 4 }
    tmnx7750AgentCapability        OBJECT IDENTIFIER ::= { tmnxAgentCapability 1 }
    tmnx7450AgentCapability        OBJECT IDENTIFIER ::= { tmnxAgentCapability 2 }
    tmnx7710AgentCapability        OBJECT IDENTIFIER ::= { tmnxAgentCapability 3 }

--
-- ----------------------------------------------------------------------------
-- timetra 5  : Product Capabilities
-- ----------------------------------------------------------------------------
--
tmnxProductCapability      OBJECT IDENTIFIER ::= { timetra 5 }
    tmnx7750Capability         OBJECT IDENTIFIER ::= { tmnxProductCapability 1 }
        tmnx7750V3v0               OBJECT IDENTIFIER ::= { tmnx7750Capability 1 }
        tmnx7750V4v0               OBJECT IDENTIFIER ::= { tmnx7750Capability 2 }
        tmnx7750V5v0               OBJECT IDENTIFIER ::= { tmnx7750Capability 3 }
        tmnx7750V6v0               OBJECT IDENTIFIER ::= { tmnx7750Capability 4 }
        tmnx7750V6v1               OBJECT IDENTIFIER ::= { tmnx7750Capability 5 }
        tmnx7750V7v0               OBJECT IDENTIFIER ::= { tmnx7750Capability 6 }
        tmnx7750V8v0               OBJECT IDENTIFIER ::= { tmnx7750Capability 7 }
    tmnx7450Capability         OBJECT IDENTIFIER ::= { tmnxProductCapability 2 }
        tmnx7450V3v0               OBJECT IDENTIFIER ::= { tmnx7450Capability 1 }
        tmnx7450V4v0               OBJECT IDENTIFIER ::= { tmnx7450Capability 2 }
        tmnx7450V5v0               OBJECT IDENTIFIER ::= { tmnx7450Capability 3 }
        tmnx7450V6v0               OBJECT IDENTIFIER ::= { tmnx7450Capability 4 }
        tmnx7450V6v1               OBJECT IDENTIFIER ::= { tmnx7450Capability 5 }
        tmnx7450V7v0               OBJECT IDENTIFIER ::= { tmnx7450Capability 6 }
        tmnx7450V8v0               OBJECT IDENTIFIER ::= { tmnx7450Capability 7 }
    tmnx7710Capability         OBJECT IDENTIFIER ::= { tmnxProductCapability 3 }
        tmnx7710V3v0               OBJECT IDENTIFIER ::= { tmnx7710Capability 1 }
        tmnx7710V4v0               OBJECT IDENTIFIER ::= { tmnx7710Capability 2 }
        tmnx7710V5v0               OBJECT IDENTIFIER ::= { tmnx7710Capability 3 }
        tmnx7710V6v0               OBJECT IDENTIFIER ::= { tmnx7710Capability 4 }
        tmnx7710V6v1               OBJECT IDENTIFIER ::= { tmnx7710Capability 5 }
        tmnx7710V7v0               OBJECT IDENTIFIER ::= { tmnx7710Capability 6 }
        tmnx7710V8v0               OBJECT IDENTIFIER ::= { tmnx7710Capability 7 }
    tmnx7750MGCapability       OBJECT IDENTIFIER ::= { tmnxProductCapability 4 }
        tmnx7750MGV1v0             OBJECT IDENTIFIER ::= { tmnx7750MGCapability 1 }
        tmnx7750MGV2v0             OBJECT IDENTIFIER ::= { tmnx7750MGCapability 2 }
        tmnx7750MGV3v0             OBJECT IDENTIFIER ::= { tmnx7750MGCapability 3 }
        tmnx7750MGV4v0             OBJECT IDENTIFIER ::= { tmnx7750MGCapability 4 }
    tmnxSROSCapability         OBJECT IDENTIFIER ::= { tmnxProductCapability 5 }
        tmnxSROSV8v0               OBJECT IDENTIFIER ::= { tmnxSROSCapability 1 }
        tmnxSROSV9v0               OBJECT IDENTIFIER ::= { tmnxSROSCapability 2 }
        tmnxSROSV10v0              OBJECT IDENTIFIER ::= { tmnxSROSCapability 3 }

--
-- ----------------------------------------------------------------------------
-- timetra 6  : Other Alcatel-Lucent Products based on TIMOS 
-- ----------------------------------------------------------------------------
--
tmnxBasedProducts         OBJECT IDENTIFIER ::= { timetra 6 }
-- aluServiceAggrRouters    OBJECT IDENTIFIER ::= { tmnxBasedProducts 1 }

END
