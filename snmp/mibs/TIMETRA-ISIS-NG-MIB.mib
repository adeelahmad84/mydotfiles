TIMETRA-ISIS-NG-MIB DEFINITIONS ::= BEGIN

IMPORTS
        Integer32, IpAddress, MODULE-IDENTITY,
        NOTIFICATION-TYPE, TimeTicks,
        OBJECT-TYPE, Unsigned32, Counter32, 
        Gauge32                                         FROM SNMPv2-SMI

        MODULE-COMPLIANCE, OBJECT-GROUP,
        NOTIFICATION-GROUP                              FROM SNMPv2-CONF

        DisplayString, RowStatus,
        TruthValue, TimeStamp, MacAddress,
        TimeInterval, TEXTUAL-CONVENTION                FROM SNMPv2-TC

        timetraSRMIBModules, tmnxSRObjs, tmnxSRConfs,
        tmnxSRNotifyPrefix                              FROM TIMETRA-GLOBAL-MIB
        
        TNamedItemOrEmpty, TmnxAdminState, 
        TmnxSpbFid,
        TmnxOperState, TmnxEnabledDisabled,
        TmnxReferenceBandwidth,TNamedItem               
                                                        FROM TIMETRA-TC-MIB

        vRtrIfIndex, TmnxInetCidrNextHopType,
        TmnxInetCidrNextHopOwner,
        vRtrID                                          FROM TIMETRA-VRTR-MIB

        InterfaceIndex                                  FROM IF-MIB

        isisISAdjEntry, isisSysInstance,
        isisSysL1State, isisSysL2State,
        isisISAdjState, isisManAreaAddrExistState,
        isisCircIndex, isisISAdjIndex,
        SystemID, SNPAAddress                           FROM ISIS-MIB

        InetAddressType, InetAddress, 
        InetAddressPrefixLength                         FROM INET-ADDRESS-MIB
        
        ;

timetraIsisNgMIBModule MODULE-IDENTITY
        LAST-UPDATED "201304080000Z"
        ORGANIZATION "Alcatel-Lucent"
        CONTACT-INFO
            "Alcatel-Lucent SROS Support
             Web: http://support.alcatel-lucent.com"
        DESCRIPTION
        "This document is the SNMP MIB module to manage and provision the 
        extensions to the ISIS routing protocol for the Alcatel-Lucent
        SROS device.

        Copyright 2013-2014 Alcatel-Lucent. All rights reserved.
        Reproduction of this document is authorized on the condition that
        the foregoing copyright notice is included.

        This SNMP MIB module (Specification) embodies Alcatel-Lucent's
        proprietary intellectual property.  Alcatel-Lucent retains
        all title and ownership in the Specification, including any
        revisions.

        Alcatel-Lucent grants all interested parties a non-exclusive
        license to use and distribute an unmodified copy of this
        Specification in connection with management of Alcatel-Lucent
        products, and without fee, provided this copyright notice and
        license appear on all copies.

        This Specification is supplied 'as is', and Alcatel-Lucent
        makes no warranty, either express or implied, as to the use,
        operation, condition, or performance of the Specification."
--
--  Revision History
--
        REVISION        "201304080000Z"
        DESCRIPTION     "Rev 0.1                08 Apr 2013 00:00
                         Initial version of the TIMETRA-ISIS-NG-MIB."

        ::= { timetraSRMIBModules 88 }


--%%%%%%%%%%%%%%%%%%%%%%%%%%%%%%%%%%%%%%%%%%%%%%%%%%%%%%%%%%%%%%%%%%%%%%
--
--  Alcatel-Lucent SROS series IS-IS protocol extensions
--

tmnxIsisObjs              OBJECT IDENTIFIER ::= { tmnxSRObjs 88 }
    tmnxIsisSystemObjs         OBJECT IDENTIFIER ::= { tmnxIsisObjs 1 }
    tmnxIsisIfObjs             OBJECT IDENTIFIER ::= { tmnxIsisObjs 2 }
    tmnxIsisAdjObjs            OBJECT IDENTIFIER ::= { tmnxIsisObjs 3 }
    tmnxIsisNotificationObjs   OBJECT IDENTIFIER ::= { tmnxIsisObjs 4 }

tmnxIsisNotifyPrefix      OBJECT IDENTIFIER ::= { tmnxSRNotifyPrefix 88 }
    tmnxIsisNotifications    OBJECT IDENTIFIER ::= { tmnxIsisNotifyPrefix 0 }
    
tmnxIsisConformance       OBJECT IDENTIFIER ::= { tmnxSRConfs 88 }
    tmnxIsisCompliances   OBJECT IDENTIFIER ::= { tmnxIsisConformance 1 }
    tmnxIsisGroups        OBJECT IDENTIFIER ::= { tmnxIsisConformance 2 }
    
-- --------------------------------------------------------------------------
--  Textual Conventions
-- --------------------------------------------------------------------------

TmnxIsisLSPBuffSize ::= TEXTUAL-CONVENTION
    STATUS      current
    DESCRIPTION
        "TmnxIsisLSPBuffSize is the extended integer
         sub range for LSP size."
    SYNTAX         Integer32 (490..9190)

TmnxIsisRoutingTopology ::= TEXTUAL-CONVENTION
    STATUS      current
    DESCRIPTION
        "TmnxIsisRoutingTopology specifies the isis routing topology.

         native(1) - Indicates standard topology.

         mt(2) - Indicates multi-topology for IPv4/IPv6 unicast/multicast 
         routing."
    SYNTAX  INTEGER {
                none (0),
                native (1),
                mt (2)
            }
            
-- --------------------------------------------------------------------------
--  Object definitions
-- --------------------------------------------------------------------------

-- --------------------------------------------------------------------------
--  tmnxIsisTable
-- --------------------------------------------------------------------------
--
--  Extensions to isisSystemTable in ISIS-MIB
--
--  A one-to-one dependent relationship exists between a row in the base
--  table, isisSystemTable, and the extension table, tmnxIsisTable.
--  This in effect extends the isisSystemTable with additional columns.
--  Creation (or deletion) of a row in the isisSystemTable results in the same
--  fate for the equivantly indexed row in the tmnxIsisTable.
--

tmnxIsisTable    OBJECT-TYPE
    SYNTAX      SEQUENCE OF TmnxIsisEntry
    MAX-ACCESS  not-accessible
    STATUS      current
    DESCRIPTION
        "The tmnxIsisTable provides an extension of the isisSysTable in
         the ISIS-MIB."
    ::= { tmnxIsisSystemObjs 1 }

tmnxIsisEntry    OBJECT-TYPE
    SYNTAX      TmnxIsisEntry
    MAX-ACCESS  not-accessible
    STATUS      current
    DESCRIPTION
        "Each row entry in the tmnxIsisTable represents additional columns
         for attributes specific to the Alcatel-Lucent SROS series IS-IS 
         protocol instance on this router."
    INDEX { vRtrID, isisSysInstance }
   ::= { tmnxIsisTable 1 }

TmnxIsisEntry ::=
    SEQUENCE {
        tmnxIsisLastEnabledTime          TimeStamp,
        tmnxIsisAuthKey                  OCTET STRING,
        tmnxIsisAuthType                 INTEGER,
        tmnxIsisAuthCheck                TruthValue,
        tmnxIsisExportPolicy1            TNamedItemOrEmpty,
        tmnxIsisExportPolicy2            TNamedItemOrEmpty,
        tmnxIsisExportPolicy3            TNamedItemOrEmpty,
        tmnxIsisExportPolicy4            TNamedItemOrEmpty,
        tmnxIsisExportPolicy5            TNamedItemOrEmpty,
        tmnxIsisLspLifetime              Unsigned32,
        tmnxIsisOverloadTimeout          Unsigned32,
        tmnxIsisOperState                TmnxOperState,
        tmnxIsisReferenceBw              TmnxReferenceBandwidth,
        tmnxIsisTrafficEng               TruthValue,
        tmnxIsisShortCuts                TruthValue,
        tmnxIsisSpfHoldTime              Integer32,
        tmnxIsisLastSpfRun               TimeStamp,
        tmnxIsisGracefulRestart          TruthValue,
        tmnxIsisOverloadOnBoot           INTEGER,
        tmnxIsisOverloadOnBootTimeout    Unsigned32,
        tmnxIsisSpfWait                  Unsigned32,
        tmnxIsisSpfInitialWait           Unsigned32,
        tmnxIsisSpfSecondWait            Unsigned32,
        tmnxIsisLspMaxWait               Unsigned32,
        tmnxIsisLspInitialWait           Unsigned32,
        tmnxIsisLspSecondWait            Unsigned32,
        tmnxIsisCsnpAuthentication       TruthValue,
        tmnxIsisHelloAuthentication      TruthValue,
        tmnxIsisPsnpAuthentication       TruthValue,
        tmnxIsisGRHelperMode             TruthValue,
        tmnxIsisEnableIPv4               TruthValue,
        tmnxIsisUnicastImport            TruthValue,
        tmnxIsisMulticastImport          TruthValue,
        tmnxIsisStrictAdjacencyCheck     TruthValue,
        tmnxIsisManualSpfTrigger         INTEGER,
        tmnxIsisMultiTopology            TruthValue,
        tmnxIsisMultiTopoIPv6Ucast       TruthValue,
        tmnxIsisIPv6RoutingTopo          INTEGER,
        tmnxIsisSysOrigL1LSPBuffSize     TmnxIsisLSPBuffSize,
        tmnxIsisSysOrigL2LSPBuffSize     TmnxIsisLSPBuffSize,
        tmnxIsisLdpSyncAdminState        TruthValue, 
        tmnxIsisIPv6UnicastImport        TruthValue,
        tmnxIsisIPv6MulticastImport      TruthValue,
        tmnxIsisAdvertisePassiveOnly     TruthValue,
        tmnxIsisDefaultRouteTag          Unsigned32,
        tmnxIsisSuppressDefault          TruthValue,
        tmnxIsisLdpOverRsvp              TmnxEnabledDisabled,
        tmnxIsisExportLimit              Unsigned32,
        tmnxIsisExportLimitLogPercent    Unsigned32,
        tmnxIsisTotalL1ExportedRoutes    Gauge32,
        tmnxIsisTotalL2ExportedRoutes    Gauge32,
        tmnxIsisRsvpShortcut             TruthValue,
        tmnxIsisAdvertiseTunnelLink      TruthValue,
        tmnxIsisIidTlv                   TmnxEnabledDisabled,
        tmnxIsisL1MacAddress             MacAddress,
        tmnxIsisL2MacAddress             MacAddress,
        tmnxIsisSysOperL1LSPBuffSize     TmnxIsisLSPBuffSize,
        tmnxIsisSysOperL2LSPBuffSize     TmnxIsisLSPBuffSize,
        tmnxIsisLoopfreeAlternate        TruthValue,
        tmnxIsisIPv4McastRoutingTopo     TmnxIsisRoutingTopology,
        tmnxIsisIPv6McastRoutingTopo     TmnxIsisRoutingTopology,
        tmnxIsisMultiTopoIPv4Mcast       TruthValue,
        tmnxIsisMultiTopoIPv6Mcast       TruthValue,
        tmnxIsisOverloadMaxMetric        TruthValue,
        tmnxIsisOverloadOnBootMaxMetric  TruthValue,
        tmnxIsisRouterId                 Unsigned32,
        tmnxIsisAdvRtrCapability         INTEGER,
        tmnxIsisHelloPadding             INTEGER,
        tmnxIsisLspRefreshInterval       Unsigned32,
        tmnxIsisOperRouterId            Unsigned32,
        tmnxIsisAuthKeyChain            TNamedItemOrEmpty,
        tmnxIsisIgnoreLspErrors         TruthValue
    }

tmnxIsisLastEnabledTime    OBJECT-TYPE
    SYNTAX      TimeStamp
    MAX-ACCESS  read-only
    STATUS      current
    DESCRIPTION
        "The value of the object tmnxIsisLastEnabledTime indicates the 
         sysUpTime value when isisSysAdminState was last set to enabled (1) 
         to run the IS-IS protocol in the router."
    ::= { tmnxIsisEntry 1 }

tmnxIsisAuthKey     OBJECT-TYPE
    SYNTAX      OCTET STRING (SIZE(0..254))
    MAX-ACCESS  read-write
    STATUS      current
    DESCRIPTION
        "The value of the object tmnxIsisAuthKey specifies the 
         authentication key string used to verify the authenticity of
         packets sent by neighboring routers on an IS-IS interface.
             
         For authentication to succeed both the authentication key and
         the authentication type defined by the object tmnxIsisAuthType
         must match.
             
         If tmnxIsisAuthType is set to 'password', tmnxIsisAuthKey can 
         include any ASCII character.

         Authentication can be configured globally and applied to all
         ISIS levels or it can be configured on a per level basis;
         the most specific value is used.

         When read, tmnxIsisAuthKey always returns an Octet String of
         length zero."
    DEFVAL { ''H }   
    ::= { tmnxIsisEntry 2 }

tmnxIsisAuthType        OBJECT-TYPE
    SYNTAX      INTEGER {
                    none (1),
                    password (2),
                    md5 (3)
                }
    MAX-ACCESS  read-write
    STATUS      current
    DESCRIPTION
        "The value of the object tmnxIsisAuthType specifies the method of
         authentication used to verify the authenticity of packets sent
         by neighboring routers on an IS-IS interface.  
             
         For authentication to succeed both the authentication key defined in 
         the tmnxIsisAuthKey object and the authentication type must match.

         Authentication can be configured globally and applied to all
         ISIS levels or it can be configured on a per level basis; the
         most specific value is used."
    DEFVAL { none }
    ::= { tmnxIsisEntry 3 }

tmnxIsisAuthCheck       OBJECT-TYPE
    SYNTAX      TruthValue
    MAX-ACCESS  read-write
    STATUS      current
    DESCRIPTION
        "The value of the object tmnxIsisAuthCheck specifies whether
         authentication check has to be performed on received 
             IS-IS protocol packets to determine if they should be rejected.
             
             When tmnxIsisAuthCheck has a value of 'true', all IS-IS protocol
             packets that have a mismatch on either the authentication type,
             specified by the value of tmnxIsisAuthType, or the authentication
             key, given in tmnxIsisAuthKey are rejected.

             When tmnxIsisAuthCheck has a value of 'false', authentication is
             performed on received IS-IS protocol packets but mismatched
             packets are not rejected."
    DEFVAL { true }
    ::= { tmnxIsisEntry 4 }

tmnxIsisExportPolicy1   OBJECT-TYPE
    SYNTAX      TNamedItemOrEmpty
    MAX-ACCESS  read-write
    STATUS      current
    DESCRIPTION
        "The value of the object tmnxIsisExportPolicy1 specifies the name of
         the first policy to be used for determining which routes are exported 
         from the routing table to IS-IS. 
             
         If no export policy is defined, non IS-IS router will not be exported
         from the routing table manager to IS-IS.

         If multiple policy names are specified, the policies are evaluated
         in the order they are specified and the first policy that matches
         will be applied.

         The export policy name list, tmnxIsisExportPolicy1 through
         tmnxIsisExportPolicy5, is handled by the SNMP agent as a single
         entity.  When an SNMP SET request is received to modify one or
         more of the policy names, all the policy variables are first
         set to the empty string, ''H, and then the new names are set
         into the specified policy variables within a single SNMP SET PDU."
    DEFVAL { ''H }  
    ::= { tmnxIsisEntry 5 }

tmnxIsisExportPolicy2   OBJECT-TYPE
    SYNTAX      TNamedItemOrEmpty
    MAX-ACCESS  read-write
    STATUS      current
    DESCRIPTION
        "The value of the object tmnxIsisExportPolicy2 specifies the name of
         the second policy to be used for determining which routes are exported 
         from the routing table to IS-IS.
             
         If no export policy is defined, non IS-IS router will not be exported
         from the routing table manager to IS-IS.

         If multiple policy names are specified, the policies are evaluated
         in the order they are specified and the first policy that matches
         will be applied.

         The export policy name list, tmnxIsisExportPolicy1 through
         tmnxIsisExportPolicy5, is handled by the SNMP agent as a single
         entity.  When an SNMP SET request is received to modify one or
         more of the policy names, all the policy variables are first
         set to the empty string, ''H, and then the new names are set
         into the specified policy variables within a single SNMP SET PDU."
    DEFVAL { ''H }  
    ::= { tmnxIsisEntry 6 }

tmnxIsisExportPolicy3   OBJECT-TYPE
    SYNTAX      TNamedItemOrEmpty
    MAX-ACCESS  read-write
    STATUS      current
    DESCRIPTION
        "The value of the object tmnxIsisExportPolicy1 specifies the name of
         the third policy to be used for determining which routes are exported 
         from the routing table to IS-IS.
             
         If no export policy is defined, non IS-IS router will not be exported from
         the routing table manager to IS-IS.

         If multiple policy names are specified, the policies are evaluated
         in the order they are specified and the first policy that matches
         will be applied.

         The export policy name list, tmnxIsisExportPolicy1 through
         tmnxIsisExportPolicy5, is handled by the SNMP agent as a single
         entity.  When an SNMP SET request is received to modify one or
         more of the policy names, all the policy variables are first
         set to the empty string, ''H, and then the new names are set
         into the specified policy variables within a single SNMP SET PDU."
    DEFVAL { ''H }  
    ::= { tmnxIsisEntry 7 }

tmnxIsisExportPolicy4   OBJECT-TYPE
    SYNTAX      TNamedItemOrEmpty
    MAX-ACCESS  read-write
    STATUS      current
    DESCRIPTION
        "The value of the object tmnxIsisExportPolicy1 specifies the name of
         the fourth policy to be used for determining which routes are exported
         from the routing table to IS-IS.
         
         If no export policy is defined, non IS-IS router will not be exported
         from the routing table manager to IS-IS.

         If multiple policy names are specified, the policies are evaluated
         in the order they are specified and the first policy that matches
         will be applied.

         The export policy name list, tmnxIsisExportPolicy1 through
         tmnxIsisExportPolicy5, is handled by the SNMP agent as a single
         entity.  When an SNMP SET request is received to modify one or
         more of the policy names, all the policy variables are first
         set to the empty string, ''H, and then the new names are set
         into the specified policy variables within a single SNMP SET PDU."
    DEFVAL { ''H }  
    ::= { tmnxIsisEntry 8 }

tmnxIsisExportPolicy5   OBJECT-TYPE
    SYNTAX      TNamedItemOrEmpty
    MAX-ACCESS  read-write
    STATUS      current
    DESCRIPTION
        "The value of the object tmnxIsisExportPolicy1 specifies the name of
         the fifth policy to be used for determining which routes are exported
         from the routing table to IS-IS.
         
         If no export policy is defined, non IS-IS router will not be exported
         from the routing table manager to IS-IS.

         If multiple policy names are specified, the policies are evaluated
         in the order they are specified and the first policy that matches
         will be applied.

         The export policy name list, tmnxIsisExportPolicy1 through
         tmnxIsisExportPolicy5, is handled by the SNMP agent as a single
         entity.  When an SNMP SET request is received to modify one or
         more of the policy names, all the policy variables are first
         set to the empty string, ''H, and then the new names are set
         into the specified policy variables within a single SNMP SET PDU."
    DEFVAL { ''H }  
    ::= { tmnxIsisEntry 9 }

tmnxIsisLspLifetime     OBJECT-TYPE
    SYNTAX      Unsigned32 (350..65535)
    UNITS       "seconds"
    MAX-ACCESS  read-write
    STATUS      current
    DESCRIPTION
        "The value of the object tmnxIsisLspLifetime specifies the amount of 
         time, in seconds, a given LSP is considered valid without the originating 
         router having refreshed the LSP.  
     
         The actual LSP refresh timer is the value of tmnxIsisLspLifetime minus
         317 seconds."
    DEFVAL { 1200 }
    ::= { tmnxIsisEntry 10 }

tmnxIsisOverloadTimeout     OBJECT-TYPE
    SYNTAX      Unsigned32 (0|60..1800)
    UNITS       "seconds"
    MAX-ACCESS  read-write
    STATUS      current
    DESCRIPTION
        "The value of the object tmnxIsisOverloadTimeout specifies the amount of 
         time, in seconds, the router operates in the overload state before
         attempting to reestablish normal operations. 
         
         While in overload state, this IS-IS router will only be used if the 
         destination is only reachable via this router; it is not used for other 
         transit traffic.  
         
         Operationally placing the router into the overload state is
         often used as a precursor to shutting down the IS-IS protocol operation.
         
         This variable is an extension to the isisSysWaitTime to accept an
         additional value of 0 to specify that the router is in overload
         infinitely."
    DEFVAL { 0 }
    ::= { tmnxIsisEntry 11 }

tmnxIsisOperState    OBJECT-TYPE
    SYNTAX      TmnxOperState
    MAX-ACCESS  read-only
    STATUS      current
    DESCRIPTION
        "The value of the object tmnxIsisOperState indicates the current 
         operating state of this IS-IS protocol instance on this router."
    ::= { tmnxIsisEntry 12 }

tmnxIsisReferenceBw     OBJECT-TYPE
    SYNTAX      TmnxReferenceBandwidth
    UNITS       "kilobits per second"
    MAX-ACCESS  read-write
    STATUS      current
    DESCRIPTION
        "The value of the object tmnxIsisReferenceBw specifies 
         the reference bandwidth that needs to be used to calculate
         the cost. 
         
         In order to calculate the lowest cost to reach a given destination
         each configured level on each interface must have a cost.
         
         If the reference-bandwidth is defined then the cost is calculated
         using the following formula:
             Cost = reference-bandwidth / bandwidth.
                 
         If the reference bandwidth is configured as Ten Gig (10,000,000,000)
         a 100-Mbps interface has a default metric of 100. 
         In order for metrics in excess of 63 to be configured wide metrics must
         be deployed.

         A value of '0' means that the reference bandwidth is not defined."
    DEFVAL { 0 }
    ::= { tmnxIsisEntry 13 }

tmnxIsisTrafficEng      OBJECT-TYPE
    SYNTAX      TruthValue
    MAX-ACCESS  read-write
    STATUS      current
    DESCRIPTION
        "The value of the object tmnxIsisTrafficEng specifies whether
         traffic engineering is enabled for the router.
         
         When the value of tmnxIsisTrafficEng is 'true', traffic
         engineering is enabled for the router.
         
         When the value of tmnxIsisTrafficEng is 'false', traffic 
         engineering is disabled so that te-metrics are not generated and
         are ignored when received by this node."
    DEFVAL { false }
    ::= { tmnxIsisEntry 14 }

tmnxIsisShortCuts       OBJECT-TYPE
    SYNTAX      TruthValue
    MAX-ACCESS  read-only
    STATUS      current
    DESCRIPTION
        "The value of the object tmnxIsisShortCuts indicates whether
         IGP shortcuts are required or not.
         
         When the value of tmnxIsisShortCuts is 'true', MPLS label switched
         paths of LSPs are used as next hops whenever BGP need to resolve
         the next hop within the IS-IS domain. 
         
         When the value of tmnxIsisShortCuts is 'false', IGP shortcuts are not 
         required by BGP.
             
         This doesn't have any meaning if tmnxIsisTrafficEng is set to false."
    ::= { tmnxIsisEntry 15 }

tmnxIsisSpfHoldTime      OBJECT-TYPE
    SYNTAX      Integer32 (0..65535)
    UNITS       "seconds"
    MAX-ACCESS  read-only
    STATUS      current
    DESCRIPTION
        "The value of the object tmnxIsisSpfHoldTime indicates the
         time interval at which SPF is run."
    ::= { tmnxIsisEntry 16 }

tmnxIsisLastSpfRun    OBJECT-TYPE
    SYNTAX      TimeStamp
    MAX-ACCESS  read-only
    STATUS      current
    DESCRIPTION
        "The value of the object tmnxIsisLastSpfRun indicates the  
         sysUpTime value when the last SPF run was performed for this 
         instance of the IS-IS protocol in the router."
    ::= { tmnxIsisEntry 17 }

tmnxIsisGracefulRestart    OBJECT-TYPE
    SYNTAX      TruthValue
    MAX-ACCESS  read-write
    STATUS      current
    DESCRIPTION
        "The value of the object tmnxIsisGracefulRestart specifies  
         whether the graceful restart is enabled or disabled for this 
         instance of IS-IS on the router."
    DEFVAL { false }
    ::= { tmnxIsisEntry 18 }

tmnxIsisOverloadOnBoot     OBJECT-TYPE
    SYNTAX INTEGER
        {
          disabled(1),
          enabled(2)
        }
    MAX-ACCESS  read-write
    STATUS      current
    DESCRIPTION
        "The value of the object tmnxIsisOverloadOnBoot specifies if 
         the router should be in overload state right after the boot up process.
         
         If the tmnxIsisOverloadOnBoot is set to 'enabled' the overload 
         timeout is maintained by tmnxIsisOverloadOnBootTimeout."
     DEFVAL { disabled }
    ::= { tmnxIsisEntry 19 }

tmnxIsisOverloadOnBootTimeout     OBJECT-TYPE
    SYNTAX      Unsigned32 (0|60..1800)
    UNITS       "seconds"
    MAX-ACCESS  read-write
    STATUS      current
    DESCRIPTION
        "The value of the object tmnxIsisOverloadOnBootTimeout specifies
         the amount of time, in seconds, for which the router operates in  
         the overload state before attempting to reestablish normal operations  
         when the system comes up after a fresh boot.  
         
         While in overload state, this IS-IS router will only be used if 
         the destination is only reachable via this router; it is not used
         for other transit traffic."
    DEFVAL { 0 }
    ::= { tmnxIsisEntry 20 }

tmnxIsisSpfWait     OBJECT-TYPE
    SYNTAX      Unsigned32 (1..120)
    UNITS       "seconds"
    MAX-ACCESS  read-write
    STATUS      current
    DESCRIPTION
        "The value of the object tmnxIsisSpfWait specifies the  
         Maximum intervalbetween two consecutive spf calculations
         in seconds."
    DEFVAL { 10 }
    ::= { tmnxIsisEntry 21 }

tmnxIsisSpfInitialWait     OBJECT-TYPE
    SYNTAX      Unsigned32 (10..100000)
    UNITS       "milliseconds"
    MAX-ACCESS  read-write
    STATUS      current
    DESCRIPTION
        "The value of the object tmnxIsisSpfInitialWait specifies the 
         initial SPF calculation delay (in milliseconds) after a 
         topology change."
    DEFVAL { 1000 }
    ::= { tmnxIsisEntry 22 }

tmnxIsisSpfSecondWait     OBJECT-TYPE
    SYNTAX      Unsigned32 (1..100000)
    UNITS       "milliseconds"
    MAX-ACCESS  read-write
    STATUS      current
    DESCRIPTION
        "The value of the object tmnxIsisSpfInitialWait specifies the  
         hold time, in milliseconds, between the first and second SPF
         calculation.

         Subsequent SPF runs will occur at exponentially increasing 
         intervals of spf-second-wait i.e. if spf-second-wait is 1000, 
         then the next SPF will run after 2000 msec, the next one at 
         4000 msec etc until it is capped off at spf-wait value. 

         The SPF interval will stay at spf-wait value until there are no 
         more SPF runs scheduled in that interval. After a full interval
         without any SPF runs, the SPF interval will drop back to
         spf-initial-wait."
    DEFVAL { 1000 }
    ::= { tmnxIsisEntry 23 }

tmnxIsisLspMaxWait     OBJECT-TYPE
    SYNTAX      Unsigned32 (1..120)
    UNITS       "seconds"
    MAX-ACCESS  read-write
    STATUS      current
    DESCRIPTION
        "The value of the object tmnxIsisLspMaxWait specifies the  
         maximum interval, in seconds, between two consecutive ocurrences
         of an LSP being generated."
    DEFVAL { 5 }
    ::= { tmnxIsisEntry 24 }

tmnxIsisLspInitialWait     OBJECT-TYPE
    SYNTAX      Unsigned32 (0..100)
    UNITS       "seconds"
    MAX-ACCESS  read-write
    STATUS      current
    DESCRIPTION
        "The value of the object tmnxIsisLspInitialWait specifies the 
         initial LSP generation delay in seconds."
    DEFVAL { 0 }
    ::= { tmnxIsisEntry 25 }

tmnxIsisLspSecondWait     OBJECT-TYPE
    SYNTAX      Unsigned32 (1..100)
    UNITS       "seconds"
    MAX-ACCESS  read-write
    STATUS      current
    DESCRIPTION
        "The value of the object tmnxIsisLspInitialWait specifies the 
         hold time, in seconds, between the first and second LSP
         generation."
    DEFVAL { 1 }
    ::= { tmnxIsisEntry 26 }

tmnxIsisCsnpAuthentication       OBJECT-TYPE
    SYNTAX      TruthValue
    MAX-ACCESS  read-write
    STATUS      current
    DESCRIPTION
        "The value of the object tmnxIsisCsnpAuthentication specifies
         whether authentication of CSNP packets is enabled or not.
         
         When tmnxIsisCsnpAuthentication has a value of 'true', 
         authentication of individual ISIS packets of CSNP type is
         enabled. 

         When tmnxIsisCsnpAuthentication has a value of 'false',
         authentication of CSNP packets is suppressed."
    DEFVAL { true }
    ::= { tmnxIsisEntry 27 }

tmnxIsisHelloAuthentication       OBJECT-TYPE
    SYNTAX      TruthValue
    MAX-ACCESS  read-write
    STATUS      current
    DESCRIPTION
        "The value of the object tmnxIsisHelloAuthentication specifies
         whether authentication of HELLO packets is enabled or not.
             
         When tmnxIsisHelloAuthentication has a value of 'true', 
         authentication of individual ISIS packets of HELLO type is 
         enabled. 

         When tmnxIsisHelloAuthentication has a value of 'false',
         authentication of HELLO packets is suppressed."
    DEFVAL { true }
    ::= { tmnxIsisEntry 28 }

tmnxIsisPsnpAuthentication       OBJECT-TYPE
    SYNTAX      TruthValue
    MAX-ACCESS  read-write
    STATUS      current
    DESCRIPTION
        "The value of the object tmnxIsisPsnpAuthentication specifies
         whether authentication of PSNP packets is enabled or not.
         
         When tmnxIsisPsnpAuthentication has a value of 'true', 
         authentication of individual ISIS packets of PSNP type is 
         enabled.  

         When tmnxIsisPsnpAuthentication has a value of 'false',
         authentication of PSNP packets is suppressed."
    DEFVAL { true }
    ::= { tmnxIsisEntry 29 }

tmnxIsisGRHelperMode  OBJECT-TYPE
    SYNTAX      TruthValue
    MAX-ACCESS  read-write
    STATUS      current
    DESCRIPTION
        "The value of the object tmnxIsisGRHelperMode specifies whether the 
         graceful restart helper mode is enabled or disabled for this 
         instance of IS-IS on the router.
         
         The value of the object tmnxIsisGRHelperMode is only valid if the  
         value of object tmnxIsisGracefulRestart is 'true'.
        
         When tmnxIsisGRHelperMode has a value of 'true' graceful restart
         helper capabilities are enabled.  
         
         When tmnxIsisGRHelperMode has a value of 'false' the graceful restart
         helper capabilities are disabled."
    DEFVAL { false }
    ::= { tmnxIsisEntry 30 }

tmnxIsisEnableIPv4      OBJECT-TYPE
    SYNTAX      TruthValue
    MAX-ACCESS  read-write
    STATUS      current
    DESCRIPTION
        "The value of the object tmnxIsisEnableIPv4 specifies whether this 
         IS-IS instance supports IPv4.
         
         When tmnxIsisEnableIPv4 has a value of 'true', the IS-IS instance 
         supports IPv4, and when it has a value of 'false', it does not."
    DEFVAL { true }
    ::= { tmnxIsisEntry 31 }

tmnxIsisUnicastImport      OBJECT-TYPE
    SYNTAX      TruthValue
    MAX-ACCESS  read-write
    STATUS      current
    DESCRIPTION
        "The value of the object tmnxIsisUnicastImport specifies whether ISIS 
         protocol will submit routes into the unicast Route Table Manage(RTM).
         
         When tmnxIsisUnicastImport has a value of 'true', the IS-IS instance 
         submits routes into the unicast RTM, and when it has a value 
         of 'false', it does not."
    DEFVAL { true }
    ::= { tmnxIsisEntry 32 }

tmnxIsisMulticastImport      OBJECT-TYPE
    SYNTAX      TruthValue
    MAX-ACCESS  read-write
    STATUS      current
    DESCRIPTION
        "The value of the object tmnxIsisMulticastImport specifies whether ISIS 
         protocol will submit routes into the multicast Reverse Path Forwarding(RPF) 
         Route Table Manage(RTM).
         
         When tmnxIsisMulticastImport has a value of 'true', ISIS protocol 
         submits routes into the multicast RPF RTM and when it has a 
         value of 'false', it does not."
    DEFVAL { false }
    ::= { tmnxIsisEntry 33 }

tmnxIsisStrictAdjacencyCheck    OBJECT-TYPE
    SYNTAX      TruthValue
    MAX-ACCESS  read-write
    STATUS      current
    DESCRIPTION
        "The value of the object tmnxIsisStrictAdjacencyCheck specifies whether 
         an ISIS adjacency can be formed when two routers do not run the 
         same IP versions.

         When tmnxIsisStrictAdjacencyCheck is 'true', both routers have to   
         run the same IP versions in the ISIS protocol. 
         
         When tmnxIsisStrictAdjacencyCheck is 'false', having one common 
         IP version running is enough to form an adjacency."
    DEFVAL { false }
    ::= { tmnxIsisEntry 34 }

tmnxIsisManualSpfTrigger OBJECT-TYPE
    SYNTAX      INTEGER {
                    noAction(1),
                    runTotalSpf(2)
                }
    MAX-ACCESS  read-write
    STATUS      current
    DESCRIPTION
        "The value of the object tmnxIsisManualSpfTrigger specifies a manual 
         Dijkstra SPF calculation trigger.

         When tmnxIsisManualSpfTrigger is set to 'runTotalSpf' a normal
         Dijkstra SPF calculation is performed.
         
         GETs and GETNEXTs on this variable return 'noAction'."
    DEFVAL { noAction }
    ::= { tmnxIsisEntry 35 }

tmnxIsisMultiTopology    OBJECT-TYPE
    SYNTAX      TruthValue
    MAX-ACCESS  read-write
    STATUS      current
    DESCRIPTION
        "The value of the object tmnxIsisMultiTopology specifies if the 
         multi topology for ISIS is enabled."
    DEFVAL { false }
    ::= { tmnxIsisEntry 36 }

tmnxIsisMultiTopoIPv6Ucast OBJECT-TYPE
    SYNTAX      TruthValue
    MAX-ACCESS  read-write
    STATUS      current
    DESCRIPTION
        "The value of the object tmnxIsisMultiTopoIPv6Ucast specifies if 
         IPv6 unicast is enabled for ISIS multi topology. 

         To enable IPv6 unicast on ISIS, tmnxIsisMultiTopology should
         be set to 'true'."
    DEFVAL { false }
    ::= { tmnxIsisEntry 37 }
    
tmnxIsisIPv6RoutingTopo  OBJECT-TYPE
    SYNTAX      INTEGER {
                    none(0),
                    native(1),
                    mt(2)
                }
    MAX-ACCESS  read-write
    STATUS      current
    DESCRIPTION
        "The value of the object tmnxIsisIPv6RoutingTopo specifies the 
         routing topology for IPv6.

         If the value of tmnxIsisIPv6RoutingTopo is set to 'mt', 
         multi topology for ipv6 routing is in effect only if 
         tmnxIsisMultiTopoIPv6Ucast is set to 'true'."
    DEFVAL { none }
    ::= { tmnxIsisEntry 38 }

tmnxIsisSysOrigL1LSPBuffSize OBJECT-TYPE
    SYNTAX TmnxIsisLSPBuffSize
    MAX-ACCESS read-write
    STATUS current
    DESCRIPTION
        "The value of the object tmnxIsisSysOrigL1LSPBuffSize specifies the 
         maximum size of Level 1 LSPs and SNPs originated by this instance.

         This object may only be modified when the ISIS-MIB::isisSysAdminState
         member of the corresponding entry in the ISIS-MIB::isisSysTable table
         has a value of 'outOfService (3)'.

         This object replaces the ISIS-MIB::isisSysOrigL1LSPBuffSize
         member of the ISIS-MIB::isisSysTable table."
     DEFVAL { 1492 }
     ::= { tmnxIsisEntry 39 }

tmnxIsisSysOrigL2LSPBuffSize OBJECT-TYPE
    SYNTAX TmnxIsisLSPBuffSize
    MAX-ACCESS read-write
    STATUS current
    DESCRIPTION
        "The value of the object tmnxIsisSysOrigL2LSPBuffSize specifies the 
         maximum size of Level 2 LSPs and SNPs originated by this system.

         This object may only be modified when the ISIS-MIB::isisSysAdminState
         member of the corresponding entry in the ISIS-MIB::isisSysTable table
         has a value of 'outOfService (3)'.

         This object replaces the ISIS-MIB::isisSysOrigL2LSPBuffSize
         member of the ISIS-MIB::isisSysTable table."
     DEFVAL { 1492 }
     ::= { tmnxIsisEntry 40 }

tmnxIsisLdpSyncAdminState     OBJECT-TYPE 
    SYNTAX      TruthValue 
    MAX-ACCESS  read-write
    STATUS      current 
    DESCRIPTION
        "The value of the object tmnxIsisLdpSyncAdminState specifies whether  
         the IGP-LDP synchronization feature is enabled or disabled on all 
         interfaces participating in the ISIS routing protocol. 
    
         When the value is set to 'false', IGP immediately advertises the actual
         value of the link cost for all interfaces which have the IGP-LDP 
         synchronization enabled if the currently advertized cost is different. 
         It will then disable IGP-LDP synchronization for all interfaces."
    DEFVAL { true }
    ::= { tmnxIsisEntry 41 }

tmnxIsisIPv6UnicastImport      OBJECT-TYPE
    SYNTAX      TruthValue
    MAX-ACCESS  read-write
    STATUS      current
    DESCRIPTION
        "The value of the object tmnxIsisIPv6UnicastImport specifies
         whether ISIS protocol will submit routes into the unicast  
         IPv6 Route Table Manage(RTM).
         
         When tmnxIsisUnicastImport has a value of 'true', the IS-IS instance 
         submits routes into the unicast IPv6 RTM, and when it has a value 
         of 'false', it does not."
    DEFVAL { true }
    ::= { tmnxIsisEntry 42 }

tmnxIsisIPv6MulticastImport      OBJECT-TYPE
    SYNTAX      TruthValue
    MAX-ACCESS  read-write
    STATUS      current
    DESCRIPTION
        "The value of the object tmnxIsisIPv6MulticastImport specifies
         whether ISIS protocol will submit routes into the multicast
         IPv6 Reverse Path Forwarding(RPF) Route Table Manage(RTM).
         
         When tmnxIsisMulticastImport has a value of 'true', ISIS protocol 
         submits routes into the multicast IPv6 RPF RTM and when it has a 
         value of 'false', it does not."
    DEFVAL { false }
    ::= { tmnxIsisEntry 43 }

tmnxIsisAdvertisePassiveOnly    OBJECT-TYPE
    SYNTAX      TruthValue
    MAX-ACCESS  read-write
    STATUS      current
    DESCRIPTION
        "The value of the object tmnxIsisAdvertisePassiveOnly specifies whether 
         ISIS protocol will advertise only prefixes that belong to passive 
         interfaces.

         When tmnxIsisAdvertisePassiveOnly is set to 'true', ISIS protocol
         advertises only prefixes that belong to passive interfaces."
    DEFVAL { false }
    ::= { tmnxIsisEntry 44 }

tmnxIsisDefaultRouteTag  OBJECT-TYPE
    SYNTAX      Unsigned32
    MAX-ACCESS  read-write
    STATUS      current
    DESCRIPTION
        "The value of the object tmnxIsisDefaultRouteTag specifies a 
         32-bit integer tag for the ISIS default route. 
         
         This route tag can be used to apply administrative
         policy. 
         
         A value of 0 indicates that the tag has not been set."
    DEFVAL { 0 }
    ::= { tmnxIsisEntry 45 }

tmnxIsisSuppressDefault     OBJECT-TYPE
    SYNTAX      TruthValue
    MAX-ACCESS  read-write
    STATUS      current
    DESCRIPTION
        "The value of the object tmnxIsisSuppressDefault specifies whether 
         ISIS protocol will suppress the installation of the default routes
         on L1 router.

         When tmnxIsisSuppressDefault is set to 'true', ISIS protocol
         will suppress the installation of the default routes."
    DEFVAL { false }
    ::= { tmnxIsisEntry 46 }

tmnxIsisLdpOverRsvp  OBJECT-TYPE
    SYNTAX      TmnxEnabledDisabled
    MAX-ACCESS  read-write
    STATUS      current
    DESCRIPTION
        "The value of the object tmnxIsisLdpOverRsvp specifies whether 
         LDP-over-RSVP feature is enabled or disabled for ISIS.

         When tmnxIsisLdpOverRsvp is enabled, ISIS will select the endpoint
         that is closest to the destination for further selection of 
         LDP-over-RSVP tunnels to that endpoint."
    DEFVAL { disabled }
    ::= { tmnxIsisEntry 47 }

tmnxIsisExportLimit         OBJECT-TYPE
    SYNTAX      Unsigned32
    MAX-ACCESS  read-write
    STATUS      current
    DESCRIPTION
        "The value of the object tmnxIsisExportLimit specifies the  
         maximum number of routes or prefixes that can be exported into 
         ISIS from the route table.

         A value of 0 indicates that the export limit for routes or 
         prefixes has been disabled."
    DEFVAL { 0 }
    ::= { tmnxIsisEntry 48 }

tmnxIsisExportLimitLogPercent       OBJECT-TYPE
    SYNTAX      Unsigned32  (0..100)
    UNITS       "percentage"
    MAX-ACCESS  read-write
    STATUS      current
    DESCRIPTION
        "The value of the object tmnxIsisExportLimitLogPercent specifies the 
         percentage of the export-limit at which a warning log message and  
         SNMP notification would be sent; this would only be a warning and 
         additional routes will be learned up to 100% of tmnxIsisExportLimit.

         A value of 0 indicates that tmnxIsisExportLimitLogPercent is disabled
         and no log message or SNMP notification would be sent."
    DEFVAL { 0 }
    ::= { tmnxIsisEntry 49 }

tmnxIsisTotalL1ExportedRoutes         OBJECT-TYPE
    SYNTAX      Gauge32
    MAX-ACCESS  read-only
    STATUS      current
    DESCRIPTION
        "The value of the object tmnxIsisTotalL1ExportedRoutes indicates the 
         total number of routes exported into ISIS level 1 from the route table manager 
         when an export policy is configured.

         Value of tmnxIsisTotalL1ExportedRoutes would be 0 when no export policy
         is configured."
    ::= { tmnxIsisEntry 50 }

tmnxIsisTotalL2ExportedRoutes         OBJECT-TYPE
    SYNTAX      Gauge32
    MAX-ACCESS  read-only
    STATUS      current
    DESCRIPTION
        "The value of the object tmnxIsisTotalL2ExportedRoutes indicates the 
         total number of routes exported into ISIS level 2 from the route table manager 
         when an export policy is configured.

         Value of tmnxIsisTotalL2ExportedRoutes would be 0 when no export policy
         is configured."
    ::= { tmnxIsisEntry 51 }

tmnxIsisRsvpShortcut         OBJECT-TYPE
    SYNTAX      TruthValue
    MAX-ACCESS  read-write
    STATUS      current
    DESCRIPTION
        "The value of the object tmnxIsisRsvpShortcut specifies whether 
         RSVP-TE shortcut for resolving IGP routes has been enabled or disabled
         for IS-IS.

         When the value of tmnxIsisRsvpShortcut is set to true RSVP-TE shortcut 
         is enabled and when tmnxIsisRsvpShortcut is set to false RSVP-TE shortcut
         is disabled for IS-IS."
    DEFVAL { false }     
    ::= { tmnxIsisEntry 52 }

tmnxIsisAdvertiseTunnelLink         OBJECT-TYPE
    SYNTAX      TruthValue
    MAX-ACCESS  read-write
    STATUS      current
    DESCRIPTION
        "The value of the object tmnxIsisAdvertiseTunnelLink specifies whether 
         advertisement of LSP shortcuts into IGP has been enabled or disabled 
         for IS-IS.

         When the value of tmnxIsisAdvertiseTunnelLink is set to true LSP shortcut 
         advertisement into IGP is enabled and when tmnxIsisAdvertiseTunnelLink is 
         set to false LSP shortcut advertisement into IGP is disabled."
    DEFVAL { false }     
    ::= { tmnxIsisEntry 53 }

tmnxIsisIidTlv      OBJECT-TYPE
    SYNTAX      TmnxEnabledDisabled
    MAX-ACCESS  read-write
    STATUS      current
    DESCRIPTION
        "The value of the object tmnxIsisIidTlv specifies whether 
         Instance Identifier (IID) TLV has been enabled or disabled for 
         this ISIS instance.

         When the value of tmnxIsisIidTlv is 'enabled', each ISIS instance 
         marks its packets with the IID TLV containing its unique 16-bit IID  
         for the routing domain."
    DEFVAL  { disabled }
    ::= { tmnxIsisEntry 54 }

tmnxIsisL1MacAddress    OBJECT-TYPE
    SYNTAX      MacAddress
    MAX-ACCESS  read-write
    STATUS      current
    DESCRIPTION
        "The value of the object tmnxIsisL1MacAddress specifies the 
         destination MAC address for all L1 ISIS neighbors on the 
         link for this ISIS instance."
    DEFVAL { '0180C2000014'H }
    ::= { tmnxIsisEntry 55 }

tmnxIsisL2MacAddress    OBJECT-TYPE
    SYNTAX      MacAddress
    MAX-ACCESS  read-write
    STATUS      current
    DESCRIPTION
        "The value of the object tmnxIsisL1MacAddress specifies the 
         destination MAC address for all L2 ISIS neighbors on the 
         link for this ISIS instance."
    DEFVAL { '0180C2000015'H }
    ::= { tmnxIsisEntry 56 }

tmnxIsisSysOperL1LSPBuffSize OBJECT-TYPE
    SYNTAX TmnxIsisLSPBuffSize
    MAX-ACCESS read-only
    STATUS current
    DESCRIPTION
        "The value of the object tmnxIsisSysOperL1LSPBuffSize indicates the  
         operational size of Level 1 LSPs and SNPs originated by this instance."
     ::= { tmnxIsisEntry 57 }

tmnxIsisSysOperL2LSPBuffSize OBJECT-TYPE
    SYNTAX TmnxIsisLSPBuffSize
    MAX-ACCESS read-only
    STATUS current
    DESCRIPTION
        "The value of the object tmnxIsisSysOperL2LSPBuffSize indicates the  
         operational size of Level 2 LSPs and SNPs originated by this instance."
     ::= { tmnxIsisEntry 58 }

tmnxIsisLoopfreeAlternate    OBJECT-TYPE
    SYNTAX      TruthValue
    MAX-ACCESS  read-write
    STATUS      current
    DESCRIPTION
        "The value of the object tmnxIsisLoopfreeAlternate specifies whether 
         IP fast re-route capability for ISIS is enabled or disabled.

         When the value of tmnxIsisLoopfreeAlternate is set to 'true' IP fast 
         re-route capability for ISIS is enabled and when 
         tmnxIsisLoopfreeAlternate is set to 'false' IP fast re-route capability 
         for ISIS is disabled."
    DEFVAL { false } 
    ::= { tmnxIsisEntry 59 }

tmnxIsisIPv4McastRoutingTopo    OBJECT-TYPE
    SYNTAX      TmnxIsisRoutingTopology
    MAX-ACCESS  read-write
    STATUS      current
    DESCRIPTION
        "The value of the object tmnxIsisIPv4McastRoutingTopo specifies which  
         multicast topology (MT) is enabled.
         
         If the value of tmnxIsisIPv4McastRoutingTopo is 'native' then MT 0 IPv4 
         topology is enabled and ISIS protocol will add routes to the multicast 
         RTM.
         
         If the value of tmnxIsisIPv4McastRoutingTopo is 'mt' then MT 3 
         IPv4 topology is enabled and routes will be added to the multicast RTM.
         
         If the value of tmnxIsisIPv4McastRoutingTopo is 'none' then nothing is 
         added to the multicast RTM."
    DEFVAL { native } 
    ::= { tmnxIsisEntry 60 }

tmnxIsisIPv6McastRoutingTopo    OBJECT-TYPE
    SYNTAX      TmnxIsisRoutingTopology
    MAX-ACCESS  read-write
    STATUS      current
    DESCRIPTION
        "The value of the object tmnxIsisIPv6McastRoutingTopo specifies which  
         multicast topology (MT) is enabled.
         
         If the value of tmnxIsisIPv6McastRoutingTopo is 'native' then MT 0 IPv6 
         topology is enabled and ISIS protocol will add routes to the multicast 
         RTM. 
         
         If the value of tmnxIsisIPv6McastRoutingTopo is 'mt' then MT 4 
         IPv6 topology is enabled and routes will be added to the multicast RTM.
         
         If the value of tmnxIsisIPv6McastRoutingTopo is 'none' then nothing is 
         added to the multicast RTM."
    DEFVAL { native } 
    ::= { tmnxIsisEntry 61 }

tmnxIsisMultiTopoIPv4Mcast OBJECT-TYPE
    SYNTAX      TruthValue
    MAX-ACCESS  read-write
    STATUS      current
    DESCRIPTION
        "The value of the object tmnxIsisMultiTopoIPv4Mcast specifies whether 
         IPv4 multicast for ISIS multi topology is enabled or not. 

         To enable IPv4 multicast on ISIS, tmnxIsisMultiTopology should
         be set to 'true'."
    DEFVAL { false }
    ::= { tmnxIsisEntry 62 }

tmnxIsisMultiTopoIPv6Mcast OBJECT-TYPE
    SYNTAX      TruthValue
    MAX-ACCESS  read-write
    STATUS      current
    DESCRIPTION
        "The value of the object tmnxIsisMultiTopoIPv6Mcast specifies whether 
         IPv6 multicast for ISIS multi topology is enabled or not. 

         To enable IPv6 multicast on ISIS, tmnxIsisMultiTopology should
         be set to 'true'."
    DEFVAL { false }
    ::= { tmnxIsisEntry 63 }


tmnxIsisOverloadMaxMetric OBJECT-TYPE
    SYNTAX      TruthValue
    MAX-ACCESS  read-write
    STATUS      current
    DESCRIPTION
        "The value of the object tmnxIsisOverloadMaxMetric specifies whether 
         max-metric is enabled or disabled for this instance of IS-IS on the router. 

         If the value of tmnxIsisOverloadMaxMetric set to 'true', the SR-OS 
         router would not set the overload bit but would instead set all transit
         links to the maximum value of '0xFFFF'."
    DEFVAL { false }
   ::= { tmnxIsisEntry 64 }

tmnxIsisOverloadOnBootMaxMetric OBJECT-TYPE
    SYNTAX      TruthValue
    MAX-ACCESS  read-write
    STATUS      current
    DESCRIPTION
        "The value of the object tmnxIsisOverloadOnBootMaxMetric specifies whether 
         max-metric is enabled or disabled for this instance of IS-IS on the router. 

         If the value of tmnxIsisOverloadOnBootMaxMetric set to 'true', the SR-OS 
         router would not set the overload bit but would instead set all transit
         links to the maximum value of '0xFFFF'."
    DEFVAL { false }
   ::= { tmnxIsisEntry 65 }

tmnxIsisRouterId    OBJECT-TYPE
    SYNTAX      Unsigned32
    MAX-ACCESS  read-write
    STATUS      current
    DESCRIPTION
        "The value of the object tmnxIsisRouterId specifies a 32-bit integer 
         uniquely identifying the router in the Autonomous System."
    DEFVAL { 0 }
::= { tmnxIsisEntry 66 }

tmnxIsisAdvRtrCapability  OBJECT-TYPE
    SYNTAX      INTEGER {
                    disable(0),
                    area(2),
                    as(3)
                }
    MAX-ACCESS  read-write
    STATUS      current
    DESCRIPTION      
        "The value of the object tmnxIsisAdvRtrCapability specifies the ISIS
         advertise router capabilities." 
    DEFVAL { disable }
::= { tmnxIsisEntry 67 }

tmnxIsisHelloPadding  OBJECT-TYPE
    SYNTAX      INTEGER {
                    disable(0),
                    adaptive(1),
                    loose(2),
                    strict(3)
                }
    MAX-ACCESS  read-write
    STATUS      current
    DESCRIPTION 
        "The value of the object tmnxIsisHelloPadding specifies whether
        padding should be configured on the ISIS hello packets.
        
        If the value of tmnxIsisHelloPadding is set to disable,
        the padding is disabled on all types of interfaces for all
        adjacency states.
        
        If the value of tmnxIsisHelloPadding is set to adaptive,
        the padding is configured untill the state of the neighbor
        adjacency is up.
        
        If the value of tmnxIsisHelloPadding is set to loose,
        the padding is configured untill the state of the neighbor
        adjacency is initialized.
        
        If the value of tmnxIsisHelloPadding is set to strict,
        the padding is configured for all adjacency states."        
    DEFVAL { disable }
::= { tmnxIsisEntry 68 }

tmnxIsisLspRefreshInterval     OBJECT-TYPE
    SYNTAX      Unsigned32 (150..65535)
    UNITS       "seconds"
    MAX-ACCESS  read-write
    STATUS      current
    DESCRIPTION
        "The value of the object tmnxIsisLspRefreshInterval specifies the  
         interval, in seconds, at which LSPs are refreshed.  
     
         To be able to refresh LSPs before they time out, the 
         tmnxIsisLspRefreshInterval must be set to a value less than
         the value set for tmnxIsisLspLifetime."
    DEFVAL { 600 }
    ::= { tmnxIsisEntry 69 }

tmnxIsisOperRouterId    OBJECT-TYPE
    SYNTAX      Unsigned32
    MAX-ACCESS  read-only
    STATUS      current
    DESCRIPTION
        "The value of tmnxIsisOperRouterId indicates a 32-bit integer uniquely
         identifying the router in the Autonomous System."
::= { tmnxIsisEntry 70 }

tmnxIsisAuthKeyChain  OBJECT-TYPE
    SYNTAX      TNamedItemOrEmpty
    MAX-ACCESS  read-write
    STATUS      current
    DESCRIPTION
        "The value of tmnxIsisAuthKeyChain specifies the keychain to use
         to sign and/or authenticate the IS-IS instance.

         The keychain name is defined by tmnxKeyChainName and is the index for
         TIMETRA-SECURITY-MIB::tmnxKeyChainTable"
    DEFVAL { ''H }
    ::= { tmnxIsisEntry 71 }

tmnxIsisIgnoreLspErrors OBJECT-TYPE
    SYNTAX      TruthValue
    MAX-ACCESS  read-write
    STATUS      current
    DESCRIPTION
        "The value of the object tmnxIsisIgnoreLspErrors specifies whether 
         checksum errors are ignored or not.
         
         If the value of tmnxIsisIgnoreLspErrors is set to 'false'
         lsp packets (CSNP/PSNP) with checksum errors will purge the
         corresponding lsp entry in the database; 
         if the value is set to 'true', the packet will get discarded."
    DEFVAL { false }
   ::= { tmnxIsisEntry 72 }

-- --------------------------------------------------------
--  tmnxIsisLevelTable
-- --------------------------------------------------------

tmnxIsisLevelTable    OBJECT-TYPE
    SYNTAX      SEQUENCE OF TmnxIsisLevelEntry
    MAX-ACCESS  not-accessible
    STATUS      current
    DESCRIPTION
        "The tmnxIsisLevelTable provides attributes to be applied on a specific
         IS-IS protocol level."
    ::= { tmnxIsisSystemObjs 2 }

tmnxIsisLevelEntry    OBJECT-TYPE
    SYNTAX      TmnxIsisLevelEntry
    MAX-ACCESS  not-accessible
    STATUS      current
    DESCRIPTION
        "Each row entry in the tmnxIsisLevelTable represents IS-IS level
         default global attributes to be used with interfaces belonging to
         a specific IS-IS protocol instance on a specific
         router instance.  The rows in this table cannot be created nor
         destroyed by SNMP SET requests.  There are always two rows in this
         table that are created by the agent with default values upon system
         initialization."
    INDEX { vRtrID, isisSysInstance, tmnxIsisLevel }
    ::= { tmnxIsisLevelTable 1 }

TmnxIsisLevelEntry ::=
    SEQUENCE {
        tmnxIsisLevel                    INTEGER,
        tmnxIsisLevelAuthKey             OCTET STRING,
        tmnxIsisLevelAuthType            INTEGER,
        tmnxIsisLevelExtPreference       Unsigned32,
        tmnxIsisLevelPreference          Unsigned32,
        tmnxIsisLevelWideMetricsOnly     TruthValue,
        tmnxIsisLevelOverloadStatus      INTEGER,
        tmnxIsisLevelOverloadTimeLeft    TimeInterval,
        tmnxIsisLevelNumLSPs             Unsigned32,
        tmnxIsisLevelCsnpAuthentication  TruthValue,
        tmnxIsisLevelHelloAuthentication TruthValue,
        tmnxIsisLevelPsnpAuthentication  TruthValue,
        tmnxIsisLevelDefMetric           Unsigned32,
        tmnxIsisLevelIPv6DefMetric       Unsigned32,
        tmnxIsisLevelLoopfreeAltExclude  TruthValue,
        tmnxIsisLevelSpbBridgePriority   Unsigned32,
        tmnxIsisLevelSpbForwardTreeTopo  Unsigned32,
        tmnxIsisLevelDefIPv4McastMetric  Unsigned32,
        tmnxIsisLevelDefIPv6McastMetric  Unsigned32,
        tmnxIsisLevelAdvRtrCapability    TruthValue,
        tmnxIsisLevelAuthKeyChain        TNamedItemOrEmpty
        }

tmnxIsisLevel                OBJECT-TYPE
    SYNTAX      INTEGER {
                    level1 (1),
                    level2 (2)
                }
    MAX-ACCESS  not-accessible
    STATUS      current
    DESCRIPTION
        "The value of the object tmnxIsisLevel specifies the 
         IS-IS protocol level to which these row attributes are 
         applied."
    ::= { tmnxIsisLevelEntry 1 }

tmnxIsisLevelAuthKey     OBJECT-TYPE
    SYNTAX      OCTET STRING (SIZE(0..254))
    MAX-ACCESS  read-write
    STATUS      current
    DESCRIPTION
        "The value of the object tmnxIsisLevelAuthKey specifies the 
         authentication key string used to verify the authenticity of packets
         sent by neighboring routers on an IS-IS interface at this level.
         
         For authentication to succeed both the authentication key and the 
         authentication type defined by the tmnxIsisLevelAuthType variable 
         must match.  
         
         If tmnxIsisLevelAuthType is set to 'password', 
         tmnxIsisLevelAuthKey can include any ASCII character.

         When read, tmnxIsisLevelAuthKey always returns an Octet String 
         of length zero."
    DEFVAL { ''H }   
    ::= { tmnxIsisLevelEntry 2 }

tmnxIsisLevelAuthType        OBJECT-TYPE
    SYNTAX      INTEGER {
                    none (1),
                    password (2),
                    md5 (3)
                }
    MAX-ACCESS  read-write
    STATUS      current
    DESCRIPTION
        "The value of the object tmnxIsisLevelAuthType specifies the method of
         authentication used to verify the authenticity of packets sent
         by neighboring routers on an IS-IS interface at this level.  
         
         For authentication to succeed both the authentication key defined in
         the tmnxIsisLevelAuthKey variable and the authentication type
         must match."
    DEFVAL { none }
    ::= { tmnxIsisLevelEntry 3 }

tmnxIsisLevelExtPreference   OBJECT-TYPE
    SYNTAX      Unsigned32 (1..255)
    MAX-ACCESS  read-write
    STATUS      current
    DESCRIPTION
        "The value of the object tmnxIsisLevelExtPreference specifies the 
         preference level to be used with external routes at this IS-IS level.
         
         A route can be learned from different routing protocols supported
         in the system, in which case their costs are not comparable.  In
         this case the preference value is used to decide which route to
         use.

         The initial default external preference value for IS-IS level 1
         is 160.  The initial default external preference value for IS-IS
         level 2 is 165."
    ::= { tmnxIsisLevelEntry 4 }

tmnxIsisLevelPreference      OBJECT-TYPE
    SYNTAX      Unsigned32 (1..255)
    MAX-ACCESS  read-write
    STATUS      current
    DESCRIPTION
        "The value of the object tmnxIsisLevelPreference specifies the 
         preference level to be used with internal routes at this IS-IS level.
         
         A route can be learned from different routing protocols supported
         in the system, in which case their costs are not comparable.  In
         this case the preference value is used to decide which route to
         use.

         The initial default internal preference value for IS-IS level 1
         is 15.  The initial default internal preference value for IS-IS
         level 2 is 18."
    ::= { tmnxIsisLevelEntry 5 }

tmnxIsisLevelWideMetricsOnly OBJECT-TYPE
    SYNTAX      TruthValue
    MAX-ACCESS  read-write
    STATUS      current
    DESCRIPTION
        "The value of the object tmnxIsisLevelWideMetricsOnly specifies whether
         only the wide metric pair of TLV's is generated.
         
         IS-IS metrics can have values between 1 and 63, referred to as
         small metrics.  IS-IS generates two TLVs: one for the adjacency
         and one for the IP prefix.  In order to support traffic
         engineering, wider metrics are required; a second pair of TLV's
         are also generated.

         When tmnxIsisLevelWideMetricsOnly has a value of 'false', both
         the small and wide metric pairs of TLV's are generated.

         When tmnxIsisLevelWideMetricsOnly has a value of 'true', only
         the wide metric pair of TLV's is generated."
    DEFVAL { false }
    ::= { tmnxIsisLevelEntry 6 }

tmnxIsisLevelOverloadStatus  OBJECT-TYPE
    SYNTAX      INTEGER {
                    notInOverload (1),
                    dynamic (2),
                    manual (3),
                    manualOnBoot (4),
                    singleSfm (5)
                }
    MAX-ACCESS  read-only
    STATUS      current
    DESCRIPTION
        "The value of the object tmnxIsisLevelOverloadStatus indicates whether  
         or not this level is in overload state.  
         
         When tmnxIsisLevelOverloadStatus has the value 'notInOverload', the 
         IS-IS level is normal state.  
         
         When tmnxIsisLevelOverloadStatus has the value 'dynamic', the level 
         is in the overload state because of insufficient memory to add additional
         entries to the IS-IS database for this level.  
         
         When tmnxIsisLevelOverloadStatus has the value 'manual', the level
         has been put into the overload state administratively as a result
         of the isisSysSetOverload object in the ISIS-MIB having been set.
         
         When tmnxIsisLevelOverloadStatus has the value 'singleSfm', this level 
         is in overload because there is only a signle SFM functioning, while the 
         value of the object TIMETRA-VRTR-MIB::vRtrSingleSfmOverloadAdminState is  
         equal to 'inService' for this router instance."
   ::= { tmnxIsisLevelEntry 7 }

tmnxIsisLevelOverloadTimeLeft OBJECT-TYPE
    SYNTAX      TimeInterval
    MAX-ACCESS  read-only
    STATUS      current
    DESCRIPTION
        "The value of the object tmnxIsisLevelOverloadTimeLeft indicates the 
         remaining time, measured in units of 0.01 seconds, before this level
         will attempt to enter its normal state.

         If tmnxIsisLevelOverloadStatus has a value of 'notInOverload',
         then a read of tmnxIsisLevelOverloadTimeLeft returns zero (0)."
   ::= { tmnxIsisLevelEntry 8 }

tmnxIsisLevelNumLSPs         OBJECT-TYPE
    SYNTAX      Unsigned32
    MAX-ACCESS  read-only
    STATUS      current
    DESCRIPTION
        "The value of the object tmnxIsisLevelNumLSPs indicates the 
         number of LSPs existing in the system for the particular level."
   ::= { tmnxIsisLevelEntry 9 }

tmnxIsisLevelCsnpAuthentication        OBJECT-TYPE
    SYNTAX      TruthValue
    MAX-ACCESS  read-write
    STATUS      current
    DESCRIPTION
        "The value of the object tmnxIsisLevelCsnpAuthentication specifies 
         whether authentication of CSNP packets at this level is enabled or not.
         
         When tmnxIsisLevelCsnpAuthentication has a value of 'true', 
         authentication of individual ISIS packets of CSNP type at this 
         level is enabled.   

         When tmnxIsisLevelCsnpAuthentication has a value of 'false',
         authentication of CSNP packets at this level is suppressed."
    DEFVAL { true }
    ::= { tmnxIsisLevelEntry 10 }

tmnxIsisLevelHelloAuthentication OBJECT-TYPE
    SYNTAX      TruthValue
    MAX-ACCESS  read-write
    STATUS      current
    DESCRIPTION
        "The value of the object tmnxIsisLevelHelloAuthentication specifies 
         whether authentication of HELLO packets at this level is enabled or not.
         
         When tmnxIsisLevelHelloAuthentication has a value of 'true', 
         authentication of individual ISIS packets of HELLO type at this
         level is enabled. 

         When tmnxIsisLevelHelloAuthentication has a value of 'false',
         authentication of HELLO packets at this level is suppressed."
    DEFVAL { true }
    ::= { tmnxIsisLevelEntry 11 }

tmnxIsisLevelPsnpAuthentication  OBJECT-TYPE
    SYNTAX      TruthValue
    MAX-ACCESS  read-write
    STATUS      current
    DESCRIPTION
        "The value of the object tmnxIsisLevelPsnpAuthentication specifies 
         whether authentication of PSNP packets at this level is enabled or not.
         
         When tmnxIsisLevelPsnpAuthentication has a value of 'true', 
         authentication of individual ISIS packets of PSNP type at this 
         level is enabled. 

         When tmnxIsisLevelPsnpAuthentication has a value of 'false',
         authentication of PSNP packets at this level is suppressed."
    DEFVAL { true }
    ::= { tmnxIsisLevelEntry 12 }

tmnxIsisLevelDefMetric       OBJECT-TYPE
    SYNTAX      Unsigned32(0..16777215)
    MAX-ACCESS  read-write
    STATUS      current
    DESCRIPTION
        "The value of the object tmnxIsisLevelDefMetric specifies the  
         configurable default metric used for all IS-IS interfaces on
         this level.

         The value of tmnxIsisLevelDefMetric will not be used if 
         tmnxIsisIfLevelAdminMetric is configured for an interface."
    DEFVAL { 10 }
    ::= { tmnxIsisLevelEntry 13 }

tmnxIsisLevelIPv6DefMetric  OBJECT-TYPE
    SYNTAX      Unsigned32(0..16777215)
    MAX-ACCESS  read-write
    STATUS      current
    DESCRIPTION
        "The value of the object tmnxIsisLevelIPv6DefMetric specifies the 
         configurable default metric used for all IS-IS interfaces 
         on this level for IPv6.
             
         The value of tmnxIsisLevelIPv6DefMetric will not be used if 
         tmnxIsisIfLvlIPv6UcastAdmMet is configured for an interface."
    DEFVAL { 10 }
    ::= { tmnxIsisLevelEntry 14 }

tmnxIsisLevelLoopfreeAltExclude OBJECT-TYPE
    SYNTAX      TruthValue
    MAX-ACCESS  read-write
    STATUS      current
    DESCRIPTION
        "The value of the object tmnxIsisLevelLoopfreeAltExclude specifies whether
         or not the ISIS level should be excluded during LFA calculations.
      
         If the value is 'true', the ISIS level is excluded from LFA 
         calculations; if the value is 'false', the ISIS level is included 
         in LFA calculations.
         
         The value of tmnxIsisLevelLoopfreeAltExclude is only valid when 
         tmnxIsisLoopfreeAlternate has a value of 'true'."
    DEFVAL { false } 
    ::= { tmnxIsisLevelEntry 15 }
    
tmnxIsisLevelSpbBridgePriority   OBJECT-TYPE
    SYNTAX      Unsigned32
    MAX-ACCESS  read-only
    STATUS      current
    DESCRIPTION
        "The value of the object tmnxIsisLevelSpbBridgePriority indicates the
         bridge priority of the SPB instance on this IS-IS level."
    ::= { tmnxIsisLevelEntry 16 }
    
tmnxIsisLevelSpbForwardTreeTopo   OBJECT-TYPE
    SYNTAX      Unsigned32
    MAX-ACCESS  read-only
    STATUS      current
    DESCRIPTION
        "The value of the object tmnxIsisLevelSpbForwardTreeTopo indicates the
         forwarding tree topology of the SPB instance on this IS-IS level."
    ::= { tmnxIsisLevelEntry 17 }
        
tmnxIsisLevelDefIPv4McastMetric OBJECT-TYPE
    SYNTAX      Unsigned32(0..16777215)
    MAX-ACCESS  read-write
    STATUS      current
    DESCRIPTION
        "The value of the object tmnxIsisLevelDefIPv4McastMetric specifies the 
         configurable default IPv4 multicast metric used for all IS-IS 
         interfaces on this level."
    DEFVAL { 10 }
    ::= { tmnxIsisLevelEntry 18 }

tmnxIsisLevelDefIPv6McastMetric  OBJECT-TYPE
    SYNTAX      Unsigned32(0..16777215)
    MAX-ACCESS  read-write
    STATUS      current
    DESCRIPTION
        "The value of the object tmnxIsisLevelDefIPv6McastMetric specifies the 
         configurable default IPv6 multicast metric used for all IS-IS 
         interfaces on this level."
    DEFVAL { 10 }
    ::= { tmnxIsisLevelEntry 19 }

tmnxIsisLevelAdvRtrCapability      OBJECT-TYPE
    SYNTAX      TruthValue
    MAX-ACCESS  read-write
    STATUS      current
    DESCRIPTION
        "The value of the object tmnxIsisLevelAdvRtrCapability specifies
         wether or not advertise-router-capabilities are enabled at 
         IS-IS instance L1 or L2 level."
    DEFVAL { true }
    ::= { tmnxIsisLevelEntry 20 }

tmnxIsisLevelAuthKeyChain  OBJECT-TYPE
    SYNTAX      TNamedItemOrEmpty
    MAX-ACCESS  read-write
    STATUS      current
    DESCRIPTION
        "The value of tmnxIsisLevelAuthKeyChain specifies the keychain to use
         to sign and/or authenticate the IS-IS instance L1 or L2 level.

         The keychain name is defined by tmnxKeyChainName and is the index for
         TIMETRA-SECURITY-MIB::tmnxKeyChainTable"
    DEFVAL { ''H }
    ::= { tmnxIsisLevelEntry 21 }


-- --------------------------------------------------------
--  tmnxIsisStatsTable
-- --------------------------------------------------------

tmnxIsisStatsTable    OBJECT-TYPE
    SYNTAX      SEQUENCE OF TmnxIsisStatsEntry
    MAX-ACCESS  not-accessible
    STATUS      current
    DESCRIPTION
        "The tmnxIsisStatsTable provides statsistics for each instance of IS-IS
         protocol configured. There is a one-to-one dependent relationship
         between the tables tmnxIsisTable and tmnxIsisStatsTable."
    ::= { tmnxIsisSystemObjs 3 }

tmnxIsisStatsEntry    OBJECT-TYPE
    SYNTAX      TmnxIsisStatsEntry
    MAX-ACCESS  not-accessible
    STATUS      current
    DESCRIPTION
        "Each row entry in the tmnxIsisStatsTable stores statistics for an
         instance of IS-IS protocol configured."
    INDEX { vRtrID, isisSysInstance }
    ::= { tmnxIsisStatsTable 1 }

TmnxIsisStatsEntry ::=
    SEQUENCE {
        tmnxIsisStatsSpfRuns             Counter32,
        tmnxIsisStatsLSPRegenerations    Counter32,
        tmnxIsisStatsInitiatedPurges     Counter32,
        tmnxIsisStatsLSPRecd             Counter32,
        tmnxIsisStatsLSPDrop             Counter32,
        tmnxIsisStatsLSPSent             Counter32,
        tmnxIsisStatsLSPRetrans          Counter32,
        tmnxIsisStatsIIHRecd             Counter32,
        tmnxIsisStatsIIHDrop             Counter32,
        tmnxIsisStatsIIHSent             Counter32,
        tmnxIsisStatsIIHRetrans          Counter32,
        tmnxIsisStatsCSNPRecd            Counter32,
        tmnxIsisStatsCSNPDrop            Counter32,
        tmnxIsisStatsCSNPSent            Counter32,
        tmnxIsisStatsCSNPRetrans         Counter32,
        tmnxIsisStatsPSNPRecd            Counter32,
        tmnxIsisStatsPSNPDrop            Counter32,
        tmnxIsisStatsPSNPSent            Counter32,
        tmnxIsisStatsPSNPRetrans         Counter32,
        tmnxIsisStatsUnknownRecd         Counter32,
        tmnxIsisStatsUnknownDrop         Counter32,
        tmnxIsisStatsUnknownSent         Counter32,
        tmnxIsisStatsUnknownRetrans      Counter32,
        tmnxIsisStatsCSPFRequests        Counter32,
        tmnxIsisStatsCSPFDroppedRequests Counter32,
        tmnxIsisStatsCSPFPathsFound      Counter32,
        tmnxIsisStatsCSPFPathsNotFound   Counter32,
        tmnxIsisStatsLfaRuns             Counter32,
        tmnxIsisStatsPartSpfRuns         Counter32,
        tmnxIsisStatsPartSpfTimeStamp    TimeStamp
        }

tmnxIsisStatsSpfRuns OBJECT-TYPE
    SYNTAX       Counter32
    MAX-ACCESS   read-only
    STATUS       current
    DESCRIPTION
        "The value of the object tmnxIsisStatsSpfRuns indicates the number of 
         times shortest path first calculations have been made."
    ::= { tmnxIsisStatsEntry 1 }

tmnxIsisStatsLSPRegenerations OBJECT-TYPE
    SYNTAX       Counter32
    MAX-ACCESS   read-only
    STATUS       current
    DESCRIPTION
        "The value of the object tmnxIsisStatsLSPRegenerations indicates the 
         count of LSP regenerations."
    ::= { tmnxIsisStatsEntry 2 }

tmnxIsisStatsInitiatedPurges OBJECT-TYPE
    SYNTAX       Counter32
    MAX-ACCESS   read-only
    STATUS       current
    DESCRIPTION
        "The value of the object tmnxIsisStatsInitiatedPurges indicates the 
         number of times purges have been initiated."
    ::= { tmnxIsisStatsEntry 3 }

tmnxIsisStatsLSPRecd OBJECT-TYPE
    SYNTAX       Counter32
    MAX-ACCESS   read-only
    STATUS       current
    DESCRIPTION
        "The value of the object tmnxIsisStatsLSPRecd indicates the 
         count of link state PDUs received by this instance of the
         protocol is maintained by tmnxIsisStatsLSPRecd."
    ::= { tmnxIsisStatsEntry 4 }

tmnxIsisStatsLSPDrop OBJECT-TYPE
    SYNTAX       Counter32
    MAX-ACCESS   read-only
    STATUS       current
    DESCRIPTION
        "The value of the object tmnxIsisStatsLSPDrop indicates the 
         count of link state PDUs dropped by this instance of the
         protocol is maintained by tmnxIsisStatsLSPDrop."
    ::= { tmnxIsisStatsEntry 5 }

tmnxIsisStatsLSPSent OBJECT-TYPE
    SYNTAX       Counter32
    MAX-ACCESS   read-only
    STATUS       current
    DESCRIPTION
        "The value of the object tmnxIsisStatsLSPSent indicates the
         count of link state PDUs sent out by this instance of the
         protocol is maintained by tmnxIsisStatsLSPSent."
    ::= { tmnxIsisStatsEntry 6 }

tmnxIsisStatsLSPRetrans OBJECT-TYPE
    SYNTAX       Counter32
    MAX-ACCESS   read-only
    STATUS       current
    DESCRIPTION
        "The value of the object tmnxIsisStatsLSPRetrans indicates the
         count of link state PDUs that had to be retransmitted by this
         instance of the protocol is maintained by tmnxIsisStatsLSPRetrans."
    ::= { tmnxIsisStatsEntry 7 }

tmnxIsisStatsIIHRecd OBJECT-TYPE
    SYNTAX       Counter32
    MAX-ACCESS   read-only
    STATUS       current
    DESCRIPTION
        "The value of the object tmnxIsisStatsIIHRecd indicates the
         count of link state PDUs received by this instance of the
         protocol is maintained by tmnxIsisStatsIIHRecd."
    ::= { tmnxIsisStatsEntry 8 }

tmnxIsisStatsIIHDrop OBJECT-TYPE
    SYNTAX       Counter32
    MAX-ACCESS   read-only
    STATUS       current
    DESCRIPTION
        "The value of the object tmnxIsisStatsIIHDrop indicates the
         count of link state PDUs dropped by this instance of the
         protocol is maintained by tmnxIsisStatsIIHDrop."
    ::= { tmnxIsisStatsEntry 9 }

tmnxIsisStatsIIHSent OBJECT-TYPE
    SYNTAX       Counter32
    MAX-ACCESS   read-only
    STATUS       current
    DESCRIPTION
        "The value of the object tmnxIsisStatsIIHSent indicates the
         count of link state PDUs sent out by this instance of the
         protocol is maintained by tmnxIsisStatsIIHSent."
    ::= { tmnxIsisStatsEntry 10 }

tmnxIsisStatsIIHRetrans OBJECT-TYPE
    SYNTAX       Counter32
    MAX-ACCESS   read-only
    STATUS       current
    DESCRIPTION
        "The value of the object tmnxIsisStatsIIHRetrans indicates the
         count of link state PDUs that had to be retransmitted by this
         instance of the protocol is maintained by tmnxIsisStatsIIHRetrans."
    ::= { tmnxIsisStatsEntry 11 }

tmnxIsisStatsCSNPRecd OBJECT-TYPE
    SYNTAX       Counter32
    MAX-ACCESS   read-only
    STATUS       current
    DESCRIPTION
        "The value of the object tmnxIsisStatsCSNPRecd indicates the
         count of link state PDUs received by this instance of the
         protocol is maintained by tmnxIsisStatsCSNPRecd."
    ::= { tmnxIsisStatsEntry 12 }

tmnxIsisStatsCSNPDrop OBJECT-TYPE
    SYNTAX       Counter32
    MAX-ACCESS   read-only
    STATUS       current
    DESCRIPTION
        "The value of the object tmnxIsisStatsCSNPDrop indicates the
         count of link state PDUs dropped by this instance of the
         protocol is maintained by tmnxIsisStatsCSNPDrop."
    ::= { tmnxIsisStatsEntry 13 }

tmnxIsisStatsCSNPSent OBJECT-TYPE
    SYNTAX       Counter32
    MAX-ACCESS   read-only
    STATUS       current
    DESCRIPTION
        "The value of the object tmnxIsisStatsCSNPSent indicates the
         count of link state PDUs sent out by this instance of the
         protocol is maintained by tmnxIsisStatsCSNPSent."
    ::= { tmnxIsisStatsEntry 14 }

tmnxIsisStatsCSNPRetrans OBJECT-TYPE
    SYNTAX       Counter32
    MAX-ACCESS   read-only
    STATUS       current
    DESCRIPTION
        "The value of the object tmnxIsisStatsCSNPRetrans indicates the 
         count of link state PDUs that had to be retransmitted by this
         instance of the protocol is maintained by tmnxIsisStatsCSNPRetrans."
    ::= { tmnxIsisStatsEntry 15 }

tmnxIsisStatsPSNPRecd OBJECT-TYPE
    SYNTAX       Counter32
    MAX-ACCESS   read-only
    STATUS       current
    DESCRIPTION
        "The value of the object tmnxIsisStatsPSNPRecd indicates the
         count of link state PDUs received by this instance of the
         protocol is maintained by tmnxIsisStatsPSNPRecd."
    ::= { tmnxIsisStatsEntry 16 }

tmnxIsisStatsPSNPDrop OBJECT-TYPE
    SYNTAX       Counter32
    MAX-ACCESS   read-only
    STATUS       current
    DESCRIPTION
        "The value of the object tmnxIsisStatsPSNPDrop indicates the 
         count of link state PDUs dropped by this instance of the
         protocol is maintained by tmnxIsisStatsPSNPDrop."
    ::= { tmnxIsisStatsEntry 17 }

tmnxIsisStatsPSNPSent OBJECT-TYPE
    SYNTAX       Counter32
    MAX-ACCESS   read-only
    STATUS       current
    DESCRIPTION
        "The value of the object tmnxIsisStatsPSNPSent indicates the 
         count of link state PDUs sent out by this instance of the
         protocol is maintained by tmnxIsisStatsPSNPSent."
    ::= { tmnxIsisStatsEntry 18 }

tmnxIsisStatsPSNPRetrans OBJECT-TYPE
    SYNTAX       Counter32
    MAX-ACCESS   read-only
    STATUS       current
    DESCRIPTION
        "The value of the object tmnxIsisStatsPSNPRetrans indicates the 
         count of link state PDUs that had to be retransmitted by this
         instance of the protocol is maintained by tmnxIsisStatsPSNPRetrans."
    ::= { tmnxIsisStatsEntry 19 }

tmnxIsisStatsUnknownRecd OBJECT-TYPE
    SYNTAX       Counter32
    MAX-ACCESS   read-only
    STATUS       current
    DESCRIPTION
        "The value of the object tmnxIsisStatsUnknownRecd indicates the 
         count of link state PDUs received by this instance of the
         protocol is maintained by tmnxIsisStatsUnknownRecd."
    ::= { tmnxIsisStatsEntry 20 }

tmnxIsisStatsUnknownDrop OBJECT-TYPE
    SYNTAX       Counter32
    MAX-ACCESS   read-only
    STATUS       current
    DESCRIPTION
        "The value of the object tmnxIsisStatsUnknownDrop indicates the 
         count of link state PDUs dropped by this instance of the
         protocol is maintained by tmnxIsisStatsUnknownDrop."
    ::= { tmnxIsisStatsEntry 21 }

tmnxIsisStatsUnknownSent OBJECT-TYPE
    SYNTAX       Counter32
    MAX-ACCESS   read-only
    STATUS       current
    DESCRIPTION
        "The value of the object tmnxIsisStatsUnknownSent indicates the 
         count of link state PDUs sent out by this instance of the
         protocol is maintained by tmnxIsisStatsUnknownSent."
    ::= { tmnxIsisStatsEntry 22 }

tmnxIsisStatsUnknownRetrans OBJECT-TYPE
    SYNTAX       Counter32
    MAX-ACCESS   read-only
    STATUS       current
    DESCRIPTION
        "The value of the object tmnxIsisStatsUnknownRetrans indicates the 
         count of link state PDUs that had to be retransmitted by this
         instance of the protocol is maintained by tmnxIsisStatsUnknownRetrans."
    ::= { tmnxIsisStatsEntry 23 }

tmnxIsisStatsCSPFRequests OBJECT-TYPE
    SYNTAX       Counter32
    MAX-ACCESS   read-only
    STATUS       current
    DESCRIPTION
        "The value of the object tmnxIsisStatsCSPFRequests indicates the 
         number of CSPF requests made to the protocol."
    ::= { tmnxIsisStatsEntry 24 }

tmnxIsisStatsCSPFDroppedRequests OBJECT-TYPE
    SYNTAX       Counter32
    MAX-ACCESS   read-only
    STATUS       current
    DESCRIPTION
        "The value of the object tmnxIsisStatsCSPFDroppedRequests indicates the 
         number of dropped CSPF requests by the protocol."
    ::= { tmnxIsisStatsEntry 25 }

tmnxIsisStatsCSPFPathsFound OBJECT-TYPE
    SYNTAX       Counter32
    MAX-ACCESS   read-only
    STATUS       current
    DESCRIPTION
        "The value of the object tmnxIsisStatsCSPFPathsFound indicates the 
         number of responses to CSPF requests for which paths satisfying
         the constraints were found."
    ::= { tmnxIsisStatsEntry 26 }

tmnxIsisStatsCSPFPathsNotFound OBJECT-TYPE
    SYNTAX       Counter32
    MAX-ACCESS   read-only
    STATUS       current
    DESCRIPTION
        "The value of the object tmnxIsisStatsCSPFPathsFound indicates the
         number of responses to CSPF requests for which no paths satisfying
         the constraints were found."
    ::= { tmnxIsisStatsEntry 27 }

tmnxIsisStatsLfaRuns OBJECT-TYPE
    SYNTAX       Counter32
    MAX-ACCESS   read-only
    STATUS       current
    DESCRIPTION
        "The value of the object tmnxIsisStatsLfaRuns indicates the 
         number of times loopfree-alternate calculations have been made."
    ::= { tmnxIsisStatsEntry 28 }

tmnxIsisStatsPartSpfRuns OBJECT-TYPE
    SYNTAX       Counter32
    MAX-ACCESS   read-only
    STATUS       current
    DESCRIPTION
        "The value of the object tmnxIsisStatsPartSpfRuns indicates the 
         number of times Partial SPF calculations have been made."
    ::= { tmnxIsisStatsEntry 29 }

tmnxIsisStatsPartSpfTimeStamp OBJECT-TYPE
    SYNTAX       TimeStamp
    MAX-ACCESS   read-only
    STATUS       current
    DESCRIPTION
        "The value of the object tmnxIsisStatsPartSpfTimeStamp indicates the 
         timestamp when the last Partial SPF was calculated."
    ::= { tmnxIsisStatsEntry 30 }

-- --------------------------------------------------------
--  tmnxIsisHostTable
-- --------------------------------------------------------

tmnxIsisHostTable    OBJECT-TYPE
    SYNTAX      SEQUENCE OF TmnxIsisHostEntry
    MAX-ACCESS  not-accessible
    STATUS      current
    DESCRIPTION
        "The tmnxIsisHostTable provides the mapping of a system-id for an
         IS to the hostname as provided by the system.
         This table may not have mapping of all system-id to hostname as it is
         not mandatory to exchange hostnames."
    ::= { tmnxIsisSystemObjs 4 }

tmnxIsisHostEntry    OBJECT-TYPE
    SYNTAX      TmnxIsisHostEntry
    MAX-ACCESS  not-accessible
    STATUS      current
    DESCRIPTION
        "Each row entry in the tmnxIsisHostTable stores the mapping of a
         system-id to a hostname."
    INDEX { vRtrID, isisSysInstance, tmnxIsisHostSysID }
    ::= { tmnxIsisHostTable 1 }

TmnxIsisHostEntry ::=
    SEQUENCE {
        tmnxIsisHostSysID          SystemID,
        tmnxIsisHostName           DisplayString
        }

tmnxIsisHostSysID OBJECT-TYPE
    SYNTAX       SystemID
    MAX-ACCESS   not-accessible
    STATUS       current
    DESCRIPTION
        "The value of the object tmnxIsisHostSysID specifies the system-id
         for which we map the hostname in the object tmnxIsisHostName."
    ::= { tmnxIsisHostEntry 1 }

tmnxIsisHostName OBJECT-TYPE
    SYNTAX       DisplayString
    MAX-ACCESS   read-only
    STATUS       current
    DESCRIPTION
        "The value of the object tmnxIsisHostName indicates the 
         mapping hostname for the corresponding system-id."
    ::= { tmnxIsisHostEntry 2 }

-- --------------------------------------------------------
-- tmnxIsisRouteTable
-- --------------------------------------------------------

tmnxIsisRouteTable    OBJECT-TYPE
    SYNTAX      SEQUENCE OF TmnxIsisRouteEntry
    MAX-ACCESS  not-accessible
    STATUS      current
    DESCRIPTION
        "The tmnxIsisRouteTable maintains the routes learned by an
         instance of IS-IS protocol for a specific multi topology id."
    ::= { tmnxIsisSystemObjs 5 }

tmnxIsisRouteEntry    OBJECT-TYPE
    SYNTAX      TmnxIsisRouteEntry
    MAX-ACCESS  not-accessible
    STATUS      current
    DESCRIPTION
        "Each row entry in the tmnxIsisRouteTable stores a route for a given
         instance of the IS-IS protocol for a specific multi topology id."
    INDEX { vRtrID,
            isisSysInstance,
            tmnxIsisRouteMtId,
            tmnxIsisRouteDestType,
            tmnxIsisRouteDest,
            tmnxIsisRoutePrefixLength,
            tmnxIsisRouteNexthopIPType,
            tmnxIsisRouteNexthopIP }
    ::= { tmnxIsisRouteTable 1 }

TmnxIsisRouteEntry ::=
    SEQUENCE {
            tmnxIsisRouteMtId                Unsigned32,
            tmnxIsisRouteDestType            InetAddressType,
            tmnxIsisRouteDest                InetAddress,
            tmnxIsisRoutePrefixLength        InetAddressPrefixLength,
            tmnxIsisRouteNexthopIPType       InetAddressType,
            tmnxIsisRouteNexthopIP           InetAddress,
            tmnxIsisRouteLevel               INTEGER,
            tmnxIsisRouteSpfRunNumber        Counter32,
            tmnxIsisRouteMetric              Unsigned32,
            tmnxIsisRouteType                INTEGER,
            tmnxIsisRouteNHopSysID           SystemID,
            tmnxIsisRouteTag                 Unsigned32,
            tmnxIsisRouteBkupFlags           INTEGER,
            tmnxIsisRouteBkupNextHopTy       INTEGER,
            tmnxIsisRouteBkupNextHopType     InetAddressType,
            tmnxIsisRouteBkupNextHop         InetAddress,
            tmnxIsisRouteBkupMetric          Unsigned32,
            tmnxIsisRouteNextHopType         TmnxInetCidrNextHopType,
            tmnxIsisRouteNextHopOwner        TmnxInetCidrNextHopOwner,
            tmnxIsisRouteNHOwnerAuxInfo      Unsigned32,
            tmnxIsisRouteBkupNHType          TmnxInetCidrNextHopType,
            tmnxIsisRouteBkupNHOwner         TmnxInetCidrNextHopOwner,
            tmnxIsisRouteBkupNHOwnAxInfo     Unsigned32            
           }

tmnxIsisRouteMtId OBJECT-TYPE
    SYNTAX       Unsigned32
    MAX-ACCESS   not-accessible
    STATUS       current
    DESCRIPTION
        "The value of the object tmnxIsisRouteMtId specifies the 
         multi topology id number for this route. 
         
         If multi-topology is not supported for the route then 
         the value of tmnxIsisRouteMtId should be 0."
    ::= { tmnxIsisRouteEntry 1 }

tmnxIsisRouteDestType OBJECT-TYPE
    SYNTAX      InetAddressType
    MAX-ACCESS  not-accessible
    STATUS      current
    DESCRIPTION
        "The value of the object tmnxIsisRouteDestType specifies the IP 
         address type for tmnxIsisRouteDest."
    ::= { tmnxIsisRouteEntry 2 }

tmnxIsisRouteDest OBJECT-TYPE
    SYNTAX       InetAddress (SIZE(4|16|20))
    MAX-ACCESS   not-accessible
    STATUS       current
    DESCRIPTION
        "The value of the object tmnxIsisRouteDest specifies the 
         destination IP address of this route.
         
         The address type of tmnxIsisRouteDest is indicated by 
         tmnxIsisRouteDestType."
    ::= { tmnxIsisRouteEntry 3 }
    
tmnxIsisRoutePrefixLength OBJECT-TYPE
    SYNTAX       InetAddressPrefixLength
    MAX-ACCESS   not-accessible
    STATUS       current
    DESCRIPTION
        "The value of the object tmnxIsisRoutePrefixLength specifies the  
         prefix length to be used with tmnxIsisRouteDest to get the 
         network prefix."
    ::= { tmnxIsisRouteEntry 4 }
    
tmnxIsisRouteNexthopIPType OBJECT-TYPE
    SYNTAX      InetAddressType
    MAX-ACCESS  not-accessible
    STATUS      current
    DESCRIPTION
        "The value of the object tmnxIsisRouteNexthopIPType specifies the 
         IP address type for tmnxIsisRouteNexthopIP."
    ::= { tmnxIsisRouteEntry 5 }

tmnxIsisRouteNexthopIP OBJECT-TYPE
    SYNTAX       InetAddress (SIZE(4|16|20))
    MAX-ACCESS   not-accessible
    STATUS       current
    DESCRIPTION
        "The value of the object tmnxIsisRouteNexthopIP specifies the  
         IP address of the nexthop for this route. 
         
         The address type of tmnxIsisRouteNexthopIP is indicated by 
         tmnxIsisRouteNexthopIPType"
    ::= { tmnxIsisRouteEntry 6 }

tmnxIsisRouteLevel OBJECT-TYPE
    SYNTAX       INTEGER {
                    level1IS (1),
                    level2IS (2)
                   }
    MAX-ACCESS   read-only
    STATUS       current
    DESCRIPTION
        "The value of the object tmnxIsisRouteLevel indicates the IS-IS Level 
         at which the prefix was learned."
    ::= { tmnxIsisRouteEntry 7 }
    
tmnxIsisRouteSpfRunNumber OBJECT-TYPE
    SYNTAX       Counter32
    MAX-ACCESS   read-only
    STATUS       current
    DESCRIPTION
        "The value of the object tmnxIsisRouteSpfRunNumber indicates the
         run of spf calculation in which this route was selected."
    ::= { tmnxIsisRouteEntry 8 }

tmnxIsisRouteMetric OBJECT-TYPE
    SYNTAX       Unsigned32
    MAX-ACCESS   read-only
    STATUS       current
    DESCRIPTION
        "The value of the object tmnxIsisRouteMetric indicates the metric value 
         associated with the route. 
         
         This metric is obtained by the SPF calculations and is used by the  
         instance of the protocol. 
         
         For a given destination prefix, the route with the lower metric is the
         shorter route."
    ::= { tmnxIsisRouteEntry 9 }

tmnxIsisRouteType OBJECT-TYPE
    SYNTAX       INTEGER {
                    internal(1),
                    external(2)
                   }
    MAX-ACCESS   read-only
    STATUS       current
    DESCRIPTION
        "The value of the object tmnxIsisRouteType indicates the 
         type of route represented by this row entry."
    ::= { tmnxIsisRouteEntry 10 }

tmnxIsisRouteNHopSysID OBJECT-TYPE
    SYNTAX       SystemID
    MAX-ACCESS   read-only
    STATUS       current
    DESCRIPTION
        "The value of the object tmnxIsisRouteNHopSysID indicates the 
         system-id of the nexthop IS through which this route is reachable."
    ::= { tmnxIsisRouteEntry 11 }

tmnxIsisRouteTag  OBJECT-TYPE
    SYNTAX      Unsigned32
    MAX-ACCESS  read-only
    STATUS      current
    DESCRIPTION
        "The value of the object tmnxIsisRouteTag indicates a 
         32-bit integer route tag for this route. 
         
         A value of 0 indicates that the tag has not been set."
    ::= { tmnxIsisRouteEntry 12 }

tmnxIsisRouteBkupFlags   OBJECT-TYPE
    SYNTAX     INTEGER {
                    none       (0), -- next-hop not specified
                    hasLfa     (1)  -- next-hop has loop-free-alternate (LFA)
                 }
    MAX-ACCESS read-only
    STATUS     current
    DESCRIPTION
        "The value of the object tmnxIsisRouteBkupFlags indicates the presence  
         or absence of LFA next-hops.

         The value 'none'  indicates that no next-hop is present;         
         the value 'hasLfa' indicates that an LFA next-hop is present in addition  
         to the regular next-hop."
    ::= { tmnxIsisRouteEntry 13 }

tmnxIsisRouteBkupNextHopTy OBJECT-TYPE
    SYNTAX     INTEGER {
                    notApplicable        (0),
                    nodeProtection       (1), 
                    linkProtection       (2)  
                 }
    MAX-ACCESS read-only
    STATUS      current
    DESCRIPTION
        "The value of the object tmnxIsisRouteBkupNextHopTy indicates the  
         type of protection used by the backup next-hop.

         The value 'notApplicable' indicates that the backup next-hop type
         is not applicable;
         the value 'nodeProtection' indicates that the backup next-hop uses a
         node-protection mechanism; 
         the value 'linkProtection' indicates that the backup next-hop uses 
         link-protection mechanism."
    ::= { tmnxIsisRouteEntry 14 }
    
tmnxIsisRouteBkupNextHopType  OBJECT-TYPE
    SYNTAX      InetAddressType
    MAX-ACCESS  read-only
    STATUS      current
    DESCRIPTION
        "The value of the object tmnxIsisRouteBkupNextHopType specifies the 
         IP address type for tmnxIsisRouteBkupNextHop."
    ::= { tmnxIsisRouteEntry 15 }
    
tmnxIsisRouteBkupNextHop OBJECT-TYPE
    SYNTAX      InetAddress(SIZE(0|4|16|20))
    MAX-ACCESS  read-only
    STATUS      current
    DESCRIPTION
        "The value of the object tmnxIsisRouteBkupNextHop indicates the 
         IP address of a backup next-hop.
         
         The value of tmnxIsisRouteBkupNextHop is only 
         valid when tmnxIsisRouteBkupFlags has a value of 'hasLfa'.

         The address type of tmnxIsisRouteBkupNextHop is indicated by the 
         value of tmnxIsisRouteBkupNextHopType."
    ::= { tmnxIsisRouteEntry 16 }

tmnxIsisRouteBkupMetric  OBJECT-TYPE
    SYNTAX      Unsigned32
    MAX-ACCESS  read-only
    STATUS      current
    DESCRIPTION
        "The value of the object tmnxIsisRouteBkupMetric indicates the 
         routing metric for a backup route. 
         
         The semantics of this metric are determined by the routing-protocol
         specified in the route's ipCidrRouteProto value. 
         
         The value of tmnxIsisRouteBkupMetric is only valid when 
         tmnxIsisRouteBkupFlags has a value of 'hasLfa'."
    ::= { tmnxIsisRouteEntry 17 }

tmnxIsisRouteNextHopType      OBJECT-TYPE
    SYNTAX      TmnxInetCidrNextHopType
    MAX-ACCESS  read-only
    STATUS      current
    DESCRIPTION
        "The value of the object tmnxIsisRouteNextHopType indicates the 
         type of next hop for this route."
    ::= { tmnxIsisRouteEntry 18 }

tmnxIsisRouteNextHopOwner      OBJECT-TYPE
    SYNTAX      TmnxInetCidrNextHopOwner
    MAX-ACCESS  read-only
    STATUS      current
    DESCRIPTION
        "The value of the object tmnxIsisRouteNextHopOwner indicates the owner of  
         next hop for this route."
    ::= { tmnxIsisRouteEntry 19 }

tmnxIsisRouteNHOwnerAuxInfo      OBJECT-TYPE
    SYNTAX      Unsigned32
    MAX-ACCESS  read-only
    STATUS      current
    DESCRIPTION
        "The value of the object tmnxIsisRouteNHOwnerAuxInfo indicates the 
         auxiliary information for next hop owner as indicated by 
         tmnxIsisRouteNextHopOwner.
         
         The value of tmnxIsisRouteNHOwnerAuxInfo indicates the tunnel-id 
         existing for this next hop type and owner."
    ::= { tmnxIsisRouteEntry 20 }

tmnxIsisRouteBkupNHType      OBJECT-TYPE
    SYNTAX      TmnxInetCidrNextHopType
    MAX-ACCESS  read-only
    STATUS      current
    DESCRIPTION
        "The value of the object tmnxIsisRouteBkupNHType indicates the  
         type of next hop for this backup route."
    ::= { tmnxIsisRouteEntry 21 }

tmnxIsisRouteBkupNHOwner      OBJECT-TYPE
    SYNTAX      TmnxInetCidrNextHopOwner
    MAX-ACCESS  read-only
    STATUS      current
    DESCRIPTION
        "The value of the object tmnxIsisRouteBkupNHOwner indicates the  
         owner of next hop for this backup route."
    ::= { tmnxIsisRouteEntry 22 }

tmnxIsisRouteBkupNHOwnAxInfo      OBJECT-TYPE
    SYNTAX      Unsigned32
    MAX-ACCESS  read-only
    STATUS      current
    DESCRIPTION
        "The value of the object tmnxIsisRouteBkupNHOwnAxInfo indicates the 
         auxiliary information, for next hop owner as indicated by 
         tmnxIsisRouteBkupNHOwner.
         
         The value of tmnxIsisRouteBkupNHOwnAxInfo indicates the tunnel-id 
         existing for this backup next hop type and owner."
    ::= { tmnxIsisRouteEntry 23 }

-- --------------------------------------------------------
-- tmnxIsisPathTable
-- --------------------------------------------------------

tmnxIsisPathTable    OBJECT-TYPE
    SYNTAX      SEQUENCE OF TmnxIsisPathEntry
    MAX-ACCESS  not-accessible
    STATUS      current
    DESCRIPTION
        "The tmnxIsisPathTable maintains information 
         regarding SPF calculation for each instance 
         of IS-IS protocol."
    ::= { tmnxIsisSystemObjs 6 }

tmnxIsisPathEntry    OBJECT-TYPE
    SYNTAX      TmnxIsisPathEntry
    MAX-ACCESS  not-accessible
    STATUS      current
    DESCRIPTION
        "Each row entry in the tmnxIsisPathTable represents
         the ISIS path for an instance, level, multi topology id,
         path identifier and the path outgoing interface."
    INDEX { vRtrID,
            isisSysInstance,
            tmnxIsisLevel,
            tmnxIsisPathMtID,
            tmnxIsisPathID,
            tmnxIsisPathIfIndex,
            tmnxIsisPathNHopSysID }
    ::= { tmnxIsisPathTable 1 }

TmnxIsisPathEntry ::=
    SEQUENCE {
            tmnxIsisPathMtID              Unsigned32,
            tmnxIsisPathID                OCTET STRING,
            tmnxIsisPathIfIndex           InterfaceIndex,
            tmnxIsisPathNHopSysID         SystemID,
            tmnxIsisPathMetric            Unsigned32,
            tmnxIsisPathSNPA              SNPAAddress,
            tmnxIsisPathLfaIfIndex        InterfaceIndex,
            tmnxIsisPathLfaNHop           SystemID,
            tmnxIsisPathLfaMetric         Unsigned32,
            tmnxIsisPathLfaType           INTEGER,
            tmnxIsisPathRouteType         INTEGER
            }

tmnxIsisPathMtID OBJECT-TYPE
    SYNTAX       Unsigned32
    MAX-ACCESS   not-accessible
    STATUS       current
    DESCRIPTION
        "The value of the object tmnxIsisPathMtID specifies the 
         multi-topology id number for the path. 
         
         If multi-topology is not supported for the path then
         the value of tmnxIsisPathMtID should be 0."
    ::= { tmnxIsisPathEntry 1 }

tmnxIsisPathID OBJECT-TYPE
    SYNTAX       OCTET STRING (SIZE(7))
    MAX-ACCESS   not-accessible
    STATUS       current
    DESCRIPTION
        "The value of the object tmnxIsisPathID specifies the path identifier 
         and has first 6 octets as the system-id followed by one octet 
         of the Lan-ID."
    ::= { tmnxIsisPathEntry 2 }

tmnxIsisPathIfIndex OBJECT-TYPE
    SYNTAX       InterfaceIndex
    MAX-ACCESS   not-accessible
    STATUS       current
    DESCRIPTION
        "The value of the object tmnxIsisPathIfIndex specifies the ifIndex 
         of the outgoing interface for the path."
    ::= { tmnxIsisPathEntry 3 }

tmnxIsisPathNHopSysID OBJECT-TYPE
    SYNTAX       SystemID
    MAX-ACCESS   not-accessible
    STATUS       current
    DESCRIPTION
        "The value of the object tmnxIsisPathNHopSysID specifies the 
         system-id of the nexthop and is used to reference the 
         nexthop for this route."
    ::= { tmnxIsisPathEntry 4 }

tmnxIsisPathMetric OBJECT-TYPE
    SYNTAX       Unsigned32
    MAX-ACCESS   read-only
    STATUS       current
    DESCRIPTION
        "The value of the object tmnxIsisPathMetric indicates the metric
         assigned to this path entry after SPF calculations. 
         
         The lower the metric value, the shorter is the path and hence more
         preferred by the protocol."
    ::= { tmnxIsisPathEntry 5 }

tmnxIsisPathSNPA OBJECT-TYPE
    SYNTAX       SNPAAddress
    MAX-ACCESS   read-only
    STATUS       current
    DESCRIPTION
        "The value of the object tmnxIsisPathSNPA indicates the subnet point 
         of attachment for this path."
    ::= { tmnxIsisPathEntry 6 }

tmnxIsisPathLfaIfIndex OBJECT-TYPE
    SYNTAX       InterfaceIndex
    MAX-ACCESS   read-only
    STATUS       current
    DESCRIPTION
        "The value of the object tmnxIsisPathLfaIfIndex indicates the 
         loopfree-alternate ifIndex of the outgoing interface for the path."
    ::= { tmnxIsisPathEntry 7 }

tmnxIsisPathLfaNHop OBJECT-TYPE
    SYNTAX       SystemID
    MAX-ACCESS   read-only
    STATUS       current
    DESCRIPTION
        "The value of the object tmnxIsisPathLfaNHop indicates the  
         loopfree-alternate nexthop and is referenced by the system-id."
    ::= { tmnxIsisPathEntry 8 }

tmnxIsisPathLfaMetric OBJECT-TYPE
    SYNTAX       Unsigned32
    MAX-ACCESS   read-only
    STATUS       current
    DESCRIPTION
        "The value of the object tmnxIsisPathLfaMetric indicates the metric  
         assigned to this entry which are a result of loopfree-alternate 
         calculations. 
         
         The lower the metric value, the shorter is the path and hence more 
         preferred by the protocol."
    ::= { tmnxIsisPathEntry 9 }

tmnxIsisPathLfaType OBJECT-TYPE
    SYNTAX       INTEGER {
                    none(0),
                    nodeLink(1),
                    pathLink(2)
                   }
    MAX-ACCESS   read-only
    STATUS       current
    DESCRIPTION
        "The value of the object tmnxIsisPathLfaType indicates the type of  
         route represented by this row entry."
    ::= { tmnxIsisPathEntry 10 }

tmnxIsisPathRouteType OBJECT-TYPE
    SYNTAX       INTEGER {
                    spf(0),       -- shortest path first
                    lfa(1)        -- loopfree-alternate
                   }
    MAX-ACCESS   read-only
    STATUS       current
    DESCRIPTION
        "The value of the object tmnxIsisPathRouteType indicates whether  
         a backup route exists for this row entry."
    ::= { tmnxIsisPathEntry 11 }

-- --------------------------------------------------------
-- tmnxIsisLSPTable
-- --------------------------------------------------------

tmnxIsisLSPTable    OBJECT-TYPE
    SYNTAX      SEQUENCE OF TmnxIsisLSPEntry
    MAX-ACCESS  not-accessible
    STATUS      current
    DESCRIPTION
        "The tmnxIsisLSPTable maintain information regarding all the LSPs
         in the LSP database of each instance of IS-IS protocol for a given
         level."
    ::= { tmnxIsisSystemObjs 7 }

tmnxIsisLSPEntry    OBJECT-TYPE
    SYNTAX      TmnxIsisLSPEntry
    MAX-ACCESS  not-accessible
    STATUS      current
    DESCRIPTION
        "Each row entry in the tmnxIsisLSPTable represents an LSP in the LSP
         database."
    INDEX { vRtrID,
            isisSysInstance,
            tmnxIsisLevel,
            tmnxIsisLSPId }
    ::= { tmnxIsisLSPTable 1 }

TmnxIsisLSPEntry ::=
    SEQUENCE {
            tmnxIsisLSPId               OCTET STRING,
            tmnxIsisLSPSeq              Counter32,
            tmnxIsisLSPChecksum         Integer32,
            tmnxIsisLSPLifetimeRemain   Integer32,
            tmnxIsisLSPVersion          Integer32,
            tmnxIsisLSPPktType          Integer32,
            tmnxIsisLSPPktVersion       Integer32,
            tmnxIsisLSPMaxArea          Integer32,
            tmnxIsisLSPSysIdLen         Integer32,
            tmnxIsisLSPAttributes       Integer32,
            tmnxIsisLSPUsedLen          Integer32,
            tmnxIsisLSPAllocLen         Integer32,
            tmnxIsisLSPBuff             OCTET STRING,
            tmnxIsisLSPZeroRLT          TruthValue
          }

tmnxIsisLSPId OBJECT-TYPE
    SYNTAX      OCTET STRING (SIZE(0..8))
    MAX-ACCESS  not-accessible
    STATUS      current
    DESCRIPTION
        "The value of the object tmnxIsisLSPId specifies the LSP Id and 
         is given in the format as 6 octets of adjacency system-id followed by
         1 octet Lan-ID and 1 octet LSP Number."
    ::= { tmnxIsisLSPEntry 1 }

tmnxIsisLSPSeq OBJECT-TYPE
    SYNTAX      Counter32
    MAX-ACCESS  read-only
    STATUS      current
    DESCRIPTION
        "The value of the object tmnxIsisLSPSeq indicates the sequence number of
         an LSP and is a four byte quantity that represents the version of an LSP.
         
         The higher the sequence number, the more up to date the information. 
         
         The sequence number is always incremented by the system that originated
         the LSP and ensures that there is only one version of that LSP in the 
         entire network."
    ::= { tmnxIsisLSPEntry 2 }

tmnxIsisLSPChecksum OBJECT-TYPE
    SYNTAX      Integer32 (0..65535)
    MAX-ACCESS  read-only
    STATUS      current
    DESCRIPTION
        "The value of the object tmnxIsisLSPChecksum indicates the checksum of
         contents of LSP from the SourceID field in the LSP till the end. 
         
         The checksum is computed using the Fletcher checksum algorithm. "
    ::= { tmnxIsisLSPEntry 3 }

tmnxIsisLSPLifetimeRemain OBJECT-TYPE
    SYNTAX      Integer32 (0..65535)
    UNITS       "seconds"
    MAX-ACCESS  read-only
    STATUS      current
    DESCRIPTION
        "The value of the object tmnxIsisLSPLifetimeRemain indicates the 
         Remaining lifetime of this LSP and is a decrementing counter that
         decrements in seconds starting from the value as received in the 
         LSP if not self-originated OR from tmnxIsisLspLifetime for self
         originated LSPs. 
         
         When the remaining lifetime becomes zero, the contents of the LSP 
         should not be considered for SPF calculation."
    ::= { tmnxIsisLSPEntry 4 }

tmnxIsisLSPVersion OBJECT-TYPE
    SYNTAX      Integer32
    MAX-ACCESS   read-only
    STATUS      current
    DESCRIPTION
        "The value of the object tmnxIsisLSPVersion indicates the version of
         the ISIS protocol that has generated the LSP"
    ::= { tmnxIsisLSPEntry 5 }

tmnxIsisLSPPktType OBJECT-TYPE
    SYNTAX      Integer32
    MAX-ACCESS  read-only
    STATUS      current
    DESCRIPTION
        "The value of the object tmnxIsisLSPPktType indicates the packet type
         for instance Hello PDUs, LSPs, CSNPs OR PSNPs at both IS-IS protocol
         levels i.e. L1 and L2 as maintained in tmnxIsisLSPPktType."
    ::= { tmnxIsisLSPEntry 6 }

tmnxIsisLSPPktVersion OBJECT-TYPE
    SYNTAX      Integer32
    MAX-ACCESS  read-only
    STATUS      current
    DESCRIPTION
        "The value of the object tmnxIsisLSPVersion indicates the version of 
         the ISIS protocol that has generated the Packet."
    ::= { tmnxIsisLSPEntry 7 }

tmnxIsisLSPMaxArea OBJECT-TYPE
    SYNTAX      Integer32
    MAX-ACCESS  read-only
    STATUS      current
    DESCRIPTION
        "The value of the object tmnxIsisLSPMaxArea indicates the maximum number
         of areas supported by the originator of the LSP. 
         
         A value of 0 for tmnxIsisLSPMaxArea indicates a default of 3 areas. "
    ::= { tmnxIsisLSPEntry 8 }

tmnxIsisLSPSysIdLen OBJECT-TYPE
    SYNTAX      Integer32
    MAX-ACCESS  read-only
    STATUS      current
    DESCRIPTION
        "The value of the object tmnxIsisLSPSysIdLen indicates the length of
         the system-id as used by the originator."
    ::= { tmnxIsisLSPEntry 9 }

tmnxIsisLSPAttributes OBJECT-TYPE
    SYNTAX      Integer32
    MAX-ACCESS  read-only
    STATUS      current
    DESCRIPTION
        "The value of the object tmnxIsisLSPAttributes indicates the attributes
         associated with the LSP and these include the attached bit,
         overload bit, IS type of the system originating the LSP and the
         partition repair capability. 
         
         The attached bit and the overload bit are of significance only when
         present in the LSP numbered zero and should be ignored on receipt in 
         any other LSP."
    ::= { tmnxIsisLSPEntry 10 }

tmnxIsisLSPUsedLen OBJECT-TYPE
    SYNTAX      Integer32
    MAX-ACCESS  read-only
    STATUS      current
    DESCRIPTION
        "The value of the object tmnxIsisLSPUsedLen indicates the used length
         for the LSP. 
         
         For an LSP that is not self originated, the used length is always equal
         to tmnxIsisLSPAllocLen; for self originated LSPs, the used length is 
         less than or equal to tmnxIsisLSPAllocLen."
    ::= { tmnxIsisLSPEntry 11 }

tmnxIsisLSPAllocLen OBJECT-TYPE
    SYNTAX      Integer32
    MAX-ACCESS  read-only
    STATUS      current
    DESCRIPTION
        "The value of the object tmnxIsisLSPAllocLen indicates the length
         allocated for the LSP to be stored."
    ::= { tmnxIsisLSPEntry 12 }

tmnxIsisLSPBuff OBJECT-TYPE
    SYNTAX      OCTET STRING (SIZE(27..9190))
    MAX-ACCESS  read-only
    STATUS      current
    DESCRIPTION
        "The value of the object tmnxIsisLSPBuff indicates the LSP as 
         existing in the LSP database."
    ::= { tmnxIsisLSPEntry 13 }

tmnxIsisLSPZeroRLT OBJECT-TYPE
    SYNTAX      TruthValue
    MAX-ACCESS  read-only
    STATUS      current
    DESCRIPTION
        "The value of the object tmnxIsisLSPZeroRLT indicates the LSP state if
         it has once reached zero remaining lifetime. 
         
         If this object is 'true' then the object tmnxIsisLSPLifetimeRemain will
         maintain the time remaining after which this LSP will be discarded."
    ::= { tmnxIsisLSPEntry 14 }

-- --------------------------------------------------------
-- tmnxIsisSpfLogTable
-- --------------------------------------------------------

tmnxIsisSpfLogTable    OBJECT-TYPE
    SYNTAX      SEQUENCE OF TmnxIsisSpfLogEntry
    MAX-ACCESS  not-accessible
    STATUS      current
    DESCRIPTION
        "The tmnxIsisSpfLogTable maintains information regarding SPF 
         runs for each instance of IS-IS protocol.
        
         There is a maximum of 20 log entries stored per IS-IS protocol
         instance."
    ::= { tmnxIsisSystemObjs 8 }

tmnxIsisSpfLogEntry    OBJECT-TYPE
    SYNTAX      TmnxIsisSpfLogEntry
    MAX-ACCESS  not-accessible
    STATUS      current
    DESCRIPTION 
        "Each entry maintains log information about a specific SPF run
        made on a particular IS-IS protocol instance."
    INDEX { vRtrID,
            isisSysInstance,
            tmnxIsisSpfLogTimeStamp }
    ::= { tmnxIsisSpfLogTable 1 }

TmnxIsisSpfLogEntry ::=
    SEQUENCE {
            tmnxIsisSpfLogTimeStamp            TimeStamp,
            tmnxIsisSpfLogRunTime              TimeTicks,
            tmnxIsisSpfLogL1Nodes              Unsigned32,
            tmnxIsisSpfLogL2Nodes              Unsigned32,
            tmnxIsisSpfLogEventCount           Unsigned32,
            tmnxIsisSpfLogLastTriggerLSPId     OCTET STRING,
            tmnxIsisSpfLogTriggerReason        BITS,
            tmnxIsisSpfLogType                 INTEGER 
            }

tmnxIsisSpfLogTimeStamp OBJECT-TYPE
    SYNTAX       TimeStamp
    MAX-ACCESS   not-accessible
    STATUS       current
    DESCRIPTION
        "The value of the object tmnxIsisSpfLogTimeStamp specifies the
         timestamp when the SPF run started on the system."
    ::= { tmnxIsisSpfLogEntry 1 }

tmnxIsisSpfLogRunTime OBJECT-TYPE
    SYNTAX       TimeTicks
    MAX-ACCESS   read-only
    STATUS       current
    DESCRIPTION
        "The value of the object tmnxIsisSpfLogRunTime indicates the 
         time (in hundredths of a second) required to complete the SPF run."
    ::= { tmnxIsisSpfLogEntry 2 }

tmnxIsisSpfLogL1Nodes OBJECT-TYPE
    SYNTAX       Unsigned32
    MAX-ACCESS   read-only
    STATUS       current
    DESCRIPTION
        "The value of the object tmnxIsisSpfLogL1Nodes indicates the 
        number of level 1 nodes involved in the SPF run."
    ::= { tmnxIsisSpfLogEntry 3 }

tmnxIsisSpfLogL2Nodes OBJECT-TYPE
    SYNTAX       Unsigned32
    MAX-ACCESS   read-only
    STATUS       current
    DESCRIPTION
        "The value of the object tmnxIsisSpfLogL2Nodes indicates the 
         number of level 2 nodes involved in the SPF run."
    ::= { tmnxIsisSpfLogEntry 4 }

tmnxIsisSpfLogEventCount OBJECT-TYPE
    SYNTAX       Unsigned32
    MAX-ACCESS   read-only
    STATUS       current
    DESCRIPTION
        "The value of the object tmnxIsisSpfLogEventCount indicates the
         number of SPF events that triggered the SPF calculation."
    ::= { tmnxIsisSpfLogEntry 5 }

tmnxIsisSpfLogLastTriggerLSPId OBJECT-TYPE
    SYNTAX       OCTET STRING (SIZE(0..8))
    MAX-ACCESS   read-only
    STATUS       current
    DESCRIPTION
        "The value of the object tmnxIsisSpfLogLastTriggerLSPId indicates the
         LSPId of the last LSP processed before the SPF run."
    ::= { tmnxIsisSpfLogEntry 6 }

tmnxIsisSpfLogTriggerReason OBJECT-TYPE
    SYNTAX       BITS {
                    newAdjacency (0),
                    newLSP (1),
                    newArea (2),
                    reach (3),
                    ecmpChanged (4),
                    newMetric (5),
                    teChanged (6),
                    restart (7),
                    lspExpired (8),
                    lspDbChanged (9),
                    lspChanged (10),
                    newPreference (11),
                    newNLPID (12),
                    manualRun (13),
                    adminTagChanged (14),
                    tunnelChanged (15),
                    throttleEnd (16)
                    }
    MAX-ACCESS   read-only
    STATUS       current
    DESCRIPTION
        "The value of the object tmnxIsisSpfLogTriggerReason indicates the reasons 
         that triggered this SPF run.
         
         newAdjacency (0)    - a new adjacency was formed.
         newLSP (1)          - a new LSP was received.
         newArea (2)         - a new area was joined.
         reach (3)           - a new prefix can be reached.
         ecmpChanged (4)     - the number of ecmp routes to a destination
                               changed.
         newMetric (5)       - a route has a new metric.
         teChanged (6)       - traffic engineering changed.
         restart (7)         - the IS-IS router was restarted.
         lspExpired (8)      - an LSP expired.
         lspDbChanged (9)    - the IS-IS LSP database was cleared.
         lspChanged (10)     - an LSP changed.
         newPreference (11)  - a route preference changed.
         newNLPID (12)       - a Network Layer Protocol was added to the 
                               IS-IS router protocl set.
         manualRun (13)      - Manual request issued.
         adminTagChanged (14)- admin tag has changed.
         tunnelChanged (15)  - list of tunnels has changed.
         throttleEnd (16)    - throttling of SPF ended."
    ::= { tmnxIsisSpfLogEntry 7 }

tmnxIsisSpfLogType OBJECT-TYPE
    SYNTAX       INTEGER {
                    regular(0),
                    lfa (1)
                    }
    MAX-ACCESS   read-only
    STATUS       current
    DESCRIPTION
        "The value of the object tmnxIsisSpfLogType indicates the
         type of SPF calculation."
    ::= { tmnxIsisSpfLogEntry 8 }

-- --------------------------------------------------------
-- tmnxIsisSummaryTable
-- --------------------------------------------------------

tmnxIsisSummaryTable    OBJECT-TYPE
    SYNTAX      SEQUENCE OF TmnxIsisSummaryEntry
    MAX-ACCESS  not-accessible
    STATUS      current
    DESCRIPTION
        "The tmnxIsisSummaryTable maintains the summary prefixes for a 
         specific instance of the IS-IS protocol."
    ::= { tmnxIsisSystemObjs 9 }

tmnxIsisSummaryEntry    OBJECT-TYPE
    SYNTAX      TmnxIsisSummaryEntry
    MAX-ACCESS  not-accessible
    STATUS      current
    DESCRIPTION
        "Each row entry in the tmnxIsisSummaryTable stores a summary 
         prefix for a specific instance of the IS-IS protocol."
    INDEX { vRtrID,
            isisSysInstance,
            tmnxIsisSummPrefixType,
            tmnxIsisSummPrefix,
            tmnxIsisSummPrefixLength }
    ::= { tmnxIsisSummaryTable 1 }

TmnxIsisSummaryEntry ::=
    SEQUENCE {
            tmnxIsisSummPrefixType     InetAddressType,
            tmnxIsisSummPrefix         InetAddress,
            tmnxIsisSummPrefixLength   InetAddressPrefixLength,
            tmnxIsisSummRowStatus      RowStatus,
            tmnxIsisSummLevel          INTEGER,
            tmnxIsisSummRouteTag       Unsigned32
           }

tmnxIsisSummPrefixType OBJECT-TYPE
    SYNTAX      InetAddressType
    MAX-ACCESS  not-accessible
    STATUS      current
    DESCRIPTION
        "The value of the object tmnxIsisSummPrefixType specifies the 
         IP address type of tmnxIsisSummPrefix."
    ::= { tmnxIsisSummaryEntry 1 }

tmnxIsisSummPrefix OBJECT-TYPE
    SYNTAX       InetAddress (SIZE(4|16|20))
    MAX-ACCESS   not-accessible
    STATUS       current
    DESCRIPTION
        "The value of the object tmnxIsisSummPrefix specifies the  
         prefix for this summary address entry."
    ::= { tmnxIsisSummaryEntry 2 }

tmnxIsisSummPrefixLength OBJECT-TYPE
    SYNTAX       InetAddressPrefixLength
    MAX-ACCESS   not-accessible
    STATUS       current
    DESCRIPTION
        "The value of the object tmnxIsisSummPrefixLength specifies the
         prefix length to be used with tmnxIsisSummPrefix to get the 
         network prefix."
    ::= { tmnxIsisSummaryEntry 3 }

tmnxIsisSummRowStatus OBJECT-TYPE
    SYNTAX       RowStatus
    MAX-ACCESS   read-create
    STATUS       current
    DESCRIPTION
        "The value of the object tmnxIsisSummRowStatus specifies the row status 
         used to create and delete entries in the tmnxIsisSummaryTable."
    ::= { tmnxIsisSummaryEntry 4 }

tmnxIsisSummLevel OBJECT-TYPE
    SYNTAX       INTEGER {
                    level1 (1),
                    level2 (2),
                    level1L2 (3)
                   }
    MAX-ACCESS   read-create
    STATUS       current
    DESCRIPTION
        "The value of the object tmnxIsisSummLevel specifies the   
         IS-IS Level from which the prefix should be summarized."
    DEFVAL { level1L2 }
    ::= { tmnxIsisSummaryEntry 5 }

tmnxIsisSummRouteTag  OBJECT-TYPE
    SYNTAX      Unsigned32
    MAX-ACCESS  read-create
    STATUS      current
    DESCRIPTION
        "The value of the object tmnxIsisSummRouteTag specifies a 
         32-bit integer tag for the ISIS summary address and can be
         used to apply administrative policy. 
         
         A value of 0 indicates that the tag has not been set."
    DEFVAL { 0 }
    ::= { tmnxIsisSummaryEntry 6 }

-- --------------------------------------------------------
-- tmnxIsisLfaTable
-- --------------------------------------------------------

tmnxIsisLfaTable    OBJECT-TYPE
    SYNTAX      SEQUENCE OF TmnxIsisLfaEntry
    MAX-ACCESS  not-accessible
    STATUS      current
    DESCRIPTION
        "The tmnxIsisLfaTable maintains information on loopfree-alternate (LFA) 
         coverage for each instance of IS-IS protocol."
    ::= { tmnxIsisSystemObjs 10 }

tmnxIsisLfaEntry    OBJECT-TYPE
    SYNTAX      TmnxIsisLfaEntry
    MAX-ACCESS  not-accessible
    STATUS      current
    DESCRIPTION
        "Each row entry in the tmnxIsisLfaTable represents information on 
         LFA coverage for various topologies of the system."
    INDEX { vRtrID,
            isisSysInstance,
            tmnxIsisLevel,
            tmnxIsisLfaFamilyCoverage }
    ::= { tmnxIsisLfaTable 1 }

TmnxIsisLfaEntry ::=
    SEQUENCE {
            tmnxIsisLfaFamilyCoverage     INTEGER,
            tmnxIsisLfaNodesCovered       Unsigned32,
            tmnxIsisLfaTotalNodes         Unsigned32,
            tmnxIsisLfaNodeCoverage       Unsigned32,
            tmnxIsisLfaIPv4NodesCovered   Unsigned32,
            tmnxIsisLfaIPv4TotalNodes     Unsigned32,
            tmnxIsisLfaIPv4Coverage       Unsigned32, 
            tmnxIsisLfaIPv6NodesCovered   Unsigned32, 
            tmnxIsisLfaIPv6TotalNodes     Unsigned32, 
            tmnxIsisLfaIPv6Coverage       Unsigned32 
            }

tmnxIsisLfaFamilyCoverage OBJECT-TYPE
    SYNTAX       INTEGER {
                    ipv4(0),      
                    ipv6(1),
                    ipv4Mcast(2),
                    ipv6Mcast(3)       
                   }
    MAX-ACCESS   not-accessible
    STATUS       current
    DESCRIPTION
        "The value of the object tmnxIsisLfaFamilyCoverage specifies the
         multi topology (MT's) for which LFA coverage has been computed.

         Possible values are:

         ipv4(0)      - indicates MT0 or standard topology
         ipv6(1)      - indicates MT2 or IPv6 routing topology
         ipv4Mcast(2) - indicates MT3 or IPv4 multicast routing topology
         ipv6Mcast(3) - indicates MT4 or IPv6 multicast routing topology."
    ::= { tmnxIsisLfaEntry 1 }

tmnxIsisLfaNodesCovered OBJECT-TYPE
    SYNTAX       Unsigned32 
    MAX-ACCESS   read-only
    STATUS       current
    DESCRIPTION
        "The value of the object tmnxIsisLfaNodesCovered indicates in 
         absolute numbers how much LFA coverage is being obtained for
         the available routes."
    ::= { tmnxIsisLfaEntry 2 }

tmnxIsisLfaTotalNodes OBJECT-TYPE
    SYNTAX       Unsigned32
    MAX-ACCESS   read-only
    STATUS       current
    DESCRIPTION
        "The value of the object tmnxIsisLfaTotalNodes indicates in 
         absolute numbers how much LFA coverage can be obtained for
         the available routes."
    ::= { tmnxIsisLfaEntry 3 }

tmnxIsisLfaNodeCoverage OBJECT-TYPE
    SYNTAX       Unsigned32 (0..10000)
    UNITS        "hundredths of a percent"
    MAX-ACCESS   read-only
    STATUS       current
    DESCRIPTION
        "The value of the object tmnxIsisLfaNodeCoverage indicates how much
         LFA coverage is being obtained for the set of available nodes."
    ::= { tmnxIsisLfaEntry 4 }

tmnxIsisLfaIPv4NodesCovered OBJECT-TYPE
    SYNTAX       Unsigned32
    MAX-ACCESS   read-only
    STATUS       current
    DESCRIPTION
        "The value of the object tmnxIsisLfaIPv4NodesCovered indicates in
         absolute numbers how much LFA coverage is being obtained for the
         available IPv4 routes."
    ::= { tmnxIsisLfaEntry 5 }

tmnxIsisLfaIPv4TotalNodes OBJECT-TYPE
    SYNTAX       Unsigned32
    MAX-ACCESS   read-only
    STATUS       current
    DESCRIPTION
        "The value of the object tmnxIsisLfaIPv4TotalNodes indicates in 
         absolute numbers how much LFA coverage can be obtained for the
         available IPv4 routes."
    ::= { tmnxIsisLfaEntry 6 }

tmnxIsisLfaIPv4Coverage OBJECT-TYPE
    SYNTAX       Unsigned32 (0..10000)
    UNITS        "hundredths of a percent"
    MAX-ACCESS   read-only
    STATUS       current
    DESCRIPTION
        "The value of the object tmnxIsisLfaIPv4Coverage indicates how much 
         LFA coverage is being obtained for the available IPv4 routes."
    ::= { tmnxIsisLfaEntry 7 }

tmnxIsisLfaIPv6NodesCovered OBJECT-TYPE
    SYNTAX       Unsigned32
    MAX-ACCESS   read-only
    STATUS       current
    DESCRIPTION
        "The value of the object tmnxIsisLfaIPv6NodesCovered indicates in 
         absolute numbers how much LFA coverage is being obtained for 
         available IPv6 routes."
    ::= { tmnxIsisLfaEntry 8 }

tmnxIsisLfaIPv6TotalNodes OBJECT-TYPE
    SYNTAX       Unsigned32
    MAX-ACCESS   read-only
    STATUS       current
    DESCRIPTION
        "The value of the object tmnxIsisLfaIPv6TotalNodes indicates in 
         absolute numbers how much LFA coverage can be obtained for the 
         available IPv6 routes."
    ::= { tmnxIsisLfaEntry 9 }

tmnxIsisLfaIPv6Coverage OBJECT-TYPE
    SYNTAX       Unsigned32 (0..10000)
    UNITS        "hundredths of a percent"
    MAX-ACCESS   read-only
    STATUS       current
    DESCRIPTION
        "The value of the object tmnxIsisLfaIPv6Coverage indicates how much
         LFA coverage is being obtained for the available IPv6 routes."
    ::= { tmnxIsisLfaEntry 10 }

--
--  Augmentation of the tmnxIsisTable
--  Use of AUGMENTS clause implies a one-to-one dependent relationship
--  between the base table, tmnxIsisTable, and the augmenting table,
--  tmnxIsisExtTable. This in effect extends the tmnxIsisTable with
--  additional columns. Creation (or deletion) of a row in the tmnxIsisTable
--  results in the same fate for the row in the tmnxIsisExtTable.
--

tmnxIsisExtTable OBJECT-TYPE
    SYNTAX      SEQUENCE OF TmnxIsisExtEntry
    MAX-ACCESS  not-accessible
    STATUS      current
    DESCRIPTION
        "The tmnxIsisExtTable provides an extension of the tmnxIsisTable."
    ::= { tmnxIsisSystemObjs 11 }

tmnxIsisExtEntry OBJECT-TYPE
    SYNTAX      TmnxIsisExtEntry
    MAX-ACCESS  not-accessible
    STATUS      current
    DESCRIPTION
        "Each row entry in tmnxIsisExtTable represents additional
         columns for attributes specific to the Alcatel-Lucent
         SROS series implementation for the ISIS configuration table."
    AUGMENTS { tmnxIsisEntry }
    ::= { tmnxIsisExtTable 1 }

TmnxIsisExtEntry ::=
    SEQUENCE {
        tmnxIsisExLastChanged           TimeStamp,
        tmnxIsisLFAExcludePolicy1       TNamedItemOrEmpty,
        tmnxIsisLFAExcludePolicy2       TNamedItemOrEmpty,
        tmnxIsisLFAExcludePolicy3       TNamedItemOrEmpty,
        tmnxIsisLFAExcludePolicy4       TNamedItemOrEmpty,
        tmnxIsisLFAExcludePolicy5       TNamedItemOrEmpty
    }

tmnxIsisExLastChanged  OBJECT-TYPE
    SYNTAX      TimeStamp
    MAX-ACCESS  read-only
    STATUS      current
    DESCRIPTION
        "The value of tmnxIsisExLastChanged indicates the sysUpTime
         when a configurable object in this row was last modified."
    ::= { tmnxIsisExtEntry 1 } 

tmnxIsisLFAExcludePolicy1   OBJECT-TYPE
        SYNTAX      TNamedItemOrEmpty
        MAX-ACCESS  read-write
        STATUS      current
        DESCRIPTION
            "The value of tmnxIsisLFAExcludePolicy1 is the name of the first
             policy from which prefixes are excluded which match on the ISIS
             tag. Prefixes excluded from LFA (Loopfree Alternative) this way
             will not be used in the LFA calculation, regardless of its
             priority."
        DEFVAL { ''H }
        ::= { tmnxIsisExtEntry 2 }

tmnxIsisLFAExcludePolicy2   OBJECT-TYPE
        SYNTAX      TNamedItemOrEmpty
        MAX-ACCESS  read-write
        STATUS      current
        DESCRIPTION
            "The value of tmnxIsisLFAExcludePolicy2 is the name of the second
             policy from which prefixes are excluded which match on the ISIS
             tag. Prefixes excluded from LFA (Loopfree Alternative) this way
             will not be used in the LFA calculation, regardless of its
             priority."
        DEFVAL { ''H }
        ::= { tmnxIsisExtEntry 3 }

tmnxIsisLFAExcludePolicy3   OBJECT-TYPE
        SYNTAX      TNamedItemOrEmpty
        MAX-ACCESS  read-write
        STATUS      current
        DESCRIPTION
            "The value of tmnxIsisLFAExcludePolicy3 is the name of the third
             policy from which prefixes are excluded which match on the ISIS
             tag. Prefixes excluded from LFA (Loopfree Alternative) this way
             will not be used in the LFA calculation, regardless of its
             priority."
        DEFVAL { ''H }
        ::= { tmnxIsisExtEntry 4 }

tmnxIsisLFAExcludePolicy4   OBJECT-TYPE
        SYNTAX      TNamedItemOrEmpty
        MAX-ACCESS  read-write
        STATUS      current
        DESCRIPTION
            "The value of tmnxIsisLFAExcludePolicy4 is the name of the fourth
             policy from which prefixes are excluded which match on the ISIS
             tag. Prefixes excluded from LFA (Loopfree Alternative) this way
             will not be used in the LFA calculation, regardless of its
             priority."
        DEFVAL { ''H }
        ::= { tmnxIsisExtEntry 5 }

tmnxIsisLFAExcludePolicy5   OBJECT-TYPE
        SYNTAX      TNamedItemOrEmpty
        MAX-ACCESS  read-write
        STATUS      current
        DESCRIPTION
            "The value of tmnxIsisLFAExcludePolicy5 is the name of the fifth
             policy from which prefixes are excluded which match on the ISIS
             tag. Prefixes excluded from LFA (Loopfree Alternative) this way
             will not be used in the LFA calculation, regardless of its
             priority."
        DEFVAL { ''H }
        ::= { tmnxIsisExtEntry 6 }

-- --------------------------------------------------------
-- Read-only objects
-- --------------------------------------------------------


-- --------------------------------------------------------
--  tmnxIsisIfTable  IS-IS Interfaces Table
-- ---------------------------------------------------------

tmnxIsisIfTable    OBJECT-TYPE
    SYNTAX      SEQUENCE OF TmnxIsisIfEntry
    MAX-ACCESS  not-accessible
    STATUS      current
    DESCRIPTION
        "The tmnxIsisIfTable has an entry for each router interface 
         configured for the IS-IS protocol."
    ::= { tmnxIsisIfObjs 1 }

tmnxIsisIfEntry    OBJECT-TYPE
    SYNTAX      TmnxIsisIfEntry
    MAX-ACCESS  not-accessible
    STATUS      current
    DESCRIPTION
        "Each row entry in the tmnxIsisIfTable represents an interface on
         this router that participates in the IS-IS protocol.  An entry in
         this table can be created or destroyed by an SNMP SET request to
         tmnxIsisIfRowStatus.  An attempt to destroy a row will fail if
         tmnxIsisIfAdminState has not first been set to 'outOfService'."
    INDEX { vRtrID, isisSysInstance, vRtrIfIndex }
    ::= { tmnxIsisIfTable 1 }

TmnxIsisIfEntry ::=
    SEQUENCE {
            tmnxIsisIfRowStatus          RowStatus,
            tmnxIsisIfLastChanged        TimeStamp,
            tmnxIsisIfAdminState         TmnxAdminState,
            tmnxIsisIfOperState          TmnxOperState,
            tmnxIsisIfCsnpInterval       Unsigned32,
            tmnxIsisIfHelloAuthKey       OCTET STRING,
            tmnxIsisIfHelloAuthType      INTEGER,
            tmnxIsisIfLspPacingInterval  Unsigned32,
            tmnxIsisIfCircIndex          Integer32,
            tmnxIsisIfRetransmitInterval Unsigned32,
            tmnxIsisIfTypeDefault        TruthValue,
            tmnxIsisIfEnableBfd          TruthValue,
            tmnxIsisIfIPv6Unicast        TruthValue,  
            tmnxIsisIfTeMetric           Unsigned32,
            tmnxIsisIfTeState            TmnxOperState,
            tmnxIsisIfAdminGroup         Unsigned32,
            tmnxIsisIfLdpSyncState       TmnxOperState,
            tmnxIsisIfLdpSyncMaxMetric   TruthValue,
            tmnxIsisIfLdpSyncTimerState  INTEGER,
            tmnxIsisIfLdpSyncTimeLeft    Unsigned32,
            tmnxIsisIfRouteTag           Unsigned32,
            tmnxIsisIfIPv6EnableBfd      TruthValue,
            tmnxIsisIfHelloAuth          TruthValue,
            tmnxIsisIfLoopfreeAltExclude TruthValue,
            tmnxIsisIfOperType           INTEGER,
            tmnxIsisIfIPv4Mcast          TruthValue,
            tmnxIsisIfIPv6Mcast          TruthValue,
            tmnxIsisIfBerState           INTEGER,
            tmnxIsisIfIPv4IncludeBfdTlv   TruthValue,
            tmnxIsisIfIPv6IncludeBfdTlv   TruthValue,
            tmnxIsisIfHelloAuthKeyChain   TNamedItemOrEmpty,
            tmnxIsisIfRouteNHTemplate     TNamedItemOrEmpty

        }

tmnxIsisIfRowStatus       OBJECT-TYPE
    SYNTAX      RowStatus
    MAX-ACCESS  read-create
    STATUS      current
    DESCRIPTION
       "The value of the object tmnxIsisIfRowStatus specifies the row status  
        used for creation, deletion, or control of tmnxIsisIfTable entries.
        
        Before this row can be destroyed, tmnxIsisIfAdminState must have been
        set to 'outOfService'."
    ::= { tmnxIsisIfEntry 1 }

tmnxIsisIfLastChanged       OBJECT-TYPE
    SYNTAX      TimeStamp
    MAX-ACCESS  read-only
    STATUS      current
    DESCRIPTION
        "The value of the object tmnxIsisIfLastChanged indicates the 
         sysUpTime when this row was last modified."
    ::= { tmnxIsisIfEntry 2 }

tmnxIsisIfAdminState       OBJECT-TYPE
    SYNTAX      TmnxAdminState
    MAX-ACCESS  read-create
    STATUS      current
    DESCRIPTION
        "The value of the object tmnxIsisIfAdminState specifies the desired
         administrative state for IS-IS protocol on this interface."
    DEFVAL { outOfService }
    ::= { tmnxIsisIfEntry 3 }

tmnxIsisIfOperState        OBJECT-TYPE
    SYNTAX      TmnxOperState
    MAX-ACCESS  read-only
    STATUS      current
    DESCRIPTION
        "The value of the object tmnxIsisIfOperState indicates the current 
         operational state of IS-IS protocol on this interface."
    ::= { tmnxIsisIfEntry 4 }

tmnxIsisIfCsnpInterval      OBJECT-TYPE
    SYNTAX      Unsigned32 (1..65535)
    UNITS       "seconds"
    MAX-ACCESS  read-create
    STATUS      current
    DESCRIPTION
       "The value of the object tmnxIsisIfCsnpInterval specifies the 
        interval of time, in seconds, between transmission of 
        Complete Sequence Number PDUs (CSNP).
        
        If the value of isisCircType for this interface is 'broadcast' and
        this router is the designated router on a LAN, the default frequency 
        is ten seconds.  
        
        If the value of isisCircType for this  interface is 'ptToPt', 
        point-to-point, the default frequency is every five seconds."
    DEFVAL { 10 } 
    ::= { tmnxIsisIfEntry 5 }

tmnxIsisIfHelloAuthKey      OBJECT-TYPE
    SYNTAX      OCTET STRING (SIZE(0..254))
    MAX-ACCESS  read-create
    STATUS      current
    DESCRIPTION
        "The value of the object tmnxIsisIfHelloAuthKey specifies the
         authentication key string used to verify the authenticity of 
         packets sent by neighboring routers on this IS-IS interface.
         
         For authentication to succeed both the authentication key and
         the authentication type defined by the tmnxIsisIfHelloAuthType 
         variable must match.  
         
         If tmnxIsisIfHelloAuthType is set to 'password',
         tmnxIsisIfHelloAuthKey can include any ASCII character.

         Authentication can be configured globally and applied to all
         ISIS levels running on this interface or it can be configured
         on a per level basis.  The most specific value is used.

         When read, tmnxIsisIfHelloAuthKey always returns an 
         Octet String of length zero."
    DEFVAL { ''H }   
    ::= { tmnxIsisIfEntry 6 }

tmnxIsisIfHelloAuthType     OBJECT-TYPE
    SYNTAX      INTEGER {
                    none (1),
                    password (2),
                    md5 (3)
                }
    MAX-ACCESS  read-create
    STATUS      current
    DESCRIPTION
        "The value of the object tmnxIsisIfHelloAuthType specifies the 
         method of authentication used to verify the authenticity of 
         packets sent by neighboring routers on this IS-IS interface.
         
         For authentication to succeed both the authentication key 
         defined in the tmnxIsisIfHelloAuthKey variable and the 
         authentication type must match.

         Authentication can be configured globally and applied to all
         ISIS levels running on this interface or it can be configured on
         a per level basis.  The most specific value is used."
    DEFVAL { none }
    ::= { tmnxIsisIfEntry 7 }

tmnxIsisIfLspPacingInterval       OBJECT-TYPE
    SYNTAX      Unsigned32 (0..65535)
    UNITS       "milliseconds"
    MAX-ACCESS  read-create
    STATUS      current
    DESCRIPTION
        "The value of the object tmnxIsisIfLspPacingInterval specifies the
         minimal interval of time, in milliseconds, between transmission of
         Link State PDUs (LSPs) for all ISIS levels running on this interface.

         If the value of tmnxIsisIfLspPacingInterval is zero (0),  
         no LSPs will be sent on this interface."
    DEFVAL { 100 }
    ::= { tmnxIsisIfEntry 8 }

tmnxIsisIfCircIndex       OBJECT-TYPE
    SYNTAX      Integer32 (1..2000000000)
    MAX-ACCESS  read-only
    STATUS      current
    DESCRIPTION
        "The value of the object tmnxIsisIfCircIndex indicates a 
         cross reference index to the isisCircTable."
    ::= { tmnxIsisIfEntry 9 }

tmnxIsisIfRetransmitInterval       OBJECT-TYPE
    SYNTAX      Unsigned32 (1..65535)
    UNITS       "seconds"
    MAX-ACCESS  read-create
    STATUS      current
    DESCRIPTION
        "The value of the object tmnxIsisIfRetransmitInterval specifies the
         minimal interval of time, in seconds between retransmission of an  
         LSP on point-to-point interfaces."
    DEFVAL { 5 }     
    ::= { tmnxIsisIfEntry 10 }

tmnxIsisIfTypeDefault       OBJECT-TYPE
    SYNTAX      TruthValue
    MAX-ACCESS  read-create
    STATUS      current
    DESCRIPTION
        "The value of the object tmnxIsisIfTypeDefault specifies if the 
         circuit type is default or has been modified.
         
         Setting tmnxIsisIfTypeDefault to 'true' resets isisCircType to 
         the default for that interface. 
         
         Similarly any modification to the object isisCircType triggers 
         this object to become 'false'. 
         
         There is no effect of setting this object to 'false'."
    DEFVAL { true }     
    ::= { tmnxIsisIfEntry 11 }

tmnxIsisIfEnableBfd       OBJECT-TYPE
    SYNTAX      TruthValue
    MAX-ACCESS  read-create
    STATUS      current
    DESCRIPTION
        "The value of the object tmnxIsisIfEnableBfd specifies whether 
         Bi-directional Forwarding Detection is enabled for IPv4 on this
         IS-IS interface.

         When the value is 'true', this IS-IS interface can establish BFD 
         sessions and use BFD as a signaling mechanism for forming 
         adjacencies. 
         
         When tmnxIsisIfEnableBfd is 'false', BFD cannot be for IPv4."
    DEFVAL { false }
    ::= { tmnxIsisIfEntry 12 }

tmnxIsisIfIPv6Unicast       OBJECT-TYPE
    SYNTAX      TruthValue
    MAX-ACCESS  read-create
    STATUS      current
    DESCRIPTION
        "The value of the object tmnxIsisIfIPv6Unicast specifies whether
         IPv6 unicast routing is enabled for the interface.

         By default IPv6 unicast on all interfaces is set to true.
         However, IPv6 unicast routing on ISIS is in effect when 
         the object 'tmnxIsisMultiTopoIPv6Ucast' is set to 'true'."
    DEFVAL { true }
    ::= { tmnxIsisIfEntry 13 }

tmnxIsisIfTeMetric  OBJECT-TYPE
    SYNTAX      Unsigned32 (0..16777215)
    MAX-ACCESS  read-only
    STATUS      current
    DESCRIPTION    
        "The value of the object tmnxIsisIfTeMetric indicates the 
         MPLS TE metric configured for this interface; 
         this metric is flooded out in the TE metric sub-tlv in the ISIS LSPs. 
         
         Depending on the configuration, either the TE metric value or the
         native ISIS metric values are used in CSPF computations."
    ::= { tmnxIsisIfEntry 14 }  

tmnxIsisIfTeState        OBJECT-TYPE
    SYNTAX      TmnxOperState
    MAX-ACCESS  read-only
    STATUS      current
    DESCRIPTION
        "The value of the object tmnxIsisIfTeState indicates the 
         MPLS interface TE status from the ISIS standpoint."
    ::= { tmnxIsisIfEntry 15 } 

tmnxIsisIfAdminGroup  OBJECT-TYPE
    SYNTAX      Unsigned32
    MAX-ACCESS  read-only
    STATUS      current
    DESCRIPTION
        "The value of the object tmnxIsisIfAdminGroup indicates the bit-map   
         inherited from MPLS interface that identifies the admin groups to which   
         the interface belongs. 
         
         If bit 'n' is set, then the interface belongs to the admin 
         group with value 'n'."
    ::= { tmnxIsisIfEntry 16 }

tmnxIsisIfLdpSyncState  OBJECT-TYPE
    SYNTAX      TmnxOperState
    MAX-ACCESS  read-only
    STATUS      current
    DESCRIPTION
        "The value of the object tmnxIsisIfLdpSyncState indicates if 
         IGP-LDP synchronization is enabled on this interface. 
         
         tmnxIsisIfLdpSyncState is derived from tmnxIsisLdpSyncAdminState and
         also whether it was enabled at the IP layer from ISIS standpoint."
    ::= { tmnxIsisIfEntry 17 }

tmnxIsisIfLdpSyncMaxMetric   OBJECT-TYPE
    SYNTAX      TruthValue
    MAX-ACCESS  read-only
    STATUS      current
    DESCRIPTION
        "The value of the object tmnxIsisIfLdpSyncMaxMetric indicates if ISIS  
         advertised maximum metric value for the interface, depending on 
         whether tmnxIsisIfLdpSyncState is enabled on this interface."
    ::= { tmnxIsisIfEntry 18 }

tmnxIsisIfLdpSyncTimerState   OBJECT-TYPE
    SYNTAX      INTEGER {
                    waitForLdpAdj (1), -- Waiting for LDP adj to come up
                    timerActive (2),   -- LDP adj up (sync timer running)
                    ldpExchgDone (3),  -- LDP label exchange done
                    timerExpired (4),  -- Sync timer expired
                    manualExit (5),    -- User intervened for sync termination
                    disabled (6)       -- LDP Sync is not being done
                }
    MAX-ACCESS  read-only
    STATUS      current
    DESCRIPTION
        "The value of the object tmnxIsisIfLdpSyncTimerState indicates the 
         state of the tmnxIsisIfLdpSyncTimeLeft on this ISIS interface."
    ::= { tmnxIsisIfEntry 19 }

tmnxIsisIfLdpSyncTimeLeft  OBJECT-TYPE
    SYNTAX      Unsigned32 (0|1..1800)
    UNITS       "seconds"
    MAX-ACCESS  read-only
    STATUS      current
    DESCRIPTION
        "The value of the object tmnxIsisIfLdpSyncTimeLeft indicates the 
         time left before ISIS reverts back to advertising normal metric for
         this interface.
         
         This is applicable only when tmnxIsisIfLdpSyncMaxMetric is 'true'."
    ::= { tmnxIsisIfEntry 20 }

tmnxIsisIfRouteTag  OBJECT-TYPE
    SYNTAX      Unsigned32 
    MAX-ACCESS  read-create
    STATUS      current
    DESCRIPTION
        "The value of the object tmnxIsisIfRouteTag specifies a 32-bit 
         integer tag for the IP addresses of an interface.
         
         This route tag can be used to apply administrative policy. 
         
         A value of 0 indicates that the tag has not been set."
    DEFVAL { 0 }
    ::= { tmnxIsisIfEntry 21 }

tmnxIsisIfIPv6EnableBfd       OBJECT-TYPE
    SYNTAX      TruthValue
    MAX-ACCESS  read-create
    STATUS      current
    DESCRIPTION
        "The value of the object tmnxIsisIfIPv6EnableBfd specifies whether 
         Bi-directional Forwarding Detection is enabled for IPv6 on this
         IS-IS interface.

         When the value is 'true', this IS-IS interface can establish BFD 
         sessions and use BFD as a signaling mechanism for forming 
         adjacencies. When it is 'false', it cannot use BFD for IPv6."
    DEFVAL { false }
    ::= { tmnxIsisIfEntry 22 }

tmnxIsisIfHelloAuth       OBJECT-TYPE
    SYNTAX      TruthValue
    MAX-ACCESS  read-create
    STATUS      current
    DESCRIPTION
        "The value of the object tmnxIsisIfHelloAuth specifies whether ISIS
         hello-authentication is enabled or disabled on this IS-IS interface.

         When tmnxIsisIfHelloAuth is set to 'true', 
         hello-authentication is enabled on this IS-IS interface.

         When tmnxIsisIfHelloAuth is set to 'false', 
         hello-authentication is disabled on this IS-IS interface and 
         the values of the following MIB objects are no longer applicable:
         - tmnxIsisIfHelloAuthKey and tmnxIsisIfHelloAuthType at a global 
           interface level
         - tmnxIsisIfLevelHelloAuthKey and tmnxIsisIfLevelHelloAuthType   
           at the specific L1/L2 interface level
         - tmnxIsisAuthKey and tmnxIsisAuthType at the ISIS level."
    DEFVAL { true }
    ::= { tmnxIsisIfEntry 23 }

tmnxIsisIfLoopfreeAltExclude  OBJECT-TYPE
    SYNTAX      TruthValue
    MAX-ACCESS  read-create
    STATUS      current
    DESCRIPTION
         "The value of the object tmnxIsisIfLoopfreeAltExclude specifies  
          whether or not the ISIS interface should be excluded during LFA 
          calculations. 
          
          If the value is 'true', the ISIS interface is excluded
          from LFA calculations. If the value is 'false', the ISIS 
          interface is included in LFA calculations.

          The value of tmnxIsisIfLoopfreeAltExclude for an interface is  
          only valid when both conditions are met - tmnxIsisLoopfreeAlternate
          has a value of 'true' and tmnxIsisLevelLoopfreeAltExclude has   
          a value of 'false'."
    DEFVAL { false }             
    ::= {tmnxIsisIfEntry 24 }

tmnxIsisIfOperType  OBJECT-TYPE
    SYNTAX      INTEGER {
                broadcast(1),   -- Broadcast interface
                ptToPt(2)       -- Point-to-point interface
            }
    MAX-ACCESS  read-only
    STATUS      current
    DESCRIPTION
        "The value of the object tmnxIsisIfOperType specifies the 
         operational type on this ISIS interface."
    ::= { tmnxIsisIfEntry 25 }

tmnxIsisIfIPv4Mcast       OBJECT-TYPE
    SYNTAX      TruthValue
    MAX-ACCESS  read-create
    STATUS      current
    DESCRIPTION
        "The value of the object tmnxIsisIfIPv4Mcast specifies if 
         IPv4 multicast routing is enabled for the interface."
    DEFVAL { true }
    ::= { tmnxIsisIfEntry 26 }

tmnxIsisIfIPv6Mcast       OBJECT-TYPE
    SYNTAX      TruthValue
    MAX-ACCESS  read-create
    STATUS      current
    DESCRIPTION
        "The value of the object tmnxIsisIfIPv6Mcast specifies if 
         IPv6 multicast routing is enabled for the interface."
    DEFVAL { true }
    ::= { tmnxIsisIfEntry 27 }

tmnxIsisIfBerState    OBJECT-TYPE
    SYNTAX      INTEGER {
                    none(0),
                    sd(1),
                    sf(2)
                }
    MAX-ACCESS  read-only
    STATUS      current
    DESCRIPTION
         "The value of the object tmnxIsisIfBerState indicates the 
          BER (Bit Error Rate) state of this interface."            
    ::= { tmnxIsisIfEntry 28 } 

tmnxIsisIfIPv4IncludeBfdTlv       OBJECT-TYPE
    SYNTAX      TruthValue
    MAX-ACCESS  read-create
    STATUS      current
    DESCRIPTION
        "The value of the object tmnxIsisIfIPv4IncludeBfdTlv specifies  
         whether a BFD-enabled type-length-value (TLV) is included for 
         IPv4 on this IS-IS interface.

         When the value of tmnxIsisIfEnableBfd is false, the value of 
         tmnxIsisIfIPv4IncludeBfdTlv is ignored.
         
         When both tmnxIsisIfEnableBfd and tmnxIsisIfIPv4IncludeBfdTlv 
         have the value set to true, then the BFD-enabled TLV is 
         included for IPv4."
    DEFVAL { false }
    ::= { tmnxIsisIfEntry 29 }
    
tmnxIsisIfIPv6IncludeBfdTlv       OBJECT-TYPE
    SYNTAX      TruthValue
    MAX-ACCESS  read-create
    STATUS      current
    DESCRIPTION
        "The value of the object tmnxIsisIfIPv6IncludeBfdTlv specifies  
         whether a BFD-enabled type-length-value (TLV) is included for
         IPv6 on this IS-IS interface.

         When the value of tmnxIsisIfIPv6EnableBfd is false, the value of 
         tmnxIsisIfIPv6IncludeBfdTlv is ignored.
         
         When both tmnxIsisIfIPv6EnableBfd and tmnxIsisIfIPv6IncludeBfdTlv 
         have the value set to true, then the BFD-enabled TLV is 
         included for IPv6."
    DEFVAL { false }
    ::= { tmnxIsisIfEntry 30 }

tmnxIsisIfHelloAuthKeyChain  OBJECT-TYPE
    SYNTAX      TNamedItemOrEmpty
    MAX-ACCESS  read-write
    STATUS      current
    DESCRIPTION
        "The value of tmnxIsisIfHelloAuthKeyChain specifies the keychain to use
         to sign and/or authenticate the IS-IS instance.

         The keychain name is defined by tmnxKeyChainName and is the index for
         TIMETRA-SECURITY-MIB::tmnxKeyChainTable"
    DEFVAL { ''H }
    ::= { tmnxIsisIfEntry 31 }

tmnxIsisIfRouteNHTemplate  OBJECT-TYPE
    SYNTAX      TNamedItemOrEmpty
    MAX-ACCESS  read-create
    STATUS      current
    DESCRIPTION
        "The value of tmnxIsisIfRouteNHTemplate specifies the
         next-hop template that must be applied to the prefixes
         which primary next-hop uses this interface name.

         The next-hop template name is defined by tmnxRouteNHTemplateName
         and is the index for 
         TIMETRA-ROUTE-NEXT-HOP-TEMPLATE-MIB::tmnxRouteNHTemplateTable."
    DEFVAL { ''H }
    ::= { tmnxIsisIfEntry 32 }

-- --------------------------------------------------------------------------
--  tmnxIsisIfLevelTable  IS-IS Interfaces Level Table
-- --------------------------------------------------------------------------

tmnxIsisIfLevelTable    OBJECT-TYPE
    SYNTAX      SEQUENCE OF TmnxIsisIfLevelEntry
    MAX-ACCESS  not-accessible
    STATUS      current
    DESCRIPTION
        "The tmnxIsisIfLevelTable provides attributes to be applied on a
         specific IS-IS interface operating at a specific IS-IS protocol
         level."
    ::= { tmnxIsisIfObjs 2 }

tmnxIsisIfLevelEntry    OBJECT-TYPE
    SYNTAX      TmnxIsisIfLevelEntry
    MAX-ACCESS  not-accessible
    STATUS      current
    DESCRIPTION
        "Each row entry in the tmnxIsisIfLevelTable represents IS-IS level
         attributes to be used with an interface belonging to a specific IS-IS
         protocol instance on a specific router instance.
         Rows for Level 1 and 2 are created as an action of creating a row in
         the tmnxIsisIfTable."
    INDEX { vRtrID, 
            isisSysInstance, 
            vRtrIfIndex, 
            tmnxIsisIfLevel }
    ::= { tmnxIsisIfLevelTable 1 }

TmnxIsisIfLevelEntry ::=
    SEQUENCE {
            tmnxIsisIfLevel                     INTEGER,
            tmnxIsisIfLevelLastChangeTime       TimeStamp,
            tmnxIsisIfLevelHelloAuthKey         OCTET STRING,
            tmnxIsisIfLevelHelloAuthType        INTEGER,
            tmnxIsisIfLevelPassive              TruthValue,
            tmnxIsisIfLevelNumAdjacencies       Unsigned32,
            tmnxIsisIfLevelISPriority           Unsigned32,
            tmnxIsisIfLevelHelloTimer           Unsigned32,
            tmnxIsisIfLevelAdminMetric          Unsigned32,
            tmnxIsisIfLevelOperMetric           Unsigned32,
            tmnxIsisIfLvlIPv6UcastAdmMet        Unsigned32,
            tmnxIsisIfLvlIPv6UcastOperMet       Unsigned32,
            tmnxIsisIfLvlIPv4McastAdmMetric     Unsigned32,
            tmnxIsisIfLvlIPv6McastAdmMetric     Unsigned32,
            tmnxIsisIfLevelLinkGroupName        TNamedItemOrEmpty,
            tmnxIsisIfLevelSdOffset             Unsigned32,
            tmnxIsisIfLevelSfOffset             Unsigned32,
            tmnxIsisIfLvlIPv4McastOperMetric     Unsigned32,
            tmnxIsisIfLvlIPv6McastOperMetric     Unsigned32,
            tmnxIsisIfLevelHelloAuthKeyChain     TNamedItemOrEmpty
       }

tmnxIsisIfLevel     OBJECT-TYPE
    SYNTAX      INTEGER {
                    level1 (1),
                    level2 (2)
                }
    MAX-ACCESS  not-accessible
    STATUS      current
    DESCRIPTION
        "The value of the object tmnxIsisIfLevel specifies the 
         IS-IS protocol level that this row entry describes."
    ::= { tmnxIsisIfLevelEntry 1 }

tmnxIsisIfLevelLastChangeTime       OBJECT-TYPE
    SYNTAX      TimeStamp
    MAX-ACCESS  read-only
    STATUS      current
    DESCRIPTION
        "The value of the object tmnxIsisIfLevelLastChangeTime indicates the
         sysUpTime when this row was last modified."
    ::= { tmnxIsisIfLevelEntry 2 }

tmnxIsisIfLevelHelloAuthKey     OBJECT-TYPE
    SYNTAX      OCTET STRING (SIZE(0..254))
    MAX-ACCESS  read-create
    STATUS      current
    DESCRIPTION
        "The value of the object tmnxIsisIfLevelHelloAuthKey specifies the 
         authentication key string used to verify the authenticity of
         packets sent by neighboring routers on this IS-IS interface at
         this level.  
         
         For authentication to succeed both the authentication key and 
         the authentication type defined by the tmnxIsisIfLevelHelloAuthType
         variable must match.
         
         If tmnxIsisIfLevelHelloAuthType is set to 'password',
         tmnxIsisIfLevelHelloAuthKey can include any ASCII character.

         Authentication can be configured globally and applied to all
         ISIS levels or it can be configured on a per level basis; 
         the most specific value is used.  
         
         If the value of tmnxIsisIfLevelHelloAuthType is 'useGlobal', then
         the global values, if any, defined in tmnxIsisIfHelloAuthKey and
         tmnxIsisIfHelloAuthType are used instead.

         When read, tmnxIsisIfLevelHelloAuthKey always returns an Octet
         String of length zero."
    DEFVAL { ''H }   
    ::= { tmnxIsisIfLevelEntry 3 }

tmnxIsisIfLevelHelloAuthType        OBJECT-TYPE
    SYNTAX      INTEGER {
                    useGlobal (0),
                    none (1),
                    password (2),
                    md5 (3)
                }
    MAX-ACCESS  read-create
    STATUS      current
    DESCRIPTION
        "The value of the object tmnxIsisIfLevelHelloAuthType specifies the 
         method of authentication used to verify the authenticity of packets 
         sent by neighboring routers on this IS-IS interface at this level. 
         
         For authentication to succeed both the authentication key defined in
         the tmnxIsisIfLevelHelloAuthKey variable and the authentication
         type must match.

         Authentication can be configured globally and applied to all
         ISIS levels running on this interface or it can be configured on
         a per level basis; the most specific value is used.  
         
         When tmnxIsisIfLevelHelloAuthType has a value of 'useGlobal', the
         values of tmnxIsisIfLevelHelloAuthKey and tmnxIsisIfLevelHelloAuthType
         are applied to the interfaces for this level."
    DEFVAL { useGlobal }
    ::= { tmnxIsisIfLevelEntry 4 }

tmnxIsisIfLevelPassive  OBJECT-TYPE
    SYNTAX      TruthValue
    MAX-ACCESS  read-create
    STATUS      current
    DESCRIPTION
        "The value of the object tmnxIsisIfLevelPassive specifies whether
         the interface level is running in passive mode.
        
         When tmnxIsisIfLevelPassive has the value 'true', this interface
         address is advertised for this level without running the IS-IS
         protocol on this interface level; while in passive mode, the
         interface level ignores ingress IS-IS protocol packets and does
         not transmit any IS-IS protocol packets.

         When tmnxIsisIfLevelPassive has the value 'false', this interface
         address is advertised at this IS-IS level only if it is configured
         as with the IS-IS protocol as enabled."
    DEFVAL { false }
    ::= { tmnxIsisIfLevelEntry 5 }

tmnxIsisIfLevelNumAdjacencies  OBJECT-TYPE
    SYNTAX      Unsigned32
    MAX-ACCESS  read-only
    STATUS      current
    DESCRIPTION
        "The value of the object tmnxIsisIfLevelNumAdjacencies indicates the 
         number of adjacencies on this particular level of the interface."
    ::= { tmnxIsisIfLevelEntry 6 }

tmnxIsisIfLevelISPriority  OBJECT-TYPE
    SYNTAX      Unsigned32(0..127)
    MAX-ACCESS  read-create
    STATUS      current
    DESCRIPTION
        "The value of the object tmnxIsisIfLevelISPriority specifies the 
         priority for becoming LAN Designated Intermediate System at this level.
         
         The value of tmnxIsisIfLevelISPriority shadows the value of object
         isisCircLevelISPriority to have an additional accepted value of 0."
    ::= { tmnxIsisIfLevelEntry 7 }

tmnxIsisIfLevelHelloTimer  OBJECT-TYPE
    SYNTAX      Unsigned32(1..20000)
    MAX-ACCESS  read-create
    STATUS      current
    DESCRIPTION
        "The value of the object tmnxIsisIfLevelHelloTimer specifies the 
         maximum period, in seconds, between IIH PDUs on multiaccess networks
         at this level for LANs.
        
         The value of tmnxIsisIfLevelHelloTimer shadows isisCircLevelHelloTimer 
         to store the values of hello timer in seconds."
    ::= { tmnxIsisIfLevelEntry 8 }

tmnxIsisIfLevelAdminMetric  OBJECT-TYPE
    SYNTAX      Unsigned32(0..16777215)
    MAX-ACCESS  read-create
    STATUS      current
    DESCRIPTION
        "The value of the object tmnxIsisIfLevelAdminMetric specifies the 
         default metric value of this circuit for this level.
              
         A value of 0 means that the metric is not configured; in such
         a case if the tmnxIsisReferenceBw is configured, the value of 
         the metric should be calculated using the formula :
                    
            Metric = reference-bandwidth / bandwidth.

         If the tmnxIsisReferenceBw is configured as Ten Gig (10,000,000,000)
         a 100-Mbps interface has a default metric of 100. 
          
         In order for metrics in excess of 63 to be configured wide metrics
         must be deployed.

         If the reference bandwidth is not configured then all levels will
         have a default metric of 10.

         System and loopback interface levels will always have a metric
         value of 0.

         The operational value of the metric is maintained in the object
         tmnxIsisIfLevelOperMetric."
    DEFVAL { 0 }
    ::= { tmnxIsisIfLevelEntry 9 }

tmnxIsisIfLevelOperMetric  OBJECT-TYPE
    SYNTAX      Unsigned32(0..16777215)
    MAX-ACCESS  read-only
    STATUS      current
    DESCRIPTION
        "The value of the object tmnxIsisIfLevelOperMetric indicates the
         operational value of the metric being used in this circuit for
         this level.
                
         System and loop back interface levels will have metric value of 0."
    ::= { tmnxIsisIfLevelEntry 10 }

tmnxIsisIfLvlIPv6UcastAdmMet  OBJECT-TYPE
    SYNTAX      Unsigned32(0..16777215)
    MAX-ACCESS  read-create
    STATUS      current
    DESCRIPTION
        "The value of the object tmnxIsisIfLvlIPv6UcastAdmMet specifies 
         the interface level metric for IPv6 unicast."
    DEFVAL { 0 }             
    ::= { tmnxIsisIfLevelEntry 11 }        

tmnxIsisIfLvlIPv6UcastOperMet  OBJECT-TYPE
    SYNTAX      Unsigned32(0..16777215)
    MAX-ACCESS  read-only
    STATUS      current
    DESCRIPTION
        "The value of the object tmnxIsisIfLvlIPv6UcastOperMet indicates the
         operational value of the IPv6 unicast metric being used with 
         this interface level."
    ::= { tmnxIsisIfLevelEntry 12 } 
 
tmnxIsisIfLvlIPv4McastAdmMetric  OBJECT-TYPE
    SYNTAX      Unsigned32(0..16777215)
    MAX-ACCESS  read-create
    STATUS      current
    DESCRIPTION
        "The value of the object tmnxIsisIfLvlIPv4McastAdmMetric specifies 
         the interface level metric for IPv4 multicast."
    DEFVAL { 0 }             
    ::= { tmnxIsisIfLevelEntry 13 }  

tmnxIsisIfLvlIPv6McastAdmMetric  OBJECT-TYPE
    SYNTAX      Unsigned32(0..16777215)
    MAX-ACCESS  read-create
    STATUS      current
    DESCRIPTION
        "The value of the object tmnxIsisIfLvlIPv6McastAdmMetric specifies 
         the interface level metric for IPv6 multicast."
    DEFVAL { 0 }             
    ::= { tmnxIsisIfLevelEntry 14 }    

tmnxIsisIfLevelLinkGroupName    OBJECT-TYPE
    SYNTAX      TNamedItemOrEmpty
    MAX-ACCESS  read-create
    STATUS      current
    DESCRIPTION
        "The value of the object tmnxIsisIfLevelLinkGroupName specifies the
         ISIS link group associated with this particular level of the interface."  
    DEFVAL { ''H }           
    ::= { tmnxIsisIfLevelEntry 15 }  

tmnxIsisIfLevelSdOffset     OBJECT-TYPE
    SYNTAX      Unsigned32(0..16777215)
    MAX-ACCESS  read-create
    STATUS      current
    DESCRIPTION
        "The value of the object tmnxIsisIfLevelSdOffset specifies the 
         offset by which the IS-IS interface metric should be increased
         upon receiving the signal degrade threhold event."
    DEFVAL { 0 }             
    ::= { tmnxIsisIfLevelEntry 16 } 

tmnxIsisIfLevelSfOffset     OBJECT-TYPE
    SYNTAX      Unsigned32(0..16777215)
    MAX-ACCESS  read-create
    STATUS      current
    DESCRIPTION
        "The value of the object tmnxIsisIfLevelSfOffset specifies the offset 
         by which the IS-IS interface metric should be further increased in
         addition to the offset specified by tmnxIsisIfLevelSdOffset upon
         receiving the signal fail threhold event."
    DEFVAL { 0 }             
    ::= { tmnxIsisIfLevelEntry 17 }  

tmnxIsisIfLvlIPv4McastOperMetric  OBJECT-TYPE
    SYNTAX      Unsigned32(0..16777215)
    MAX-ACCESS  read-only
    STATUS      current
    DESCRIPTION
        "The value of the object tmnxIsisIfLvlIPv4McastOperMetric indicates the    
         operational value of the interface level metric for IPv4 multicast."            
    ::= { tmnxIsisIfLevelEntry 18 }  

tmnxIsisIfLvlIPv6McastOperMetric  OBJECT-TYPE
    SYNTAX      Unsigned32(0..16777215)
    MAX-ACCESS  read-only
    STATUS      current
    DESCRIPTION
        "The value of the object tmnxIsisIfLvlIPv4McastOperMetric indicates the  
         operational value of the interface level metric for IPv6 multicast."            
    ::= { tmnxIsisIfLevelEntry 19 }    

tmnxIsisIfLevelHelloAuthKeyChain  OBJECT-TYPE
    SYNTAX      TNamedItemOrEmpty
    MAX-ACCESS  read-write
    STATUS      current
    DESCRIPTION
        "The value of tmnxIsisIfLevelHelloAuthKeyChain specifies the keychain to 
         use to sign and/or authenticate the IS-IS instance.

         The keychain name is defined by tmnxKeyChainName and is the index for
         TIMETRA-SECURITY-MIB::tmnxKeyChainTable"
    DEFVAL { ''H }
    ::= { tmnxIsisIfLevelEntry 20 }


-- --------------------------------------------------------------------------
-- tmnxIsisISAdjTable
-- --------------------------------------------------------------------------

tmnxIsisISAdjTable OBJECT-TYPE
    SYNTAX      SEQUENCE OF TmnxIsisISAdjEntry
    MAX-ACCESS  not-accessible
    STATUS      current
    DESCRIPTION
        "The tmnxIsisISAdjTable is the table of adjacencies to Intermediate Systems
        and their operational status information."
    ::= { tmnxIsisAdjObjs 1 }

tmnxIsisISAdjEntry OBJECT-TYPE
    SYNTAX      TmnxIsisISAdjEntry
    MAX-ACCESS  not-accessible
    STATUS      current
    DESCRIPTION
        "Each row entry in the tmnxIsisISAdjTable represents 
         an adjacency to an Intermediate System on this system."
    INDEX { vRtrID,
            isisSysInstance,
            isisCircIndex,
            isisISAdjIndex }
    ::= { tmnxIsisISAdjTable 1 }

TmnxIsisISAdjEntry ::=
    SEQUENCE {
             tmnxIsisISAdjExpiresIn         INTEGER,
             tmnxIsisISAdjCircLevel         INTEGER,
             tmnxIsisISAdjNeighborIP        IpAddress,
             tmnxIsisISAdjRestartSupport    TruthValue,
             tmnxIsisISAdjRestartStatus     INTEGER,
             tmnxIsisISAdjRestartSupressed  TruthValue,
             tmnxIsisISAdjNumRestarts       Unsigned32,
             tmnxIsisISAdjLastRestartTime   TimeStamp,
             tmnxIsisISAdjNeighborIPv6Type  InetAddressType,
             tmnxIsisISAdjNeighborIPv6      InetAddress,
             tmnxIsisISAdjMtEnabled         TruthValue,
             tmnxIsisISAdjMtId0             TruthValue,
             tmnxIsisISAdjMtId2             TruthValue,
             tmnxIsisISAdjMtId3             TruthValue,
             tmnxIsisISAdjMtId4             TruthValue
             }

tmnxIsisISAdjExpiresIn OBJECT-TYPE
    SYNTAX      INTEGER (1..65535)
    UNITS       "seconds"
    MAX-ACCESS  read-only
    STATUS      current
    DESCRIPTION
        "The value of the object tmnxIsisISAdjExpiresIn indicates the time
         in which the adjacency will expire if no hello packets are received."
    ::= { tmnxIsisISAdjEntry 1 }

tmnxIsisISAdjCircLevel OBJECT-TYPE
    SYNTAX     INTEGER {
                   level1(1),
                   level2(2),
                   level1L2(3),
                   unknown(4)
               }
    MAX-ACCESS read-only
    STATUS     current
    DESCRIPTION
        "The value of the object tmnxIsisISAdjCircLevel indicates the 
         circuit type of the adjacency as advertised."
    DEFVAL { unknown }
    ::= { tmnxIsisISAdjEntry 2 }

tmnxIsisISAdjNeighborIP OBJECT-TYPE
    SYNTAX     IpAddress
    MAX-ACCESS read-only
    STATUS     current
    DESCRIPTION 
        "The value of the object tmnxIsisISAdjNeighborIP indicates the 
         ip-address of the neighbor with which adjacency is formed."
    ::= { tmnxIsisISAdjEntry 3 }

tmnxIsisISAdjRestartSupport  OBJECT-TYPE
    SYNTAX      TruthValue 
    MAX-ACCESS  read-only
    STATUS      current
    DESCRIPTION
        "The value of the object tmnxIsisISAdjRestartSupport indicates whether
         adjacency supports ISIS graceful restart. 
         
         If tmnxIsisISAdjRestartSupport has a value of 'true' the adjacency 
         supports graceful restart."
    ::= { tmnxIsisISAdjEntry 4 }

tmnxIsisISAdjRestartStatus OBJECT-TYPE
    SYNTAX     INTEGER {
                   notHelping (1),         -- Adjacency is not currently being helped
                   restarting (2),         -- Received restart request from the nbr
                   restartComplete (3),    -- The nbr has completed the most recent restart
                   helping (4)             -- Nbr is helping us in restarting and has sent us a
                                           -- restart ack in response to our restart request.
               }
    MAX-ACCESS read-only
    STATUS     current
    DESCRIPTION
        "The value of the object tmnxIsisISAdjRestartStatus indicates the
         graceful restart status of the adjacency."
    ::= { tmnxIsisISAdjEntry 5 }

tmnxIsisISAdjRestartSupressed OBJECT-TYPE
    SYNTAX      TruthValue 
    MAX-ACCESS  read-only
    STATUS      current
    DESCRIPTION
        "The value of the object tmnxIsisISAdjRestartSupressed indicates if
         the adjacency has requested this router to suppress advertisement of
         the adjacency in this router's LSPs.
         
         If tmnxIsisISAdjRestartSupressed has a value of 'true' the adjacency 
         has requested to suppress advertisement of the LSPs."
    ::= { tmnxIsisISAdjEntry 6 }

tmnxIsisISAdjNumRestarts OBJECT-TYPE
    SYNTAX      Unsigned32
    MAX-ACCESS  read-only
    STATUS      current
    DESCRIPTION
        "The value of the object tmnxIsisISAdjNumRestarts indicates the number 
         of times the adjacency has attempted restart."
    ::= { tmnxIsisISAdjEntry 7 }

tmnxIsisISAdjLastRestartTime OBJECT-TYPE
    SYNTAX      TimeStamp
    MAX-ACCESS  read-only
    STATUS      current
    DESCRIPTION
        "The value of the object tmnxIsisISAdjLastRestartTime indicates the  
         last time the adjacency attempted restart."
    ::= { tmnxIsisISAdjEntry 8 }

tmnxIsisISAdjNeighborIPv6Type   OBJECT-TYPE
    SYNTAX      InetAddressType
    MAX-ACCESS  read-only
    STATUS      current
    DESCRIPTION
        "The value of the object tmnxIsisISAdjNeighborIPv6Type indicates the 
         IP address type of tmnxIsisISAdjNeighborIPv6; it will be 'ipv6', 
         'ipv6z' or 'unknown'."
    ::= { tmnxIsisISAdjEntry 9 }

tmnxIsisISAdjNeighborIPv6       OBJECT-TYPE
    SYNTAX      InetAddress (SIZE(0|16|20))
    MAX-ACCESS  read-only
    STATUS      current
    DESCRIPTION
        "The value of the object tmnxIsisISAdjNeighborIPv6 indicates the 
         IP address of the neighbor with which an IPv6-adjacency is formed; 
         this will always be an IPv6 address."
    ::= { tmnxIsisISAdjEntry 10 }

tmnxIsisISAdjMtEnabled OBJECT-TYPE
    SYNTAX      TruthValue
    MAX-ACCESS  read-only
    STATUS      current
    DESCRIPTION
        "The value of the object tmnxIsisISAdjMtEnabled indicates if the
         ISIS multi-topology protocol is supported on the neighbor. 
         
         If the value of tmnxIsisISAdjMtEnabled is 'true', ISIS multi-topology 
         protocol is enabled on the neighbor."
    ::= { tmnxIsisISAdjEntry 11 }

tmnxIsisISAdjMtId0      OBJECT-TYPE
    SYNTAX      TruthValue
    MAX-ACCESS  read-only
    STATUS      current
    DESCRIPTION
        "The value of the object tmnxIsisISAdjMtId0 indicates if the 
         native topology is supported on the neighbor. 

         If the value of tmnxIsisISAdjMtId0 is 'true', native topology is 
         supported on the neighbor."
    ::= { tmnxIsisISAdjEntry 12 }

tmnxIsisISAdjMtId2    OBJECT-TYPE
    SYNTAX      TruthValue
    MAX-ACCESS  read-only
    STATUS      current
    DESCRIPTION
        "The value of the object tmnxIsisISAdjMtId2 indicates if the 
         multi-topology for IPv6 is supported on the neighbor. 
        
         If the value of tmnxIsisISAdjMtId2 is 'true', multi-topology for IPv6 
         is supported on the neighbor."
    ::= { tmnxIsisISAdjEntry 13 }         

tmnxIsisISAdjMtId3    OBJECT-TYPE
    SYNTAX      TruthValue
    MAX-ACCESS  read-only
    STATUS      current
    DESCRIPTION
        "The value of the object tmnxIsisISAdjMtId3 indicates if the 
         MT 3 IPv4 topology is supported on the neighbor. 
        
         If the value of tmnxIsisISAdjMtId3 is 'true', MT 3 IPv4 topology is 
         supported on the neighbor."
    ::= { tmnxIsisISAdjEntry 14 } 

tmnxIsisISAdjMtId4    OBJECT-TYPE
    SYNTAX      TruthValue
    MAX-ACCESS  read-only
    STATUS      current
    DESCRIPTION
        "The value of the object tmnxIsisISAdjMtId4 indicates if the 
         MT 4 IPv6 topology is supported on the neighbor. 
        
         If the value of tmnxIsisISAdjMtId4 is 'true', MT 4 IPv6 topology is 
         supported on the neighbor."
    ::= { tmnxIsisISAdjEntry 15 } 

-- ----------------------------------------------------------------------------
--  Notification objects
-- ----------------------------------------------------------------------------

-- --------------------------------------------------------------------------
--  tmnxIsisNotificationTable
--
--  The ISIS Notification Table records fields that are required for 
--  notifications. This is a temporary table and will be removed when
--  we up-rev to the newer version of the standard ISIS mib provided by
--  the IETF.
-- --------------------------------------------------------------------------

tmnxIsisNotificationTable OBJECT-TYPE
    SYNTAX SEQUENCE OF TmnxIsisNotificationEntry
    MAX-ACCESS not-accessible
    STATUS current
    DESCRIPTION
        "Objects seen in the most recent notification this instance of 
         the IS-IS protocol."
    ::= { tmnxIsisNotificationObjs 1 }

tmnxIsisNotificationEntry OBJECT-TYPE
    SYNTAX TmnxIsisNotificationEntry
    MAX-ACCESS not-accessible
    STATUS current
    DESCRIPTION
        "Each entry defines variables relevant to notifications for one 
         instance of the IS-IS protocol."
    INDEX { vRtrID, isisSysInstance }
    ::= { tmnxIsisNotificationTable 1 }

TmnxIsisNotificationEntry ::=
    SEQUENCE {
             tmnxIsisNotifTrapLSPID           OCTET STRING,
             tmnxIsisNotifSystemLevel         INTEGER,
             tmnxIsisNotifPDUFragment         OCTET STRING,
             tmnxIsisNotifFieldLen            Integer32,
             tmnxIsisNotifMaxAreaAddress      Integer32,
             tmnxIsisNotifProtocolVersion     Integer32,
             tmnxIsisNotifLSPSize             Integer32,
             tmnxIsisNotifOriginatingBuffSize Integer32,
             tmnxIsisNotifProtocolsSupported  OCTET STRING,
             tmnxIsisNotifNbrSysId            OCTET STRING
        }

tmnxIsisNotifTrapLSPID OBJECT-TYPE
    SYNTAX OCTET STRING(SIZE(0|8))
    MAX-ACCESS read-only
    STATUS current
    DESCRIPTION
        "The object tmnxIsisNotifTrapLSPID is an Octet String that 
         uniquely identifies a Link State PDU."
    ::= { tmnxIsisNotificationEntry 1 }

tmnxIsisNotifSystemLevel OBJECT-TYPE
    SYNTAX INTEGER
               {
                   l1(1),
                   l2(2),
                   l1l2(3)
                }
     MAX-ACCESS read-only
     STATUS current
     DESCRIPTION
        "The object tmnxIsisNotifSystemLevel identifies the
         level the notification applies to."
     ::= { tmnxIsisNotificationEntry 2 }

tmnxIsisNotifPDUFragment OBJECT-TYPE
    SYNTAX OCTET STRING (SIZE(0..64))
    MAX-ACCESS read-only
    STATUS current
    DESCRIPTION
        "The object tmnxIsisNotifPDUFragment holds up to the first 64 bytes of
         a PDU that triggered the notification."
    ::= { tmnxIsisNotificationEntry 3 }

tmnxIsisNotifFieldLen OBJECT-TYPE
    SYNTAX Integer32 (0..255)
    MAX-ACCESS read-only
    STATUS current
    DESCRIPTION
        "The object tmnxIsisNotifFieldLen holds the System ID length reported
         in a PDU we received."
    ::= { tmnxIsisNotificationEntry 4 }

tmnxIsisNotifMaxAreaAddress OBJECT-TYPE
    SYNTAX Integer32 (0..255)
    MAX-ACCESS read-only
    STATUS current
    DESCRIPTION
        "The object tmnxIsisNotifMaxAreaAddress holds the Max Area Addresses 
         reported in a PDU we received."
    ::= { tmnxIsisNotificationEntry 5 }

tmnxIsisNotifProtocolVersion OBJECT-TYPE
    SYNTAX Integer32 (0..255)
    MAX-ACCESS read-only
    STATUS current
    DESCRIPTION
        "The object tmnxIsisNotifProtocolVersion holds the Protocol version 
         reported in a PDU we received."
    ::= { tmnxIsisNotificationEntry 6 }

tmnxIsisNotifLSPSize OBJECT-TYPE
    SYNTAX Integer32 (0..2147483647)
    MAX-ACCESS read-only
    STATUS current
    DESCRIPTION
        "The object tmnxIsisNotifLSPSize holds the size of LSP we received that
         is too big to forward."
    ::= { tmnxIsisNotificationEntry 7 }

tmnxIsisNotifOriginatingBuffSize OBJECT-TYPE
    SYNTAX Integer32 (0..2147483647)
    MAX-ACCESS read-only
    STATUS current
    DESCRIPTION
        "The object tmnxIsisNotifOriginatingBuffSize holds the size of 
         tmnxIsisSysOrigL1LSPBuffSize or tmnxIsisSysOrigL2LSPBuffSize 
         advertised by peer in TLV."
    ::= { tmnxIsisNotificationEntry 8 }

tmnxIsisNotifProtocolsSupported OBJECT-TYPE
    SYNTAX OCTET STRING (SIZE(0..255))
    MAX-ACCESS read-only
    STATUS current
    DESCRIPTION
        "The object tmnxIsisNotifProtocolsSupported contains the list of 
         protocols supported by an adjacent system and may be empty."
    ::= { tmnxIsisNotificationEntry 9 }

tmnxIsisNotifNbrSysId OBJECT-TYPE
    SYNTAX OCTET STRING(SIZE(0..6))
    MAX-ACCESS   accessible-for-notify
    STATUS       current
    DESCRIPTION
        "The value of the object tmnxIsisNotifNbrSysId indicates the system-id of 
         the neighbor associated with the notification."
     ::= { tmnxIsisNotificationEntry 10 }
     
    
tmnxIsisFailureReasonCode  OBJECT-TYPE
    SYNTAX          INTEGER { 
                        outOfResources (1)
                    } 
    MAX-ACCESS      accessible-for-notify
    STATUS          current
    DESCRIPTION
        "The value of tmnxIsisFailureReasonCode indicates the reason for the
         last ISIS failure which resulted in it being marked operationally 
         down.This object is used by the tmnxIsisFailureDisabled notification."
    ::= { tmnxIsisNotificationObjs 4 }
    
-- --------------------------------------------------------------------------
-- Notifications
-- --------------------------------------------------------------------------

tmnxIsisDatabaseOverload NOTIFICATION-TYPE
    OBJECTS {
        tmnxIsisNotifSystemLevel,
        isisSysL1State,
        isisSysL2State
    }
    STATUS  current
    DESCRIPTION
        "[CAUSE] The tmnxIsisDatabaseOverload notification is generated when
         the system enters or leaves the Overload state.
         
         [EFFECT] Database is overloaded.
         
         [RECOVERY] No recovery is necessary."
   ::= { tmnxIsisNotifications 1 }
   
tmnxIsisManualAddressDrops NOTIFICATION-TYPE
    OBJECTS {
        isisManAreaAddrExistState
    }
    STATUS  current
    DESCRIPTION
        "[CAUSE] This notification is generated when one of the manual area addresses
         assigned to this system is ignored when computing routes. The object
         isisManAreaAddrExistState describes the area that has been 
         dropped.

         This notification is edge triggered, and should not be regenerated
         until an address that was used in the previous computation has been 
         dropped.
         
         [EFFECT] Assigned manual area address is ignored for computing routes.

         [RECOVERY] No recovery is necessary."
    ::= { tmnxIsisNotifications 2 }
    
tmnxIsisCorruptedLSPDetected NOTIFICATION-TYPE
    OBJECTS {
        tmnxIsisNotifSystemLevel,
        tmnxIsisNotifTrapLSPID
    }
    STATUS  current
    DESCRIPTION
        "[CAUSE] The tmnxIsisCorruptedLSPDetected notification is generated when
         we find that and LSP that was stored in memory has become corrupted.  

         We forward an LSP ID. We may have independent knowledge of the ID,
         but in some implementations there is a chance that the ID itself will
         be corrupted.
         
         [EFFECT] LSP is dropped.
         
         [RECOVERY] No recovery is necessary."
    ::= { tmnxIsisNotifications 3 }

tmnxIsisMaxSeqExceedAttempt NOTIFICATION-TYPE
    OBJECTS {
        tmnxIsisNotifSystemLevel,
        tmnxIsisNotifTrapLSPID
    }
    STATUS  current
    DESCRIPTION
        "[CAUSE] The tmnxIsisMaxSeqExceedAttempt notification is generated when
         the sequence number on an LSP wraps the 32 bit sequence counter,
         we purge and wait to re-announce this information.
         Since these should not be generated rapidly, we generate an event
         each time this happens.

         While the first 6 bytes of the LSPID are ours, the other two contain
         useful information.
         
         [EFFECT] No effect.
         
         [RECOVERY] No recovery is necessary."
    ::= { tmnxIsisNotifications 4 }

tmnxIsisIDLenMismatch  NOTIFICATION-TYPE
    OBJECTS {
        tmnxIsisNotifFieldLen,
        vRtrIfIndex,
        tmnxIsisNotifPDUFragment
    }
    STATUS  current
    DESCRIPTION
        "[CAUSE] The tmnxIsisIDLenMismatch notification is sent when we receive
         a PDU with a different value of the System ID Length. 
         
         This notification includes the index to identify the circuit where 
         we saw the PDU and the header of the PDU which may help a 
         network manager identify the source of the confusion.

         This should be an edge-triggered notification. We should not send a
         second notification about PDUs received from what seem to be the same
         source. This decision is up to the agent to make, and may be based on
         the circuit or on some MAC level information.
         
         [EFFECT] No effect.
         
         [RECOVERY] No recovery is necessary."
    ::= { tmnxIsisNotifications 5 }

tmnxIsisMaxAreaAddrsMismatch NOTIFICATION-TYPE
    OBJECTS {
        tmnxIsisNotifMaxAreaAddress,
        vRtrIfIndex,
        tmnxIsisNotifPDUFragment
    }
    STATUS  current
    DESCRIPTION
        "[CAUSE] The tmnxIsisMaxAreaAddrsMismatch notification is sent when we receive
         a PDU with a different value of the Maximum Area Addresses.  
         
         This notification includes the header of the packet, which may help a 
         network manager identify the source of the confusion.

         This should be an edge-triggered notification. We should not send a 
         second notification about PDUs received from what seem to be the same
         source.
         
         [EFFECT] No effect.
         
         [RECOVERY] No recovery is necessary."
    ::= { tmnxIsisNotifications 6 }

tmnxIsisOwnLSPPurge NOTIFICATION-TYPE
    OBJECTS {
        vRtrIfIndex,
        tmnxIsisNotifTrapLSPID,
        tmnxIsisNotifSystemLevel
    }
    STATUS  current
    DESCRIPTION
        "[CAUSE] The tmnxIsisOwnLSPPurge notification is sent when we receive 
         a PDU with our SystemID and zero age. 
         
         This notification includes the circuit Index if available, 
         which may help a network manager identify the source of the 
         confusion.
         
         [EFFECT] No effect.
         
         [RECOVERY] No recovery is necessary."
    ::= { tmnxIsisNotifications 7 }

tmnxIsisSequenceNumberSkip NOTIFICATION-TYPE
    OBJECTS {
        tmnxIsisNotifTrapLSPID,
        vRtrIfIndex,
        tmnxIsisNotifSystemLevel
    }
    STATUS  current
    DESCRIPTION
        "[CAUSE] The tmnxIsisSequenceNumberSkip notification is sent when we need to
         increase the sequence number by more than one.
         
         When we receive an LSP with out System ID and different contents, we
         may need to reissue the LSP with a higher sequence number.

         If two Intermediate Systems are configured with 
         the same System ID, this notification will fire.
         
         [EFFECT] No effect.
         
         [RECOVERY] No recovery is necessary."
    ::= { tmnxIsisNotifications 8 }

tmnxIsisAutTypeFail NOTIFICATION-TYPE
    OBJECTS {
        tmnxIsisNotifSystemLevel,
        tmnxIsisNotifPDUFragment,
        vRtrIfIndex
    }
    STATUS  current
    DESCRIPTION
        "[CAUSE] The tmnxIsisAutTypeFail notification is sent when we receive a
         PDU with the wrong authentication type field. 
         
         This notification includes the header of the packet, which may help a
         network manager identify the source of the confusion.

         This should be an edge-triggered notification. We should not send a 
         second notification about PDUs received from what seem to be the 
         same source.
         
         [EFFECT] No effect.
         
         [RECOVERY] No recovery is necessary."
    ::= { tmnxIsisNotifications 9 }

tmnxIsisAuthFail NOTIFICATION-TYPE
    OBJECTS {
        tmnxIsisNotifSystemLevel,
        tmnxIsisNotifPDUFragment,
        vRtrIfIndex
    }
    STATUS  current
    DESCRIPTION
        "[CAUSE] The tmnxIsisAuthFail notification is sent when we receive a 
         PDU with incorrect authentication information field. 
         
         This notification includes the header of the packet, which may help a
         network manager identify the source of the confusion.

         This should be an edge-triggered notification. We should not send a 
         second notification about PDUs received from what seem to be the same
         source.
         
         [EFFECT] No effect.
         
         [RECOVERY] No recovery is necessary."
    ::= { tmnxIsisNotifications 10 }

tmnxIsisVersionSkew NOTIFICATION-TYPE
    OBJECTS {
        tmnxIsisNotifProtocolVersion,
        tmnxIsisNotifSystemLevel,
        tmnxIsisNotifPDUFragment,
        vRtrIfIndex
    }
    STATUS  current
    DESCRIPTION
        "[CAUSE] The tmnxIsisVersionSkew notification is sent when we receive a 
         Hello PDU from an IS running a different version of the protocol.
         
         This notification includes the header of the packet, which may 
         help a network manager identify the source of the confusion.

         This should be an edge-triggered notification.
         We should not send a second notification about
         PDUs received from what seem to be the same source.
         This decision is up to the agent to make, and may
         be based on the circuit or on some MAC level
         information.
         
         [EFFECT] No effect.
         
         [RECOVERY] No recovery is necessary."

    ::= { tmnxIsisNotifications 11 }

tmnxIsisAreaMismatch NOTIFICATION-TYPE
    OBJECTS {
        tmnxIsisNotifLSPSize,
        tmnxIsisNotifSystemLevel,
        vRtrIfIndex,
        tmnxIsisNotifPDUFragment
    }
    STATUS  current
    DESCRIPTION
        "[CAUSE] The tmnxIsisAreaMismatch notification is sent when we receive a 
         Hello PDU from an IS which does not share any area address. 
          
         This notification includes the header of the packet, which may 
         help a network manager identify the source of the  confusion.

         This should be an edge-triggered notification.
         We should not send a second notification about
         PDUs received from what seem to be the same source.
         This decision is up to the agent to make, and may
         be based on the circuit or on some MAC level
         information.
         
         [EFFECT] No effect.
         
         [RECOVERY] No recovery is necessary."
    ::= { tmnxIsisNotifications 12 }

tmnxIsisRejectedAdjacency NOTIFICATION-TYPE
    OBJECTS {
        tmnxIsisNotifSystemLevel,
        vRtrIfIndex
    }
    STATUS  current
    DESCRIPTION
        "[CAUSE] The tmnxIsisRejectedAdjacency notification is sent when we  
         receive a Hello PDU from an IS, but do not establish an 
         adjacency due to a lack of resources.

         This should be an edge-triggered notification.
         We should not send a second notification about
         PDUs received from the same source.
         
         [EFFECT] No effect.
         
         [RECOVERY] No recovery is necessary."
    ::= { tmnxIsisNotifications 13 }

tmnxIsisLSPTooLargeToPropagate NOTIFICATION-TYPE
    OBJECTS {
        tmnxIsisNotifLSPSize,
        tmnxIsisNotifSystemLevel,
        tmnxIsisNotifTrapLSPID,
        vRtrIfIndex
    }
    STATUS  current
    DESCRIPTION
        "[CAUSE] The tmnxIsisLSPTooLargeToPropagate notification is sent when 
         we attempt to propagate an LSP which is larger than the 
         dataLinkBlockSize for a circuit.

         This should be an edge-triggered notification.
         We should not send a second notification about
         PDUs received from the same source.
         
         [EFFECT] No effect.
         
         [RECOVERY] No recovery is necessary."
    ::= { tmnxIsisNotifications 14 }

tmnxIsisOrigLSPBufSizeMismatch NOTIFICATION-TYPE
    OBJECTS {
        tmnxIsisNotifOriginatingBuffSize,
        tmnxIsisNotifSystemLevel,
        tmnxIsisNotifTrapLSPID,
        vRtrIfIndex
    }
    STATUS  current
    DESCRIPTION
        "[CAUSE] The tmnxIsisOrigLSPBufSizeMismatch notification is sent when
         a Level 1 LSP or Level 2 LSP is received which is larger than
         the local value for isisSysOrigL1LSPBuffSize or
         isisSysOrigL2LSPBuffSize respectively, or when
         a Level 1 LSP or Level2 LSP is received containing
         the originatingLSPBufferSize option and the value in
         the PDU option field does not match the local value
         for isisSysOrigL1LSPBuffSize or isisSysOrigL2LSPBuffSize
         respectively.  We pass up the size from the option
         field or the size of the LSP that exceeds our
         configuration.

         This should be an edge-triggered notification.
         We should not send a second notification about
         PDUs received from the same source.
         
         [EFFECT] No effect.
         
         [RECOVERY] No recovery is necessary."
    ::= { tmnxIsisNotifications 15 }

tmnxIsisProtoSuppMismatch NOTIFICATION-TYPE
    OBJECTS {
        tmnxIsisNotifProtocolsSupported,
        tmnxIsisNotifSystemLevel,
        tmnxIsisNotifTrapLSPID,
        vRtrIfIndex
    }
    STATUS  current
    DESCRIPTION
        "[CAUSE] The tmnxIsisProtoSuppMismatch notification is sent when a
         non-pseudonode segment 0 LSP is received that has no matching
         protocols supported.
         
         This may be because the system does not generate
         the field, or because there are no common elements.
         
         The list of protocols supported should be included
         in the notification: it may be empty if the TLV
         is not supported, or if the TLV is empty.

         This should be an edge-triggered notification.
         We should not send a second notification about
         PDUs received from the same source.
         
         [EFFECT] No effect.
         
         [RECOVERY] No recovery is necessary."
    ::= { tmnxIsisNotifications 16 }

tmnxIsisAdjacencyChange NOTIFICATION-TYPE
    OBJECTS {
        tmnxIsisNotifSystemLevel,
        vRtrIfIndex,
        tmnxIsisNotifTrapLSPID,
        isisISAdjState
    }
    STATUS current
    DESCRIPTION
        "[CAUSE] The tmnxIsisAdjacencyChange notification is sent when an
         adjacency changes state, entering or leaving state up. 
         
         The first 6 bytes of the tmnxIsisNotifTrapLSPID are the SystemID of
         the adjacent IS.
         
         The isisISAdjState is the new state of the adjacency.
         
         [EFFECT] No effect.
         
         [RECOVERY] No recovery is necessary."
    ::= { tmnxIsisNotifications 17 }

tmnxIsisCircIdExhausted NOTIFICATION-TYPE
    OBJECTS {
        vRtrIfIndex,
        tmnxIsisNotifSystemLevel
    }
    STATUS current
    DESCRIPTION
        "[CAUSE] The tmnxIsisCircIdExhausted notification is sent when the
         specific ISIS level cannot be started on a LAN interface as
         a unique circid could not be assigned due to the exhaustion of
         the circid space.
        
         This could happen only on the broadcast interfaces.

         [EFFECT] In such a case the interface is marked operationally 
         down. 
         
         [RECOVERY] When an operationally up interface is deleted, the 
         circid can be reused by any interface which is waiting to
         receive a unique circid."
    ::= { tmnxIsisNotifications 18 }

tmnxIsisAdjRestartStatusChange NOTIFICATION-TYPE
    OBJECTS {
        tmnxIsisNotifSystemLevel,
        vRtrIfIndex,
        tmnxIsisISAdjRestartStatus
    }
    STATUS  current
    DESCRIPTION
        "[CAUSE] The tmnxIsisAdjRestartStatusChange notification is sent when
         an adjancency's graceful restart status changes.
         
         The tmnxIsisISAdjRestartStatus is the new graceful restart state of
         the adjacency.
         
         [EFFECT] No effect.
         
         [RECOVERY] No recovery is necessary."
    ::= { tmnxIsisNotifications 19 }

tmnxIsisLdpSyncTimerStarted NOTIFICATION-TYPE
    OBJECTS {
        vRtrIfIndex,
        tmnxIsisIfLdpSyncTimerState
    }
    STATUS  current
    DESCRIPTION
        "[CAUSE] The tmnxIsisLdpSyncTimerStarted notification is sent when the
         vRtrIfLdpSyncTimer is started.
         
         The timer is started from the time the LDP session to the 
         neighbor is up over the interface.
         
         [EFFECT] This allows for the label FEC bindings to be exchanged.
         
         [RECOVERY] No recovery is necessary."
    ::= { tmnxIsisNotifications 20 }

tmnxIsisLdpSyncExit NOTIFICATION-TYPE
    OBJECTS {
        vRtrIfIndex,
        tmnxIsisIfLdpSyncTimerState
    }
    STATUS  current
    DESCRIPTION
        "[CAUSE] The tmnxIsisLdpSyncExit notification is sent when 
         IGP-LDP synchronization has stopped.  
         
         The cause of this event is indicated by tmnxIsisIfLdpSyncTimerState, 
         one of them being expiry of vRtrIfLdpSyncTimer.  
         
         [EFFECT] The IGP link metric is restored to normal levels.
                  
         [RECOVERY] No recovery is necessary."
    ::= { tmnxIsisNotifications 21 }

tmnxIsisExportLimitReached  NOTIFICATION-TYPE
    OBJECTS {
        tmnxIsisNotifSystemLevel,
        tmnxIsisExportLimit
    }
    STATUS  current
    DESCRIPTION
        "[CAUSE] The tmnxIsisExportLimitReached notification is sent when the 
         total number of exported routes for the level is equal to the 
         configured limit for exported routes, tmnxIsisExportLimit. 
         
         [EFFECT] Additional routes would not be exported into this ISIS level from
         the route table.
                  
         [RECOVERY] Change ISIS export policy."
    ::= { tmnxIsisNotifications 22 }

tmnxIsisExportLimitWarning  NOTIFICATION-TYPE
    OBJECTS {
        tmnxIsisNotifSystemLevel,
        tmnxIsisExportLimit,
        tmnxIsisExportLimitLogPercent
    }
    STATUS  current
    DESCRIPTION
        "[CAUSE] The tmnxIsisExportLimitWarning notification is sent when the 
         total number of exported routes or the level is equal to the  
         configured percent, tmnxIsisExportLimitLogPercent
         of the export limit, tmnxIsisExportLimit. 
         
         Additional routes will continue to be exported into this 
         ISIS level from the route table till the export limit is reached.
         
         [EFFECT] No effect.
         
         [RECOVERY] No recovery is necessary."
    ::= { tmnxIsisNotifications 23 }

tmnxIsisRoutesExpLmtDropped  NOTIFICATION-TYPE
    OBJECTS {
        tmnxIsisNotifSystemLevel,
        tmnxIsisExportLimit
    }
    STATUS  current
    DESCRIPTION
        "[CAUSE] The tmnxIsisRoutesExpLmtDropped notification is sent when the
         total number of exported routes from the route table to this 
         ISIS level drops below the configured export limit,
         tmnxIsisExportLimit.
         
         [EFFECT] No effect.
         
         [RECOVERY] No recovery is necessary."
    ::= { tmnxIsisNotifications 24 }


    
tmnxIsisFailureDisabled  NOTIFICATION-TYPE
    OBJECTS {
        tmnxIsisFailureReasonCode
    }
    STATUS  current
    DESCRIPTION
        "[CAUSE] A tmnxIsisFailureDisabled notification is generated when ISIS
         is operationally brought down. Reason for the failure is indicated by
         tmnxIsisFailureReasonCode.

         [EFFECT] ISIS is now operationally down.

         [RECOVERY] ISIS will auto restart."
    ::= { tmnxIsisNotifications 28 }
       
-- --------------------------------------------------------------------------
-- Group Statements
-- --------------------------------------------------------------------------

tmnxIsisGroup OBJECT-GROUP
    OBJECTS {
                tmnxIsisLastEnabledTime,
                tmnxIsisAuthKey,
                tmnxIsisAuthType,
                tmnxIsisAuthCheck,
                tmnxIsisExportPolicy1,
                tmnxIsisExportPolicy2,
                tmnxIsisExportPolicy3,
                tmnxIsisExportPolicy4,
                tmnxIsisExportPolicy5,
                tmnxIsisLspLifetime,
                tmnxIsisOverloadTimeout,
                tmnxIsisOperState,
                tmnxIsisReferenceBw,
                tmnxIsisTrafficEng,
                tmnxIsisShortCuts,
                tmnxIsisSpfHoldTime,
                tmnxIsisLastSpfRun,
                tmnxIsisGracefulRestart,
                tmnxIsisOverloadOnBoot,
                tmnxIsisOverloadOnBootTimeout,
                tmnxIsisSpfWait,
                tmnxIsisSpfInitialWait,
                tmnxIsisSpfSecondWait,
                tmnxIsisLspMaxWait,
                tmnxIsisLspInitialWait,
                tmnxIsisLspSecondWait,
                tmnxIsisCsnpAuthentication,
                tmnxIsisHelloAuthentication,
                tmnxIsisPsnpAuthentication,
                tmnxIsisGRHelperMode,
                tmnxIsisEnableIPv4,
                tmnxIsisUnicastImport,
                tmnxIsisMulticastImport,
                tmnxIsisStrictAdjacencyCheck,
                tmnxIsisManualSpfTrigger,
                tmnxIsisMultiTopology,
                tmnxIsisMultiTopoIPv6Ucast,
                tmnxIsisIPv6RoutingTopo,
                tmnxIsisSysOrigL1LSPBuffSize,
                tmnxIsisSysOrigL2LSPBuffSize,
                tmnxIsisLdpSyncAdminState, 
                tmnxIsisIPv6UnicastImport,
                tmnxIsisIPv6MulticastImport,
                tmnxIsisAdvertisePassiveOnly,
                tmnxIsisDefaultRouteTag,
                tmnxIsisSuppressDefault,
                tmnxIsisLdpOverRsvp,
                tmnxIsisExportLimit,
                tmnxIsisExportLimitLogPercent,
                tmnxIsisTotalL1ExportedRoutes,
                tmnxIsisTotalL2ExportedRoutes,
                tmnxIsisRsvpShortcut,
                tmnxIsisAdvertiseTunnelLink,
                tmnxIsisIidTlv,
                tmnxIsisL1MacAddress,
                tmnxIsisL2MacAddress,
                tmnxIsisSysOperL1LSPBuffSize,
                tmnxIsisSysOperL2LSPBuffSize,
                tmnxIsisLoopfreeAlternate,
                tmnxIsisIPv4McastRoutingTopo,
                tmnxIsisIPv6McastRoutingTopo,
                tmnxIsisMultiTopoIPv4Mcast,
                tmnxIsisMultiTopoIPv6Mcast,
                tmnxIsisOverloadMaxMetric,
                tmnxIsisOverloadOnBootMaxMetric,
                tmnxIsisRouterId,
                tmnxIsisAdvRtrCapability,
                tmnxIsisHelloPadding,
                tmnxIsisLspRefreshInterval,
                tmnxIsisIgnoreLspErrors,
                tmnxIsisLevelAuthKey,
                tmnxIsisLevelAuthType,
                tmnxIsisLevelExtPreference,
                tmnxIsisLevelPreference,
                tmnxIsisLevelWideMetricsOnly,
                tmnxIsisLevelOverloadStatus,
                tmnxIsisLevelOverloadTimeLeft,
                tmnxIsisLevelNumLSPs,
                tmnxIsisLevelCsnpAuthentication,
                tmnxIsisLevelHelloAuthentication,
                tmnxIsisLevelPsnpAuthentication,
                tmnxIsisLevelDefMetric,
                tmnxIsisLevelIPv6DefMetric,
                tmnxIsisLevelLoopfreeAltExclude,
                tmnxIsisLevelSpbBridgePriority,
                tmnxIsisLevelSpbForwardTreeTopo,
                tmnxIsisLevelDefIPv4McastMetric,
                tmnxIsisLevelDefIPv6McastMetric,
                tmnxIsisLevelAdvRtrCapability,
                tmnxIsisLevelAuthKeyChain,
                tmnxIsisStatsSpfRuns,
                tmnxIsisStatsLSPRegenerations,
                tmnxIsisStatsInitiatedPurges,
                tmnxIsisStatsLSPRecd,
                tmnxIsisStatsLSPDrop,
                tmnxIsisStatsLSPSent,
                tmnxIsisStatsLSPRetrans,
                tmnxIsisStatsIIHRecd,
                tmnxIsisStatsIIHDrop,
                tmnxIsisStatsIIHSent,
                tmnxIsisStatsIIHRetrans,
                tmnxIsisStatsCSNPRecd,
                tmnxIsisStatsCSNPDrop,
                tmnxIsisStatsCSNPSent,
                tmnxIsisStatsCSNPRetrans,
                tmnxIsisStatsPSNPRecd,
                tmnxIsisStatsPSNPDrop,
                tmnxIsisStatsPSNPSent,
                tmnxIsisStatsPSNPRetrans,
                tmnxIsisStatsUnknownRecd,
                tmnxIsisStatsUnknownDrop,
                tmnxIsisStatsUnknownSent,
                tmnxIsisStatsUnknownRetrans,
                tmnxIsisStatsCSPFRequests,
                tmnxIsisStatsCSPFDroppedRequests,
                tmnxIsisStatsCSPFPathsFound,
                tmnxIsisStatsCSPFPathsNotFound,
                tmnxIsisStatsLfaRuns,
                tmnxIsisHostName,
                tmnxIsisRouteLevel,
                tmnxIsisRouteSpfRunNumber,
                tmnxIsisRouteMetric,
                tmnxIsisRouteType,
                tmnxIsisRouteNHopSysID,
                tmnxIsisRouteTag,
                tmnxIsisRouteBkupFlags,
                tmnxIsisRouteBkupNextHopTy,
                tmnxIsisRouteBkupNextHopType,
                tmnxIsisRouteBkupNextHop,
                tmnxIsisRouteBkupMetric,
                tmnxIsisRouteNextHopType,
                tmnxIsisRouteNextHopOwner,
                tmnxIsisRouteNHOwnerAuxInfo,
                tmnxIsisRouteBkupNHType,
                tmnxIsisRouteBkupNHOwner,
                tmnxIsisRouteBkupNHOwnAxInfo,
                tmnxIsisPathMetric,
                tmnxIsisPathSNPA,
                tmnxIsisPathLfaIfIndex,
                tmnxIsisPathLfaNHop,
                tmnxIsisPathLfaMetric,
                tmnxIsisPathLfaType,
                tmnxIsisPathRouteType, 
                tmnxIsisLSPSeq,
                tmnxIsisLSPChecksum,
                tmnxIsisLSPLifetimeRemain,
                tmnxIsisLSPVersion,
                tmnxIsisLSPPktType,
                tmnxIsisLSPPktVersion,
                tmnxIsisLSPMaxArea,
                tmnxIsisLSPSysIdLen,
                tmnxIsisLSPAttributes,
                tmnxIsisLSPUsedLen,
                tmnxIsisLSPAllocLen,
                tmnxIsisLSPBuff,
                tmnxIsisLSPZeroRLT,
                tmnxIsisSpfLogRunTime,
                tmnxIsisSpfLogL1Nodes,
                tmnxIsisSpfLogL2Nodes,
                tmnxIsisSpfLogEventCount,
                tmnxIsisSpfLogLastTriggerLSPId,
                tmnxIsisSpfLogTriggerReason,
                tmnxIsisSpfLogType,                                                     
                tmnxIsisSummRowStatus,
                tmnxIsisSummLevel,
                tmnxIsisSummRouteTag,
                tmnxIsisLfaNodesCovered,
                tmnxIsisLfaTotalNodes,
                tmnxIsisLfaNodeCoverage,
                tmnxIsisLfaIPv4NodesCovered,
                tmnxIsisLfaIPv4TotalNodes,
                tmnxIsisLfaIPv4Coverage, 
                tmnxIsisLfaIPv6NodesCovered, 
                tmnxIsisLfaIPv6TotalNodes, 
                tmnxIsisLfaIPv6Coverage,
                tmnxIsisOperRouterId,
                tmnxIsisAuthKeyChain,
                tmnxIsisStatsPartSpfRuns,
                tmnxIsisStatsPartSpfTimeStamp,
                tmnxIsisNotifTrapLSPID,
                tmnxIsisNotifSystemLevel,
                tmnxIsisNotifPDUFragment,
                tmnxIsisNotifFieldLen,
                tmnxIsisNotifMaxAreaAddress,
                tmnxIsisNotifProtocolVersion,
                tmnxIsisNotifLSPSize,
                tmnxIsisNotifOriginatingBuffSize,
                tmnxIsisNotifProtocolsSupported
    }
    STATUS    current
    DESCRIPTION
        "The group of objects supporting management of ISIS system objects
         on release 12.0 Alcatel-Lucent SROS series systems."
    ::= { tmnxIsisGroups 1 }
                                                   
tmnxIsisIfGroup OBJECT-GROUP
    OBJECTS {
                tmnxIsisIfRowStatus,
                tmnxIsisIfLastChanged,
                tmnxIsisIfAdminState,
                tmnxIsisIfOperState,
                tmnxIsisIfCsnpInterval,
                tmnxIsisIfHelloAuthKey,
                tmnxIsisIfHelloAuthType,
                tmnxIsisIfLspPacingInterval,
                tmnxIsisIfCircIndex,
                tmnxIsisIfRetransmitInterval,
                tmnxIsisIfTypeDefault,
                tmnxIsisIfEnableBfd,
                tmnxIsisIfIPv6Unicast,  
                tmnxIsisIfTeMetric,
                tmnxIsisIfTeState,
                tmnxIsisIfAdminGroup,
                tmnxIsisIfLdpSyncState,
                tmnxIsisIfLdpSyncMaxMetric,
                tmnxIsisIfLdpSyncTimerState,
                tmnxIsisIfLdpSyncTimeLeft,
                tmnxIsisIfRouteTag,
                tmnxIsisIfIPv6EnableBfd,
                tmnxIsisIfHelloAuth,
                tmnxIsisIfLoopfreeAltExclude,
                tmnxIsisIfOperType,
                tmnxIsisIfIPv4Mcast,
                tmnxIsisIfIPv6Mcast,
                tmnxIsisIfBerState,
                tmnxIsisIfIPv4IncludeBfdTlv,    
                tmnxIsisIfIPv6IncludeBfdTlv,    
                tmnxIsisIfHelloAuthKeyChain,
                tmnxIsisIfLevelLastChangeTime,
                tmnxIsisIfLevelHelloAuthKey,
                tmnxIsisIfLevelHelloAuthType,
                tmnxIsisIfLevelPassive,
                tmnxIsisIfLevelNumAdjacencies,
                tmnxIsisIfLevelISPriority,
                tmnxIsisIfLevelHelloTimer,
                tmnxIsisIfLevelAdminMetric,
                tmnxIsisIfLevelOperMetric,
                tmnxIsisIfLvlIPv6UcastAdmMet,
                tmnxIsisIfLvlIPv6UcastOperMet,
                tmnxIsisIfLvlIPv4McastAdmMetric,
                tmnxIsisIfLvlIPv6McastAdmMetric,
                tmnxIsisIfLevelLinkGroupName,
                tmnxIsisIfLevelSdOffset,
                tmnxIsisIfLevelSfOffset,
                tmnxIsisIfLvlIPv4McastOperMetric,
                tmnxIsisIfLvlIPv6McastOperMetric,
                tmnxIsisIfLevelHelloAuthKeyChain
            }
    STATUS    current
    DESCRIPTION
        "The group of objects supporting management of
         ISIS interface objects on Alcatel SROS series systems."
    ::= { tmnxIsisGroups 2 }
    
tmnxIsisAdjGroup OBJECT-GROUP
    OBJECTS {
                tmnxIsisISAdjExpiresIn,
                tmnxIsisISAdjCircLevel,
                tmnxIsisISAdjNeighborIP,
                tmnxIsisISAdjRestartSupport,
                tmnxIsisISAdjRestartStatus,
                tmnxIsisISAdjRestartSupressed,
                tmnxIsisISAdjNumRestarts,
                tmnxIsisISAdjLastRestartTime,
                tmnxIsisISAdjNeighborIPv6Type,
                tmnxIsisISAdjNeighborIPv6,
                tmnxIsisISAdjMtEnabled,
                tmnxIsisISAdjMtId0,
                tmnxIsisISAdjMtId2,
                tmnxIsisISAdjMtId3,
                tmnxIsisISAdjMtId4
            }
    STATUS    current
    DESCRIPTION
        "The group of objects supporting management of
         ISIS adjacencies objects on Alcatel SROS series systems."
    ::= { tmnxIsisGroups 3 }

tmnxIsisLFAV12v0Group OBJECT-GROUP
    OBJECTS {
                tmnxIsisExLastChanged,
                tmnxIsisLFAExcludePolicy1,
                tmnxIsisLFAExcludePolicy2,
                tmnxIsisLFAExcludePolicy3,
                tmnxIsisLFAExcludePolicy4,
                tmnxIsisLFAExcludePolicy5,
                tmnxIsisIfRouteNHTemplate
            }
   STATUS    current
   DESCRIPTION
       "The group of objects supporting management of ISIS system objects on 
        Alcatel-Lucent 12.0 release of SROS series systems."
   ::= { tmnxIsisGroups 4 }

tmnxIsisNotifyObjsGroup OBJECT-GROUP
    OBJECTS {
                tmnxIsisNotifNbrSysId,
                tmnxIsisFailureReasonCode
            }
    STATUS    current
    DESCRIPTION
        "The group of notification objects supporting management of
         ISIS notification objects on Alcatel-Lucent SROS series systems."
    ::= { tmnxIsisGroups 100 }

tmnxIsisNotifyGroup NOTIFICATION-GROUP
     NOTIFICATIONS {
                 tmnxIsisDatabaseOverload,
                 tmnxIsisManualAddressDrops,
                 tmnxIsisCorruptedLSPDetected,
                 tmnxIsisMaxSeqExceedAttempt,
                 tmnxIsisIDLenMismatch,
                 tmnxIsisMaxAreaAddrsMismatch,
                 tmnxIsisOwnLSPPurge,
                 tmnxIsisSequenceNumberSkip,
                 tmnxIsisAutTypeFail,
                 tmnxIsisAuthFail,
                 tmnxIsisVersionSkew,
                 tmnxIsisAreaMismatch,
                 tmnxIsisRejectedAdjacency,
                 tmnxIsisLSPTooLargeToPropagate,
                 tmnxIsisOrigLSPBufSizeMismatch,
                 tmnxIsisProtoSuppMismatch,
                 tmnxIsisAdjacencyChange,
                 tmnxIsisCircIdExhausted,
                 tmnxIsisAdjRestartStatusChange,
                 tmnxIsisLdpSyncTimerStarted,
                 tmnxIsisLdpSyncExit,
                 tmnxIsisExportLimitReached,
                 tmnxIsisExportLimitWarning,
                 tmnxIsisRoutesExpLmtDropped,
                 tmnxIsisFailureDisabled                 
            }
     STATUS current
     DESCRIPTION
         "The group of notifications supporting management of
          ISIS notifications on Alcatel-Lucent SROS series systems."
     ::= { tmnxIsisGroups 101 }
     
-- --------------------------------------------------------------------------
-- Compliance Statements
-- --------------------------------------------------------------------------

tmnxIsisCompliance MODULE-COMPLIANCE
    STATUS  current
    DESCRIPTION
            "The compliance statement for management of ISIS routing protocol
             on Alcatel-Lucent 7xxx series systems."
    MODULE  -- this module
        MANDATORY-GROUPS {
            tmnxIsisGroup,
            tmnxIsisIfGroup,
            tmnxIsisAdjGroup,
            tmnxIsisLFAV12v0Group      
        }
    ::= { tmnxIsisCompliances 1 }
    
tmnxIsisNotifyCompliance MODULE-COMPLIANCE
    STATUS  current
    DESCRIPTION
        "The compliance statement for ISIS notifications
         on Alcatel-Lucent SROS series systems."
    MODULE  -- this module
        MANDATORY-GROUPS {
            tmnxIsisNotifyGroup
        }
    ::= { tmnxIsisCompliances 2 }    
         
END
