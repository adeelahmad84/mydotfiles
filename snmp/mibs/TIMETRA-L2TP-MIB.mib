TIMETRA-L2TP-MIB DEFINITIONS ::= BEGIN

IMPORTS
    Integer32, Unsigned32, Counter32, Gauge32,
    Counter64, TimeTicks, MODULE-IDENTITY,
    OBJECT-TYPE, NOTIFICATION-TYPE
                                                                FROM SNMPv2-SMI

    CounterBasedGauge64                                           FROM HCNUM-TC

    RowStatus, TEXTUAL-CONVENTION, 
    DisplayString, TimeStamp, TruthValue,
    MacAddress
                                                                 FROM SNMPv2-TC

    InetAddressPrefixLength,
    InetAddress, InetAddressType, InetPortNumber,
    InetAddressIPv4
                                                          FROM INET-ADDRESS-MIB

    InterfaceIndexOrZero
                                                                    FROM IF-MIB

    OBJECT-GROUP, MODULE-COMPLIANCE,
    NOTIFICATION-GROUP
                                                               FROM SNMPv2-CONF

    timetraSRMIBModules, tmnxSRObjs, tmnxSRConfs, 
    tmnxSRNotifyPrefix
                                                        FROM TIMETRA-GLOBAL-MIB

    TmnxAdminState, TmnxOperState, TmnxActionType, 
    TNamedItem, TNamedItemOrEmpty, TItemDescription,
    TmnxVRtrIDOrZero,
    TmnxServId,
    TmnxSubIdentStringOrEmpty, TmnxSubProfileStringOrEmpty,
    TmnxSubRadServAlgorithm,
    TmnxSlaProfileStringOrEmpty, TmnxAncpStringOrZero,
    TmnxSubMgtIntDestIdOrEmpty, TmnxAppProfileStringOrEmpty,
    TmnxDefSubIdSource, TmnxAsciiSpecification,
    TmnxPppoeSessionInfoOrigin, TmnxPppoeUserNameOrEmpty,
    TmnxPppoeSessionType, TmnxManagedRouteStatus,
    TmnxPppNcpProtocol,
    TDirection,
    TPIRRateOverride,
    TCIRRateOverride,
    TBurstSizeBytesOverride,
    TQosOverrideType,
    TmnxAccessLoopEncapDataLink, TmnxAccessLoopEncaps1,
    TmnxAccessLoopEncaps2,
    TmnxMlpppEpClass,
    TmnxSubNasPortPrefixType, TmnxSubNasPortSuffixType,
    TmnxSubNasPortTypeType, TmnxBinarySpecification
                                                            FROM TIMETRA-TC-MIB

    vRtrID, vRtrIfName                                          
                                                          FROM TIMETRA-VRTR-MIB

    tmnxChassisIndex, tmnxCardSlotNum, tmnxMDASlotNum
                                                       FROM TIMETRA-CHASSIS-MIB

    TmnxPppCpState  
                                                           FROM TIMETRA-PPP-MIB
    svcId, iesIfIndex
                                                          FROM TIMETRA-SERV-MIB
    ;
timetraL2tpMIBModule    MODULE-IDENTITY
        LAST-UPDATED "201401010000Z"
        ORGANIZATION "Alcatel-Lucent"
        CONTACT-INFO
            "Alcatel-Lucent SROS Support
             Web: http://support.alcatel-lucent.com"
    DESCRIPTION
    "This document is the SNMP MIB module to manage and provision
    the Layer Two Tunneling Protocol (L2TP) for the Alcatel-Lucent SROS device.

    Copyright 2009-2014 Alcatel-Lucent. All rights reserved.
    Reproduction of this document is authorized on the condition that
    the foregoing copyright notice is included.

    This SNMP MIB module (Specification) embodies Alcatel-Lucent's
    proprietary intellectual property. Alcatel-Lucent retains all title and
    ownership in the Specification, including any revisions.

    Alcatel-Lucent grants all interested parties a non-exclusive
    license to use and distribute an unmodified copy of this
    Specification in connection with management of Alcatel-Lucent products,
    and without fee, provided this copyright notice and license appear
    on all copies.

    This Specification is supplied 'as is', and Alcatel-Lucent
    makes no warranty, either express or implied, as to the use,
    operation, condition, or performance of the Specification."

--
--  Revision History
--
    REVISION        "201401010000Z"
    DESCRIPTION     "Rev 12.0                1 Jan 2014 00:00
                     12.0 release of the TIMETRA-L2TP-MIB."

    REVISION        "201102010000Z"
    DESCRIPTION     "Rev 9.0                 1 Feb 2011 00:00
                     9.0 release of the TIMETRA-L2TP-MIB."

    REVISION        "200902280000Z"
    DESCRIPTION     "Rev 7.0                28 Feb 2009 00:00
                     7.0 release of the TIMETRA-L2TP-MIB."

    ::= { timetraSRMIBModules 60 }

-- ----------------------------------------------------------------------------
--  Alcatel-Lucent SROS series L2TP MIB structure
-- ----------------------------------------------------------------------------
tmnxL2tp                      OBJECT IDENTIFIER ::= { tmnxSRObjs 60 }
    tmnxL2tpObjs              OBJECT IDENTIFIER ::= { tmnxL2tp 1 }
    tmnxL2tpNotificationObjs  OBJECT IDENTIFIER ::= { tmnxL2tp 2 }

tmnxL2tpConformance           OBJECT IDENTIFIER ::= { tmnxSRConfs 60 }
    tmnxL2tpCompliances       OBJECT IDENTIFIER ::= { tmnxL2tpConformance 1 }
    tmnxL2tpGroups            OBJECT IDENTIFIER ::= { tmnxL2tpConformance 2 }

tmnxL2tpNotifyPrefix          OBJECT IDENTIFIER ::= { tmnxSRNotifyPrefix 60 }
    tmnxL2tpNotifications     OBJECT IDENTIFIER ::= { tmnxL2tpNotifyPrefix 0 }

--
-- Subtrees
--
tmnxL2tpVrtrObjs              OBJECT IDENTIFIER ::= { tmnxL2tpObjs 1 }
tmnxL2tpTgObjs                OBJECT IDENTIFIER ::= { tmnxL2tpObjs 2 }
tmnxL2tpTunnelObjs            OBJECT IDENTIFIER ::= { tmnxL2tpObjs 3 }
tmnxL2tpPeerObjs              OBJECT IDENTIFIER ::= { tmnxL2tpObjs 4 }
tmnxL2tpSessionObjs           OBJECT IDENTIFIER ::= { tmnxL2tpObjs 5 }
tmnxL2tpLnsIsaObjs            OBJECT IDENTIFIER ::= { tmnxL2tpObjs 6 }
tmnxL2tpLnsSvcObjs            OBJECT IDENTIFIER ::= { tmnxL2tpObjs 7 }
tmnxL2tpMlpppObjs             OBJECT IDENTIFIER ::= { tmnxL2tpObjs 8 }
tmnxL2tpAccountingObjs        OBJECT IDENTIFIER ::= { tmnxL2tpObjs 100 }

-- ----------------------------------------------------------------------------
--  Textual Conventions
-- ----------------------------------------------------------------------------

TmnxAlwaysNeverOrDefault ::= TEXTUAL-CONVENTION
    STATUS       current
    DESCRIPTION
       "The TmnxAlwaysNeverOrDefault data type is an enumerated integer 
        that describes a 'boolean-like' value that can be set to a default
        value.

        The value 'default' specifies that the actual value must be
        derived from another object of the same type with a wider scope."
    SYNTAX  INTEGER {
                default (1),
                never (2),
                always (3)
            }

TmnxAlwaysOrNever ::= TEXTUAL-CONVENTION
    STATUS       current
    DESCRIPTION
       "The TmnxAlwaysOrNever data type is an enumerated integer 
        that describes a 'boolean value that can be used together
        with the 'TmnxAlwaysNeverOrDefault' data type.

        Use 'TmnxAlwaysOrNever' at the highest level and 
        'TmnxAlwaysNeverOrDefault' at lower levels of inheritance."
    SYNTAX  INTEGER {
                never (2),
                always (3)
            }

TmnxL2tpActionTypeDrain ::= TEXTUAL-CONVENTION
    STATUS  current
    DESCRIPTION
       "The TmnxL2tpActionTypeDrain data type is an enumerated integer 
        that describes the values used to specify the type of drain action."
    SYNTAX  INTEGER {
                drain (0),
                stopDrain (1),
                notApplicable (2)
            }

TmnxL2tpAuthSecret ::= TEXTUAL-CONVENTION
    STATUS  current
    DESCRIPTION
       "The TmnxL2tpAuthSecret data type contains a shared secret
        used during the tunnel authentication phase of tunnel establishment."
    SYNTAX DisplayString (SIZE (0..64))

TmnxL2tpAvpHidingMode ::= TEXTUAL-CONVENTION
    STATUS  current
    DESCRIPTION
       "The TmnxL2tpAvpHidingMode data type is an enumerated integer 
        that describes when the H bit is set in an L2TP Attribute Value Pair 
        (AVP).
        
        The value 'never' specifies that the H bit is never set.
        
        The value 'sensitive' specifies that the H bit is only set for AVP's
        containing sensitive information.
        
        The value 'always' specifies that the H bit is set for all AVP's where
        it is allowed.

        The value 'default' specifies that the actual value must be
        derived from another object of the same type but a wider scope."
    SYNTAX  INTEGER {
                default (1),
                never (2),
                sensitive (3),
                always (4)
            }

TmnxL2tpCdnResult ::= TEXTUAL-CONVENTION
    STATUS  current
    DESCRIPTION
       "The TmnxL2tpCdnResult data type is an enumerated integer 
        that indicates the result of a CDN (Call-Disconnect-Notify) message."
    REFERENCE
       "RFC 2661 Layer Two Tunneling Protocol 'L2TP', 
        section 4.4.2 Result and Error Codes."
    SYNTAX  INTEGER {
                noError (0),
                lossCarrier (1),
                generalError (2),
                admin (3),
                noFacTemporary (4),
                noFacPermanent (5),
                invalidDest (6),
                noCarrier (7),
                busy (8),
                noDialTone (9),
                notEstab (10),
                noFraming (11)
            }

TmnxL2tpConnectionId ::= TEXTUAL-CONVENTION
    STATUS  current
    DESCRIPTION
       "The TmnxL2tpConnectionId data type contains an identification number 
        for a Layer Two Tunneling Protocol Connection."
    SYNTAX Unsigned32 (0..4294967295)

TmnxL2tpDoChallenge ::= TEXTUAL-CONVENTION
    STATUS  current
    DESCRIPTION
       "The TmnxL2tpDoChallenge data type is an enumerated integer 
        that describes when challenge-response authentication is to be used.
        
        The value 'never' specifies that challenge-response authentication is 
        never used.
        
        The value 'always' specifies that challenge-response authentication is 
        always used.

        The value 'default' specifies that the actual value must be
        derived from another object of the same type but a wider scope."
    SYNTAX  INTEGER {
                default (1),
                never (2),
                always (3)
            }

TmnxL2tpErrorMessage ::= TEXTUAL-CONVENTION
    STATUS  current
    DESCRIPTION
       "The TmnxL2tpErrorMessage data type describes an L2TP error condition
        in human readable form."
    REFERENCE
       "RFC 2661 Layer Two Tunneling Protocol 'L2TP', 
        section 4.4.2 Result and Error Codes."
    SYNTAX  DisplayString (SIZE (0..255))

TmnxL2tpGeneralError ::= TEXTUAL-CONVENTION
    STATUS  current
    DESCRIPTION
       "The TmnxL2tpGeneralError data type is an enumerated integer 
        that indicates types of errors that are not specific to any particular 
        L2TP request, but rather to protocol or message format errors."
    REFERENCE
       "RFC 2661 Layer Two Tunneling Protocol 'L2TP', 
        section 4.4.2 Result and Error Codes."
    SYNTAX  INTEGER {
                noError (0),
                noControl (1),
                wrongLength (2),
                fieldOutOfRange (3),
                insufficientRes (4),
                sessionIdInvalid (5),
                vendorSpecific (6),
                tryAnother (7),
                unknownMandatory (8)
            }

TmnxL2tpHostNameOrEmpty ::= TEXTUAL-CONVENTION
    STATUS  current
    DESCRIPTION
       "The TmnxL2tpHostNameOrEmpty data type contains a valid string to
        identify the host name of a Layer Two Tunneling Protocol Tunnel
        remote system (client) or server.

        An empty string indicates that no host name is defined."
    SYNTAX DisplayString (SIZE (0..64))

TmnxL2tpIsaGrpId ::= TEXTUAL-CONVENTION
    STATUS  current
    DESCRIPTION
       "The TmnxL2tpIsaGrpId data type contains an identification number 
        for a Layer Two Tunneling Protocol Integrated Service Adaptor group."
    SYNTAX Unsigned32 (1..4)

TmnxL2tpIsaGrpIdOrZero ::= TEXTUAL-CONVENTION
    STATUS  current
    DESCRIPTION
       "The TmnxL2tpIsaGrpIdOrZero data type contains an identification number 
        for a Layer Two Tunneling Protocol Integrated Service Adaptor (ISA) 
        group.
        
        The value zero means that no L2TP ISA Group is defined."
    SYNTAX Unsigned32 (0..4)

TmnxL2tpIsaMdaLoadBalanceMethod ::= TEXTUAL-CONVENTION
    STATUS  current
    DESCRIPTION
       "The TmnxL2tpIsaMdaLoadBalanceMethod data type is an enumerated integer 
        that describes how new sessions are assigned to an L2TP ISA MDA.
        
        The value 'perSession' specifies that the lowest granularity for
        load-balancing is a session; each session can be assigned to a different
        ISA MDA.
        
        The value 'perTunnel' specifies that the lowest granularity for
        load-balancing is a tunnel; all sessions associated with the same 
        tunnel are assigned to the same ISA MDA; this may be useful or 
        required in certain cases, for example:
        - MLPPP with multiple links per bundle;
        - HPol intermediate destination arbiters where the intermediate 
          destination is an L2TP tunnel.
        
        The meaning of the value 'default' depends on the object."
    SYNTAX  INTEGER {
                default (0),
                perSession (1),
                perTunnel (2)
            }
    
TmnxL2tpIsaMdaOperState ::= TEXTUAL-CONVENTION
    STATUS  current
    DESCRIPTION
       "The TmnxL2tpIsaMdaOperState data type is an enumerated integer 
        that describes the values used to identify the operational state of 
        the L2TP ISA MDA."
    SYNTAX  INTEGER {
                unknown (1),
                inService (2),
                outOfService (3),
                draining (4),
                drained (5)
            }

TmnxL2tpLcpKaHoldUpMplier ::= TEXTUAL-CONVENTION
    STATUS  current
    DESCRIPTION
       "The TmnxL2tpLcpKaHoldUpMplier data type contains a number 
        that specifies how many LCP keepalive messages can be missed 
        before the related session is brought down.
        
        The value '0' specifies that the actual value must be
        derived from another object of the same type but a wider scope."
    SYNTAX Unsigned32 (0|1..5)

TmnxL2tpLcpKaInterval ::= TEXTUAL-CONVENTION
    STATUS  current
    DESCRIPTION
       "The TmnxL2tpLcpKaInterval data type contains a number 
        that specifies the time interval in seconds at which 
        LCP echo requests are transmitted.
        
        The value '0' specifies that the actual value must be
        derived from another object of the same type but a wider scope."
    SYNTAX Unsigned32 (0|10..300)

TmnxL2tpMlpppEndpointClass ::= TEXTUAL-CONVENTION
    STATUS  current
    DESCRIPTION
       "The TmnxL2tpMlpppEndpointClass data type is an enumerated integer 
        that specifies the class of an MLPPP endpoint specification.
        
        This is used to identify a value to be transmitted in the
        MLPPP Endpoint Discriminator Option
        
        The value 'ipv4Address' specifies that a configured IPv4 address be used.
        
        The value 'macAddress' specifies that a configured IEEE 802.1 MAC address
        be used.
        
        The meaning of 'default' depends on the object."
    REFERENCE
       "RFC 1990 The PPP Multilink Protocol (MP), 
        section 5.1.3 Endpoint Discriminator Option."
    SYNTAX  INTEGER {
                default  (0),
                ipv4Address (2),
                macAddress (3)
            }

TmnxL2tpMlpppMaxFragDelay ::= TEXTUAL-CONVENTION
    STATUS  current
    DESCRIPTION
       "The TmnxL2tpMlpppMaxFragDelay data type contains a number 
        that specifies the maximum delay of a fragment, expressed in 
        milliseconds.
        
        The meaning of the value '0' depends on the object."
    SYNTAX Unsigned32 (0|5..1000)

TmnxL2tpMlpppReassemblyTimeout ::= TEXTUAL-CONVENTION
    STATUS  current
    DESCRIPTION
       "The TmnxL2tpMlpppReassemblyTimeout data type contains a number 
        that specifies the maximum time, expressed in milliseconds, that the  
        system will keep incomplete packets while reassembling fragments.
        
        The value '0' specifies that the actual value must be
        derived from another object of the same type but a wider scope."
    SYNTAX Unsigned32 (0|100|1000)

TmnxL2tpPeerAddrChangePolicy ::= TEXTUAL-CONVENTION
    STATUS  current
    DESCRIPTION
       "The TmnxL2tpPeerAddrChangePolicy data type is an enumerated integer 
        that specifies what to do in case the system receives a L2TP response
        from another address than the one the request was sent to.
        
        The value 'accept' specifies that this system accepts any source IP 
        address change of received L2TP control messages related to 
        a locally originated tunnel in the state 'waitReply' and rejects
        any peer address change for other tunnels; in case the new peer IP
        address is accepted, it is learned and used as destination address
        in subsequent L2TP messages.
        
        The value 'ignore' specifies that this system ignores any source IP 
        address change of received L2TP control messages, does not learn any
        new peer IP address and does not change the destination address in
        subsequent L2TP messages.
        
        The value 'reject' specifies that this system rejects any source IP 
        address change of received L2TP control messages and drops those 
        messages."
    SYNTAX  INTEGER {
                accept   (1),
                ignore   (2),
                reject   (3)
            }

TmnxL2tpPppAuthentication ::= TEXTUAL-CONVENTION
    STATUS  current
    DESCRIPTION
       "The TmnxL2tpPppAuthentication data type is an enumerated integer 
        that specifies what PPP authentication protocol(s) must be negotiated 
        during the LCP phase.
        
        The value 'prefChap' specifies that an attempt is made to negotiate
        CHAP first, possibly followed by an attempt to negotiate PAP.

        The value 'prefPap' specifies that an attempt is made to negotiate
        PAP first, possibly followed by an attempt to negotiate CHAP.
                
        The value 'default  (0)' specifies that the actual value must be
        derived from another object of the same type but a wider scope."
    SYNTAX  INTEGER {
                default  (0),
                pap      (1),
                chap     (2),
                prefChap (3),
                prefPap  (4)
            }

TmnxL2tpPppMtu ::= TEXTUAL-CONVENTION
    STATUS  current
    DESCRIPTION
       "The TmnxL2tpPppMtu data type contains a number 
        that specifies the largest IP packet that can be sent out without being
        fragmented.
        
        The value '0' specifies that the actual value must be
        derived from another object of the same type but a wider scope."
    SYNTAX Unsigned32 (0|512..9212)

TmnxL2tpReceiveWindowSize ::= TEXTUAL-CONVENTION
    STATUS  current
    DESCRIPTION
       "The TmnxL2tpReceiveWindowSize data type contains a number 
        that specifies the Receive Window Size (RWS).
        
        The value '0' specifies that the actual value must be
        derived from another object of the same type but a wider scope."
    REFERENCE
       "RFC 2661 Layer Two Tunneling Protocol 'L2TP', 
        section 5.8 Reliable Delivery of Control Messages."
    SYNTAX Unsigned32 (0|4..1024)

TmnxL2tpRoles ::= TEXTUAL-CONVENTION
    STATUS  current
    DESCRIPTION
       "The TmnxL2tpRoles data type is a set of roles."
    REFERENCE
       "RFC 2661 Layer Two Tunneling Protocol 'L2TP', 
        section 1.1 Specification of Requirements."
    SYNTAX  BITS {
                roleLAC (0),
                roleLNS (1)
            }

TmnxL2tpSeOperState ::= TEXTUAL-CONVENTION
    STATUS  current
    DESCRIPTION
       "The TmnxL2tpTuOperState data type is an enumerated integer 
        that describes the values used to identify the operational state of 
        the L2TP session."
    SYNTAX  INTEGER {
                unknown (0),
                idle (1),
                waitTunnel (2),
                waitReply (3),
                waitAcceptance (4),
                waitConnected (5),
                established (6),
                closed (7),
                closedByPeer (8)
            }

TmnxL2tpSessionAssignMethod ::= TEXTUAL-CONVENTION
    STATUS  current
    DESCRIPTION
       "The TmnxL2tpSessionAssignMethod data type is an enumerated integer 
        that describes how new sessions are assigned to one of the set of 
        suitable tunnels that are available or could be made available.
        
        The value 'existingFirst' specifies that the first suitable tunnel is 
        used or set up for the first session and re-used for all subsequent 
        sessions.
        
        The value 'weighted' specifies that the sessions are shared between the
        available tunnels; if necessary, new tunnels are set up until the
        maximum number is reached; the distribution aims at an equal ratio of
        the actual number of sessions to the maximum number of sessions.

        The value 'default' specifies that the actual value must be
        derived from another object of the same type with a wider scope."
    SYNTAX  INTEGER {
                default (0),
                existingFirst (1),
                weighted (2)
            }

TmnxL2tpSessionId ::= TEXTUAL-CONVENTION
    STATUS  current
    DESCRIPTION
       "The TmnxL2tpSessionId data type contains an identification number 
        for a Layer Two Tunneling Protocol Session.
        
        This data type is only meaningful in the context of L2TP version 2; 
        in this case, the range of valid values is (1..65535).
        
        In the context of L2TP version 3, the value must be equal to 0."
    REFERENCE
       "RFC 2661 Layer Two Tunneling Protocol 'L2TP', 
        section 3.1 L2TP Header Format."
    SYNTAX Unsigned32 (0..65535)

TmnxL2tpStopCcnResult ::= TEXTUAL-CONVENTION
    STATUS  current
    DESCRIPTION
       "The TmnxL2tpStopCcnResult data type is an enumerated integer 
        that indicates the result of a 'StopCCN' 
        (Stop-Control-Connection-Notification) message."
    REFERENCE
       "RFC 2661 Layer Two Tunneling Protocol 'L2TP', 
        section 4.4.2 Result and Error Codes."
    SYNTAX  INTEGER {
                noError (0),
                generalReq (1),
                generalErr (2),
                alreadyExists (3),
                reqNotAuth (4),
                version (5),
                reqShutDown (6),
                fsmError (7)
            }

TmnxL2tpTgOperState ::= TEXTUAL-CONVENTION
    STATUS  current
    DESCRIPTION
       "The TmnxL2tpTgOperState data type is an enumerated integer 
        that describes the values used to identify the operational state of 
        the L2TP tunnel group."
    SYNTAX  INTEGER {
                active (1),
                drain (2)
            }

TmnxL2tpTransportType ::= TEXTUAL-CONVENTION
    STATUS  current
    DESCRIPTION
       "The TmnxL2tpTransportType data type is an enumerated integer 
        that describes the transport type (aka type of Packet-Switched Network)
        used to carry the L2TP messages."
    SYNTAX  INTEGER {
                unknown (0),
                udpIp (1)
            }

TmnxL2tpTunnelDestructTO ::= TEXTUAL-CONVENTION
    STATUS  current
    DESCRIPTION
       "The period of time, expressed in seconds, that the data of a  
        disconnected tunnel persists before being removed.

        If the system needs the resources taken by the disconnected tunnel
        data, it may remove the data earlier.

        The value '-2' means that the actual value must be derived from another
        object of the same type but with a wider scope."
    SYNTAX Integer32 (-2|60..86400)

TmnxL2tpTunnelGroupName ::= TEXTUAL-CONVENTION
    STATUS  current
    DESCRIPTION
       "The TmnxL2tpTunnelGroupName data type contains a valid string to
        identify a Layer Two Tunneling Protocol Tunnel Group."
    SYNTAX DisplayString (SIZE (1..63))

TmnxL2tpTunnelGroupNameOrEmpty ::= TEXTUAL-CONVENTION
    STATUS  current
    DESCRIPTION
       "The TmnxL2tpTunnelGroupNameOrEmpty data type contains a valid string 
        to identify a Layer Two Tunneling Protocol Tunnel Group.

        An empty string indicates that no Tunnel Group is defined."
    SYNTAX DisplayString (SIZE (0..63))

TmnxL2tpTunnelHelloInterval ::= TEXTUAL-CONVENTION
    STATUS  current
    DESCRIPTION
       "The time interval, expresssed in seconds, between two consecutive
        tunnel Hello messages.
        
        The value '-1' means that the keepalive function is disabled.
        
        The value '-2' means that the actual value must be derived from another
        object of the same type but with a wider scope."
    REFERENCE
       "RFC 2661 Layer Two Tunneling Protocol 'L2TP', section 6.5 Hello."
    SYNTAX Integer32 (-2|-1|60..3600)

TmnxL2tpTunnelId ::= TEXTUAL-CONVENTION
    STATUS  current
    DESCRIPTION
       "The TmnxL2tpTunnelId data type contains an identification number 
        for a Layer Two Tunneling Protocol Tunnel.
        
        This data type is only meaningful in the context of L2TP version 2; 
        in this case, the range of valid values is (1..65535).
        
        In the context of L2TP version 3, the value must be equal to 0."
    REFERENCE
       "RFC 2661 Layer Two Tunneling Protocol 'L2TP', 
        section 3.1 L2TP Header Format."
    SYNTAX Unsigned32 (0..65535)

TmnxL2tpTunnelIdleTO ::= TEXTUAL-CONVENTION
    STATUS  current
    DESCRIPTION
       "The period of time, expressed in seconds, that an established tunnel 
        with no active sessions persists before being disconnected.

        A value of '-1' leaves a tunnel up indefinitely.
        
        The value '-2' means that the actual value must be derived from another
        object of the same type but with a wider scope."
    SYNTAX Integer32 (-2|-1|0..3600)

TmnxL2tpTunnelMaxRetx ::= TEXTUAL-CONVENTION
    STATUS  current
    DESCRIPTION
       "The number of retries allowed for a tunnel before its
        control connection goes down.
        
        The value '-2' means that the actual value must be derived from another
        object of the same type but with a wider scope."
    SYNTAX Integer32 (-2|2..7)

TmnxL2tpTunnelName ::= TEXTUAL-CONVENTION
    STATUS  current
    DESCRIPTION
       "The TmnxL2tpTunnelName data type contains a valid string to
        identify a Layer Two Tunneling Protocol Tunnel."
    SYNTAX DisplayString (SIZE (1..63))

TmnxL2tpTunnelNameOrEmpty ::= TEXTUAL-CONVENTION
    STATUS  current
    DESCRIPTION
       "The TmnxL2tpTunnelNameOrEmpty data type contains a valid string 
        to identify a Layer Two Tunneling Protocol Tunnel.

        An empty string indicates that no Tunnel is defined."
    SYNTAX DisplayString (SIZE (0..63))

TmnxL2tpTunnelPreference ::= TEXTUAL-CONVENTION
    STATUS  current
    DESCRIPTION
       "The TmnxL2tpTunnelPreference data type contains a number 
        that indicates the relative preference assigned to a tunnel.
        
        The value '0' corresponds to the highest preference."
    REFERENCE
       "RFC 2868 RADIUS Attributes for Tunnel Protocol Support,
        section 3.8. Tunnel-Preference"
    SYNTAX Unsigned32 (0..16777215)

TmnxL2tpTunnelSessionLimit ::= TEXTUAL-CONVENTION
    STATUS  current
    DESCRIPTION
       "The number of sessions allowed.

        The value '-2' means that the actual value must be derived from another
        object of the same type but with a wider scope."
    SYNTAX Integer32 (-2|1..131071)

TmnxL2tpTuOperState ::= TEXTUAL-CONVENTION
    STATUS  current
    DESCRIPTION
       "The TmnxL2tpTuOperState data type is an enumerated integer 
        that describes the values used to identify the operational state of 
        the L2TP tunnel."
    SYNTAX  INTEGER {
                unknown (1),
                idle (2),
                waitReply (3),
                waitConn (4),
                establishedIdle (5),
                established (6),
                draining (7),
                drained (8),
                closed (9),
                closedByPeer (10)
            }

TmnxL2tpTuProtStatsType ::= TEXTUAL-CONVENTION
    STATUS  current
    DESCRIPTION
       "The TmnxL2tpTuProtStatsType data type is an enumerated integer 
        that describes the values used to identify the protocol statistics of 
        the L2TP tunnel."
    SYNTAX  INTEGER {
                event                      (1),
                droppedMsgType             (2),
                acceptedMsgType            (3),
                originalTransmittedMsgType (4),
                retransmittedMsgType       (5),
                incomingCDNresultCode      (6),    
                incomingStopCCNresultCode  (7),
                incomingErrorCode          (8),        
                outgoingCDNresultCode      (9),   
                outgoingStopCCNresultCode  (10),
                outgoingErrorCode          (11)
            }

-- ----------------------------------------------------------------------------
--      The L2TP Virtual Router Group
-- ----------------------------------------------------------------------------

tmnxL2tpVrtrCfgObjs            OBJECT IDENTIFIER   ::= { tmnxL2tpVrtrObjs 1 }
tmnxL2tpVrtrStatObjs           OBJECT IDENTIFIER   ::= { tmnxL2tpVrtrObjs 2 }

--
--      L2TP Virtual Router Configuration Group
--

-- ---------------------------------------------------------------------
--  tmnxL2tpTable
--
--  Deletion of a row in the vRtrConfTable results in the
--  same fate for the corresponding row in the tmnxL2tpTable.
-- ---------------------------------------------------------------------

tmnxL2tpTableLastCh OBJECT-TYPE
    SYNTAX      TimeStamp
    MAX-ACCESS  read-only
    STATUS      current
    DESCRIPTION
        "The value of tmnxL2tpTableLastCh indicates the sysUpTime 
         at the time of the most recent management-initiated change to the
         tmnxL2tpTable."
    ::= { tmnxL2tpObjs 10 }

tmnxL2tpTable OBJECT-TYPE
    SYNTAX      SEQUENCE OF TmnxL2tpEntry
    MAX-ACCESS  not-accessible
    STATUS      current
    DESCRIPTION
        "A table that contains L2TP configuration 
         information about virtual routers.

         Rows in this table can be created or deleted via SNMP operations.

         Rows in this table are automatically deleted when the corresponding
         row in the vRtrConfTable is deleted.
         
         The conceptual row that corresponds to the Base router instance, 
         however, is automatically created by the system, and cannot be
         created or deleted via SNMP operations."
    ::= { tmnxL2tpVrtrCfgObjs 2 }

tmnxL2tpEntry OBJECT-TYPE
    SYNTAX      TmnxL2tpEntry
    MAX-ACCESS  not-accessible
    STATUS      current
    DESCRIPTION
        "L2TP specific information about a virtual router.
        
         Each entry represents a L2TP protocol instance."
    INDEX { vRtrID }
    ::= { tmnxL2tpTable 1 }

TmnxL2tpEntry ::=
    SEQUENCE {
        tmnxL2tpLastMgmtChange           TimeStamp,
        tmnxL2tpAdminState               TmnxAdminState,
        tmnxL2tpSessionLimit             TmnxL2tpTunnelSessionLimit,
        tmnxL2tpReceiveWindowSize        TmnxL2tpReceiveWindowSize,
        tmnxL2tpRowStatus                RowStatus,
        tmnxL2tpPeerAddrChangePlcy       TmnxL2tpPeerAddrChangePolicy,
        tmnxL2tpAvpExclude               BITS,
        tmnxL2tpAvpCallingNumberSpec     TmnxAsciiSpecification,
        tmnxL2tpAccountingPolicy         TNamedItemOrEmpty,
        tmnxL2tpHelloInterval            TmnxL2tpTunnelHelloInterval,
        tmnxL2tpIdleTO                   TmnxL2tpTunnelIdleTO,
        tmnxL2tpDestructTO               TmnxL2tpTunnelDestructTO,
        tmnxL2tpMaxRetxEstab             TmnxL2tpTunnelMaxRetx,
        tmnxL2tpMaxRetxNotEstab          TmnxL2tpTunnelMaxRetx,
        tmnxL2tpTunnelSessionLimit       TmnxL2tpTunnelSessionLimit,
        tmnxL2tpGroupSessionLimit        TmnxL2tpTunnelSessionLimit,
        tmnxL2tpAvpHiding                TmnxL2tpAvpHidingMode,
        tmnxL2tpDoChallenge              TmnxL2tpDoChallenge,
        tmnxL2tpSecret                   TmnxL2tpAuthSecret,
        tmnxL2tpSessionAssignMethod      TmnxL2tpSessionAssignMethod,
        tmnxL2tpLocalName                TmnxL2tpHostNameOrEmpty,
        tmnxL2tpAddrType                 InetAddressType,
        tmnxL2tpAddr                     InetAddress
    }

tmnxL2tpLastMgmtChange OBJECT-TYPE
    SYNTAX      TimeStamp
    MAX-ACCESS  read-only
    STATUS      current
    DESCRIPTION
        "The value of tmnxL2tpLastMgmtChange indicates the sysUpTime at
         the time of the most recent management-initiated change to this
         table row."
    ::= { tmnxL2tpEntry 1 }

tmnxL2tpAdminState OBJECT-TYPE
    SYNTAX      TmnxAdminState
    MAX-ACCESS  read-create
    STATUS      current
    DESCRIPTION
        "The value of the object tmnxL2tpAdminState specifies
         the administrative state of this L2TP protocol instance."
    DEFVAL    { outOfService }
    ::= { tmnxL2tpEntry 2 }

tmnxL2tpSessionLimit OBJECT-TYPE
    SYNTAX      TmnxL2tpTunnelSessionLimit
    MAX-ACCESS  read-create
    STATUS      current
    DESCRIPTION
       "The value of tmnxL2tpSessionLimit specifies
        the maximum number of sessions in this L2TP protocol instance.

        The value '-2' is not allowed because this is the widest scope for
        TmnxL2tpTunnelSessionLimit."
    DEFVAL    { 131071 }
        ::= { tmnxL2tpEntry 3 }

tmnxL2tpReceiveWindowSize OBJECT-TYPE
    SYNTAX      TmnxL2tpReceiveWindowSize
    MAX-ACCESS  read-create
    STATUS      current
    DESCRIPTION
       "The value of tmnxL2tpReceiveWindowSize specifies
        the Receive Window Size in this L2TP protocol instance.
        
        The value '0' is not allowed."
    DEFVAL    { 64 }
        ::= { tmnxL2tpEntry 4 }

tmnxL2tpRowStatus OBJECT-TYPE
    SYNTAX      RowStatus
    MAX-ACCESS  read-create
    STATUS      current
    DESCRIPTION
       "The value of tmnxL2tpRowStatus specifies the row status of
        this row."
        ::= { tmnxL2tpEntry 5 }

tmnxL2tpPeerAddrChangePlcy OBJECT-TYPE
    SYNTAX      TmnxL2tpPeerAddrChangePolicy
    MAX-ACCESS  read-create
    STATUS      current
    DESCRIPTION
       "The value of the object tmnxL2tpPeerAddrChangePlcy specifies
        what to do in case the system receives a L2TP response
        from another address than the one the request was sent to, for
        a tunnel in this L2TP protocol instance."
    DEFVAL    { reject }
        ::= { tmnxL2tpEntry 6 }

tmnxL2tpAvpExclude OBJECT-TYPE
    SYNTAX      BITS 
                {
                    callingNumber (0),
                    initialRxLcpConfReq (1)
                }
    MAX-ACCESS  read-create
    STATUS      current
    DESCRIPTION
       "The value of the object tmnxL2tpAvpExclude specifies
        what AVP's (Attribute Value Pairs) to exclude from L2TP control messages 
        related to a session in this L2TP protocol instance."
    DEFVAL { {} } 
        ::= { tmnxL2tpEntry 7 }

tmnxL2tpAvpCallingNumberSpec OBJECT-TYPE
    SYNTAX      TmnxAsciiSpecification
    MAX-ACCESS  read-create
    STATUS      current
    DESCRIPTION
       "The value of the object tmnxL2tpAvpCallingNumberSpec specifies
        what string to put in the Calling Number AVP, for L2TP control messages
        related to a session in this L2TP protocol instance.
        
        This value is not applicable if the 'callingNumber' bit is set in
        the object tmnxL2tpAvpExclude.
        
        <origin>              ::= 'S' | 'c' | 's' | 'r'

        'S' - system name, the value of TIMETRA-CHASSIS-MIB::tmnxChassisName
        'c' - Agent Circuit Id
        's' - SAP ID, formatted as a character string
        'r' - Agent Remote Id
        
        An empty string is not allowed.

        Example: '%S %s' means 'the system name, followed by a blank space, 
        followed by the SAP ID formatted as a string'."
    DEFVAL    { "%S %s" }
        ::= { tmnxL2tpEntry 8 }

tmnxL2tpAccountingPolicy OBJECT-TYPE
    SYNTAX      TNamedItemOrEmpty
    MAX-ACCESS  read-create
    STATUS      current
    DESCRIPTION
       "The value of the object tmnxL2tpAccountingPolicy specifies
        the RADIUS accounting policy to use in this L2TP protocol instance.
        
        It refers to a conceptual row in the tmnxL2tpApTable.
        
        The value of tmnxL2tpAccountingPolicy can be overruled by 
        a non-empty value of tmnxL2tpTgCfgAccountingPolicy 
        or tmnxL2tpTuCfgAccountingPolicy."
    DEFVAL    { "" }
        ::= { tmnxL2tpEntry 10 }

tmnxL2tpHelloInterval OBJECT-TYPE
    SYNTAX      TmnxL2tpTunnelHelloInterval
    UNITS       "seconds"
    MAX-ACCESS  read-create
    STATUS      current
    DESCRIPTION
       "The value of tmnxL2tpHelloInterval specifies
        the time interval between two consecutive tunnel Hello messages.

        A value of '-1' specifies that the keepalive function is disabled.
        
        The value '-2' is not allowed because this is the widest scope for
        TmnxL2tpTunnelHelloInterval."
    DEFVAL    { 300 }
        ::= { tmnxL2tpEntry 11 }

tmnxL2tpIdleTO OBJECT-TYPE
    SYNTAX      TmnxL2tpTunnelIdleTO
    UNITS       "seconds"
    MAX-ACCESS  read-create
    STATUS      current
    DESCRIPTION
       "The value of tmnxL2tpIdleTO specifies
        the period of time that an established tunnel with no active sessions 
        will persist before being disconnected.

        A value of -1 leaves the tunnel up indefinitely.
        
        The value '-2' is not allowed because this is the widest scope for
        TmnxL2tpTunnelIdleTO."
    DEFVAL    { -1 }
        ::= { tmnxL2tpEntry 12 }

tmnxL2tpDestructTO OBJECT-TYPE
    SYNTAX      TmnxL2tpTunnelDestructTO
    UNITS       "seconds"
    MAX-ACCESS  read-create
    STATUS      current
    DESCRIPTION
       "The value of tmnxL2tpDestructTO specifies
        the period of time that the data of a disconnected tunnel 
        will persist before being removed.

        The value '-2' is not allowed because this is the widest scope for
        TmnxL2tpTunnelDestructTO."
    DEFVAL    { 60 }
        ::= { tmnxL2tpEntry 13 }

tmnxL2tpMaxRetxEstab OBJECT-TYPE
    SYNTAX      TmnxL2tpTunnelMaxRetx
    MAX-ACCESS  read-create
    STATUS      current
    DESCRIPTION
       "The value of tmnxL2tpMaxRetxEstab specifies
        the number of retries allowed for established tunnels before their
        control connection goes down.

        The value '-2' is not allowed because this is the widest scope for
        TmnxL2tpTunnelMaxRetx."
    DEFVAL    { 5 }
        ::= { tmnxL2tpEntry 14 }

tmnxL2tpMaxRetxNotEstab OBJECT-TYPE
    SYNTAX      TmnxL2tpTunnelMaxRetx
    MAX-ACCESS  read-create
    STATUS      current
    DESCRIPTION
       "The value of tmnxL2tpMaxRetxNotEstab specifies
        the number of retries allowed for unestablished tunnels before their
        control connection goes down.

        The value '-2' is not allowed because this is the widest scope."
    DEFVAL    { 5 }
        ::= { tmnxL2tpEntry 15 }

tmnxL2tpTunnelSessionLimit OBJECT-TYPE
    SYNTAX      TmnxL2tpTunnelSessionLimit
    MAX-ACCESS  read-create
    STATUS      current
    DESCRIPTION
       "The value of tmnxL2tpTunnelSessionLimit specifies
        the maximum number of sessions in all Layer Two Tunneling Protocol 
        Tunnels of this virtual router.

        The value '-2' is not allowed because this is the widest scope for
        TmnxL2tpTunnelSessionLimit."
    DEFVAL    { 65535 }
        ::= { tmnxL2tpEntry 16 }

tmnxL2tpGroupSessionLimit OBJECT-TYPE
    SYNTAX      TmnxL2tpTunnelSessionLimit
    MAX-ACCESS  read-create
    STATUS      current
    DESCRIPTION
        "The value of tmnxL2tpGroupSessionLimit specifies
         the maximum number of sessions in all Layer Two Tunneling Protocol 
         Tunnel Groups of this virtual router.

         The value '-2' is not allowed because this is the widest scope for
         TmnxL2tpTunnelSessionLimit."
    DEFVAL    { 131071 }
        ::= { tmnxL2tpEntry 17 }

tmnxL2tpAvpHiding OBJECT-TYPE
    SYNTAX      TmnxL2tpAvpHidingMode
    MAX-ACCESS  read-create
    STATUS      current
    DESCRIPTION
       "The value of the object tmnxL2tpAvpHiding specifies
        the method to be used for the authentication of the tunnels in this
        virtual router.
        
        The value 'default' is not allowed because this is the widest scope
        for TmnxL2tpAvpHidingMode."
    REFERENCE
       "RFC 2661 Layer Two Tunneling Protocol 'L2TP', 
        section 4.3 Hiding of AVP Attribute Values."
    DEFVAL { never }
        ::= { tmnxL2tpEntry 18 }

tmnxL2tpDoChallenge OBJECT-TYPE
    SYNTAX      TmnxL2tpDoChallenge
    MAX-ACCESS  read-create
    STATUS      current
    DESCRIPTION
       "The value of the object tmnxL2tpDoChallenge specifies
        when challenge-response is to be used for the authentication of 
        the tunnels in the Layer Two Tunneling Protocol Tunnel Groups of this
        virtual router.

        The value 'default' is not allowed because this is the widest scope
        for TmnxL2tpDoChallenge."
    DEFVAL { never }
        ::= { tmnxL2tpEntry 19 }  

tmnxL2tpSecret OBJECT-TYPE
    SYNTAX      TmnxL2tpAuthSecret
    MAX-ACCESS  read-create
    STATUS      current
    DESCRIPTION
       "The value of the object tmnxL2tpSecret specifies
        the password to be used for the authentication of the tunnels in the
        Layer Two Tunneling Protocol Tunnel Groups of this virtual router.

        For any given tunnel in this group, the value of tmnxL2tpSecret
        can be overruled with the value of tmnxL2tpTgCfgSecret.

        This object will always return an empty string on a read."
    DEFVAL { ''H }
        ::= { tmnxL2tpEntry 20 }

tmnxL2tpSessionAssignMethod OBJECT-TYPE
    SYNTAX      TmnxL2tpSessionAssignMethod
    MAX-ACCESS  read-create
    STATUS      current
    DESCRIPTION
       "The value of the object tmnxL2tpSessionAssignMethod specifies
        the method to be used for the authentication of the tunnels in the
        Layer Two Tunneling Protocol Tunnel Groups of this virtual router.

        The value 'default' is not allowed because this is the widest scope
        for TmnxL2tpSessionAssignMethod."
    DEFVAL { existingFirst }
    ::= { tmnxL2tpEntry 21 }        

tmnxL2tpLocalName OBJECT-TYPE
    SYNTAX      TmnxL2tpHostNameOrEmpty
    MAX-ACCESS  read-create
    STATUS      current
    DESCRIPTION
       "The value of the object tmnxL2tpLocalName specifies
        the host name used by this system for the tunnels in the
        Layer Two Tunneling Protocol Tunnel Groups of this virtual router during
        the authentication phase of tunnel establishment.
    
        This object is related to the RADIUS attribute Tunnel-Client-Auth-ID.
    
        It can be used to distinguish tunnels.
                
        An empty string specifies that the system name (SNMPv2-MIB::sysName) is
        used."
    REFERENCE
       "RFC 2868 RADIUS Attributes for Tunnel Protocol Support
        section 3.9."
    DEFVAL { ''H }
    ::= { tmnxL2tpEntry 22 }

tmnxL2tpAddrType OBJECT-TYPE
    SYNTAX      InetAddressType
    MAX-ACCESS  read-create
    STATUS      current
    DESCRIPTION 
       "The value of tmnxL2tpAddrType specifies the
        address type of tmnxL2tpAddr."
    DEFVAL { unknown }
    ::= { tmnxL2tpEntry 23 }

tmnxL2tpAddr OBJECT-TYPE
    SYNTAX      InetAddress (SIZE(0|4|16))
    MAX-ACCESS  read-create
    STATUS      current
    DESCRIPTION 
       "The value of tmnxL2tpAddr specifies the local IP
        address of the tunnels in the L2TP Tunnel Groups of this virtual 
        router."
    DEFVAL { ''H }  
    ::= { tmnxL2tpEntry 24 }  
    
-- ---------------------------------------------------------------------
--  tmnxL2tpXtTable - Extension of the tmnxL2tpTable
--
--  Augments the tmnxL2tpTable
-- ---------------------------------------------------------------------

tmnxL2tpXtTableLastCh OBJECT-TYPE
    SYNTAX      TimeStamp
    MAX-ACCESS  read-only
    STATUS      current
    DESCRIPTION
        "The value of the object tmnxL2tpXtTableLastCh indicates
         the value of sysUpTime at the time of the last modification of
         an entry in the tmnxL2tpXtTable."
    ::= { tmnxL2tpObjs 22 }
    
tmnxL2tpXtTable OBJECT-TYPE
    SYNTAX      SEQUENCE OF TmnxL2tpXtEntry
    MAX-ACCESS  not-accessible
    STATUS      current
    DESCRIPTION
        "A table that contains L2TP configuration
         information about virtual routers.

         A conceptual row in this table is created automatically by the system
         when a row in the tmnxL2tpTable is created.

         Rows in this table are automatically deleted when the corresponding
         row in the vRtrConfTable or the tmnxL2tpTable is deleted.

         The conceptual row that corresponds to the Base router instance,
         however, is automatically created by the system, and cannot be
         created or deleted via SNMP operations."
    ::= { tmnxL2tpVrtrCfgObjs 3 }

tmnxL2tpXtEntry OBJECT-TYPE
    SYNTAX      TmnxL2tpXtEntry
    MAX-ACCESS  not-accessible
    STATUS      current
    DESCRIPTION
        "L2TP specific information about a virtual router.

         Each entry represents a L2TP protocol instance."
    AUGMENTS { tmnxL2tpEntry }
    ::= { tmnxL2tpXtTable 1 }

TmnxL2tpXtEntry ::=
    SEQUENCE {
        tmnxL2tpXtNextAttempt            INTEGER,
        tmnxL2tpXtLastMgmtChange         TimeStamp,
        tmnxL2tpXtTuSelBlacklistReason   BITS,
        tmnxL2tpXtTuSelBlacklistMaxTime  INTEGER,
        tmnxL2tpXtTuSelBlacklistLength   INTEGER,
        tmnxL2tpXtTuSelBlacklistToAction INTEGER,
        tmnxL2tpXtReplaceResultCodes     BITS,
        tmnxL2tpXtAvpCiscoNasPortEth     TmnxBinarySpecification,
        tmnxL2tpXtAvpCiscoNasPortAtm     TmnxBinarySpecification,
        tmnxL2tpXtDfBitLac               TmnxAlwaysOrNever
    }

tmnxL2tpXtNextAttempt OBJECT-TYPE
    SYNTAX  INTEGER {
                samePreferenceLevel (0),
                nextPreferenceLevel (1)
            }
    MAX-ACCESS  read-create
    STATUS      current
    DESCRIPTION
       "The value of tmnxL2tpXtNextAttempt specifies the next tunnel to be used
        in case the session setup fails.

        A value of 'samePreferenceLevel(0)' specifies to try first any
        alternative tunnel from the same preference level before falling back to
        a lower preference level.

        A value of 'nextPreferenceLevel(1)' specifies to try a tunnel with a
        lower preference level (higher preference value)."
    DEFVAL { nextPreferenceLevel }
    ::= { tmnxL2tpXtEntry 1 }

tmnxL2tpXtLastMgmtChange OBJECT-TYPE
    SYNTAX      TimeStamp
    MAX-ACCESS  read-only
    STATUS      current
    DESCRIPTION
        "The value of tmnxL2tpXtLastMgmtChange indicates the sysUpTime at
         the time of the most recent management-initiated change to this
         table row."
    ::= { tmnxL2tpXtEntry 2 }

tmnxL2tpXtTuSelBlacklistReason OBJECT-TYPE
    SYNTAX  BITS {
                addrChangeTimeout         (0),
                cdnErrCode                (1),
                cdnInvDest                (2),
                cdnPermNoFacilities       (3),
                cdnTmpNoFacilities        (4),
                stopCcnErrCode            (5),
                stopCcnOther              (6),
                txCdnNotEstablishedInTime (7)
            }
    MAX-ACCESS  read-create
    STATUS      current
    DESCRIPTION
       "The value of tmnxL2tpXtTuSelBlacklistReason specifies the CDN or StopCCN
        result codes or tunnel or session setup failure condition  that determine
        which tunnels are added to the tunnel-selection-blacklist.

        The system will never try to put a session in a tunnel from the
        tunnel-selection-blacklist when alternative tunnels are available.

        If no value is selected for tmnxL2tpXtTuSelBlacklistReason the
        tunnel-selection-blacklist is disabled."
    DEFVAL { {} }
    ::= { tmnxL2tpXtEntry 3 }

tmnxL2tpXtTuSelBlacklistMaxTime OBJECT-TYPE
    SYNTAX      INTEGER (1..60)
    UNITS       "minutes"
    MAX-ACCESS  read-create
    STATUS      current
    DESCRIPTION
       "The value of tmnxL2tpXtTuSelBlacklistMaxTime specifies the maximum time
        a tunnel or peer may remain in the tunnel-selection-blacklist."
    DEFVAL { 5 }
    ::= { tmnxL2tpXtEntry 4 }

tmnxL2tpXtTuSelBlacklistLength OBJECT-TYPE
    SYNTAX      INTEGER (-1|1..65535)
    UNITS       "minutes"
    MAX-ACCESS  read-create
    STATUS      current
    DESCRIPTION
       "The value of tmnxL2tpXtTuSelBlacklistLength specifies how many items
        (tunnels or peers) can be in the tunnel-selection-blacklist.

        If a tunnel or peer needs to be added to the tunnel-selection-blacklist
        and the tunnel-selection-blacklist is full, the system will remove the
        item (tunnel or peer) from the blacklist that was in this blacklist for
        the longest time.

        A value of '-1' specifies there is no limit."
    DEFVAL { -1 }
    ::= { tmnxL2tpXtEntry 5 }

tmnxL2tpXtTuSelBlacklistToAction OBJECT-TYPE
    SYNTAX  INTEGER {
                removeFromBlacklist (0),
                tryOneSession       (1)
            }
    MAX-ACCESS  read-create
    STATUS      current
    DESCRIPTION
       "The value of tmnxL2tpXtTuSelBlacklistToAction specifies the action to be
        taken when a tunnel has been in the tunnel-selection-blacklist for the
        time specified in tmnxL2tpXtTuSelBlacklistMaxTime.

        A value of 'removeFromBlacklist(0)' specifies the tunnel will be removed
        from the tunnel-selection-blacklist.

        A value of 'tryOneSession(1)' specifies the tunnel will remain in the
        tunnel-selection-blacklist while the system will allow a single session
        to be added to the tunnel. Only on success will the tunnel be removed
        from the tunnel-selection-blacklist."
    DEFVAL { removeFromBlacklist }
    ::= { tmnxL2tpXtEntry 6 }

tmnxL2tpXtReplaceResultCodes OBJECT-TYPE
    SYNTAX  BITS {
                cdnInvDest          (0),
                cdnPermNoFacilities (1),
                cdnTmpNoFacilities  (2)
            }
    MAX-ACCESS  read-create
    STATUS      current
    DESCRIPTION
       "The value of tmnxL2tpXtReplaceResultCodes specifies the return codes
        that must be replaced by another appropriate result code.
        This field is typically used to solve interoperability issues.
        
        The return codes 'cdnInvDest' (6), 'cdnPermNoFacilities' (5) and
        'cdnTmpNoFacilities' (4) are all replaced by result code 'cdnErrCode' (2)
        and general error code 'insufficient resources' (4)."
    DEFVAL { {} }
    ::= { tmnxL2tpXtEntry 7 }
 
tmnxL2tpXtAvpCiscoNasPortEth OBJECT-TYPE
    SYNTAX      TmnxBinarySpecification
    MAX-ACCESS  read-create
    STATUS      current
    DESCRIPTION
        "The value of tmnxL2tpXtAvpCiscoNasPortEth specifies
        what string to put in the Cisco-NAS-Port AVP, for L2TP control messages
        related to a PPPoE session in this L2TP protocol instance.

       
         <origin>               ::= 'i' | 'm' | 'o' | 'p' | 's'

         'i' - inner VLAN ID
         'm' - MDA number
         'o' - outer VLAN ID
         'p' - port number
         's' - slot number

         Maximum 32 bits can be specified.
         
         If less than 32 bits are specified, the least significant bits are
         used and the omitted higher bits are set to zero.
         
         Example:  *12o*12i*2s01 means 'the 12 least significant bits of the
         outer VLAN ID, followed by the 12 least significant bits of the inner
         VLAN ID, followed by the two least significant bits of the slot number,
         followed by a zero and a one-bit', stored in network order in the least
         significant bits: 0000ooooooooooooiiiiiiiiiiiiss01.
         
         An empty string specifies that the Extended NAS-Port AVP must not be
         transmitted."
    DEFVAL { "" }
    ::= { tmnxL2tpXtEntry 8 }

tmnxL2tpXtAvpCiscoNasPortAtm OBJECT-TYPE
    SYNTAX      TmnxBinarySpecification
    MAX-ACCESS  read-create
    STATUS      current
    DESCRIPTION
        "The value of tmnxL2tpXtAvpCiscoNasPortAtm specifies
        what string to put in the Cisco-NAS-Port AVP, for L2TP control messages
        related to a PPPoA (PPP over ATM) session in this L2TP protocol instance.

       
         <origin>               ::= 'c' | 'i' | 'm' | 'p' | 's' | 'v'

         'c' - ATM VCI (Virtual Channel Identifier)
         'i' - inner VLAN ID
         'm' - MDA number
         'p' - port number
         's' - slot number
         'v' - ATM VPI (Virtual Path Identifier)

         Maximum 32 bits can be specified.
         
         If less than 32 bits are specified, the least significant bits are
         used and the omitted higher bits are set to zero.
         
         Example:  *12v*12c*2s01 means 'the 12 least significant bits of the
         ATM VPI, followed by the 12 least significant bits of the inner
         ATM VCI, followed by the two least significant bits of the slot number,
         followed by a zero and a one-bit', stored in network order in the least
         significant bits: 0000vvvvvvvvvvvvccccccccccccss01.
         
         An empty string specifies that the Extended NAS-Port AVP must not be
         transmitted."
    DEFVAL { "" }
    ::= { tmnxL2tpXtEntry 9 }
    
tmnxL2tpXtDfBitLac OBJECT-TYPE
    SYNTAX      TmnxAlwaysOrNever
    MAX-ACCESS  read-create
    STATUS      current
    DESCRIPTION
       "The value of tmnxL2tpXtDfBitLac specifies 
        if this system sets the DF (Don't Fragment) bit in the IP header
        of the data traffic sent from the LAC to the LNS.
         
        If the value of this object is 'always', the DF bit is set
        in upstream traffic.
        
        If the value of this object is 'never', the DF bit is cleared
        in upstream traffic.
        
        The value of this object is only relevant for tunnels where this system
        performs the LAC role."
    DEFVAL { always }
    ::= { tmnxL2tpXtEntry 10 }

--
--      L2TP Virtual Router Status and Statistics Group
--

-- ---------------------------------------------------------------------
--  tmnxL2tpStatTable
--
--
--  Sparse Dependent Extension of the TIMETRA-VRTR-MIB::vRtrConfTable.
--
--  The same indexes are used for both the base table, vRtrConfTable,
--  and the sparse dependent table, tmnxL2tpStatTable.
--
--  This in effect extends the vRtrConfTable with additional columns.
--  A row is automatically created in the tmnxL2tpStatTable for each  
--  applicable row in the vRtrConfTable .
--
--  Deletion of a row in the vRtrConfTable results in the
--  same fate for the row in the tmnxL2tpStatTable.
-- ---------------------------------------------------------------------

tmnxL2tpStatTable OBJECT-TYPE
    SYNTAX      SEQUENCE OF TmnxL2tpStatEntry
    MAX-ACCESS  not-accessible
    STATUS      current
    DESCRIPTION
        "A table that contains L2TP configuration 
         information about virtual routers.

         The system automatically creates an entry in this table
         for each virtual router where L2TP is supported. 
         
         Only the Base router supports L2TP."
    ::= { tmnxL2tpVrtrStatObjs 1 }

tmnxL2tpStatEntry OBJECT-TYPE
    SYNTAX      TmnxL2tpStatEntry
    MAX-ACCESS  not-accessible
    STATUS      current
    DESCRIPTION
        "L2TP specific information about a virtual router.
        
         Each entry represents a L2TP protocol instance."
    INDEX { vRtrID }
    ::= { tmnxL2tpStatTable 1 }

TmnxL2tpStatEntry ::=
    SEQUENCE {
        tmnxL2tpStatCleared              TimeStamp,
        tmnxL2tpStatTotalTunnels         Counter32,
        tmnxL2tpStatFailedTunnels        Counter32,
        tmnxL2tpStatFailedTuAuth         Counter32,
        tmnxL2tpStatActiveTunnels        Gauge32,
        tmnxL2tpStatTotalSessions        Counter32,
        tmnxL2tpStatFailedSessions       Counter32,
        tmnxL2tpStatActiveSessions       Gauge32,
        tmnxL2tpStatCurrentTunnels       Gauge32,
        tmnxL2tpStatCurrentSessions      Gauge32,
        tmnxL2tpStatCurrSelBlacklstLen   Gauge32,
        tmnxL2tpStatUnavailTunnelIds     Gauge32
    }

tmnxL2tpStatCleared   OBJECT-TYPE
    SYNTAX      TimeStamp
    MAX-ACCESS  read-only
    STATUS      current
    DESCRIPTION
        "The value of the object tmnxL2tpStatCleared indicates
         the value of sysUpTime when the system statistics were cleared.
         
         The value zero indicates that the system statistics have not been 
         cleared since the last re-initialization of the local network 
         management subsystem."
    ::= { tmnxL2tpStatEntry 1 }

tmnxL2tpStatTotalTunnels    OBJECT-TYPE
    SYNTAX      Counter32
    MAX-ACCESS  read-only
    STATUS      current
    DESCRIPTION
        "The value of tmnxL2tpStatTotalTunnels indicates
         the total number of tunnel set up attempts
         since the last re-initialization of the local network 
         management subsystem, or the last time the system statistics were 
         cleared."
    ::= { tmnxL2tpStatEntry 2 }

tmnxL2tpStatFailedTunnels   OBJECT-TYPE
    SYNTAX      Counter32
    MAX-ACCESS  read-only
    STATUS      current
    DESCRIPTION
       "The value of tmnxL2tpStatFailedTunnels indicates
        the number of tunnels that failed to reach the 
        established state since the last re-initialization of the local network 
        management subsystem, or the last time the system statistics were 
        cleared."
    ::= { tmnxL2tpStatEntry 3 }

tmnxL2tpStatFailedTuAuth    OBJECT-TYPE
    SYNTAX      Counter32
    MAX-ACCESS  read-only
    STATUS      current
    DESCRIPTION
       "The value of tmnxL2tpStatFailedTuAuth indicates
        the number of tunnels that failed authentication
        since the last re-initialization of the local network 
        management subsystem, or the last time the system statistics were 
        cleared."
    ::= { tmnxL2tpStatEntry 4 }

tmnxL2tpStatActiveTunnels   OBJECT-TYPE
    SYNTAX      Gauge32
    MAX-ACCESS  read-only
    STATUS      current
    DESCRIPTION
        "The value of tmnxL2tpStatActiveTunnels indicates 
        the number of tunnels currently established."
    ::= { tmnxL2tpStatEntry 5 }

tmnxL2tpStatTotalSessions  OBJECT-TYPE
    SYNTAX      Counter32
    MAX-ACCESS  read-only
    STATUS      current
    DESCRIPTION
       "The value of tmnxL2tpStatTotalSessions indicates
        the number of session creation attempts 
        since the last re-initialization of the local network 
        management subsystem, or the last time the system statistics were 
        cleared."
    ::= { tmnxL2tpStatEntry 6 }

tmnxL2tpStatFailedSessions  OBJECT-TYPE
    SYNTAX      Counter32
    MAX-ACCESS  read-only
    STATUS      current
    DESCRIPTION
       "The value of tmnxL2tpStatFailedSessions indicates
        the number of sessions that failed to reach the 
        established state since the last re-initialization of the local network 
        management subsystem, or the last time the system statistics were 
        cleared."
    ::= { tmnxL2tpStatEntry 7 }

tmnxL2tpStatActiveSessions  OBJECT-TYPE
    SYNTAX      Gauge32
    MAX-ACCESS  read-only
    STATUS      current
    DESCRIPTION
        "The value of tmnxL2tpStatActiveSessions indicates 
        the number of sessions currently established."
    ::= { tmnxL2tpStatEntry 8 }

tmnxL2tpStatCurrentTunnels  OBJECT-TYPE
    SYNTAX      Gauge32
    MAX-ACCESS  read-only
    STATUS      current
    DESCRIPTION
        "The value of tmnxL2tpStatCurrentTunnels indicates 
        the actual number of tunnels."
    ::= { tmnxL2tpStatEntry 9 }

tmnxL2tpStatCurrentSessions  OBJECT-TYPE
    SYNTAX      Gauge32
    MAX-ACCESS  read-only
    STATUS      current
    DESCRIPTION
        "The value of tmnxL2tpStatCurrentSessions indicates 
        the actual number of sessions."
    ::= { tmnxL2tpStatEntry 10 }

tmnxL2tpStatCurrSelBlacklstLen   OBJECT-TYPE
    SYNTAX      Gauge32
    MAX-ACCESS  read-only
    STATUS      current
    DESCRIPTION
        "The value of tmnxL2tpStatCurrSelBlacklstLen indicates
         the actual number of tunnels and peers in the
        tunnel-selection-blacklist."
    ::= { tmnxL2tpStatEntry 11 }

tmnxL2tpStatUnavailTunnelIds   OBJECT-TYPE
    SYNTAX      Gauge32
    MAX-ACCESS  read-only
    STATUS      current
    DESCRIPTION
        "The value of tmnxL2tpStatUnavailTunnelIds indicates
         the number of tunnel identifiers that is unavailable for the L2TP
         protocol because they are used by some other application.
         
         An example of such an application is NAT."
    ::= { tmnxL2tpStatEntry 12 }

-- ----------------------------------------------------------------------------
--      The "L2TP Tunnel Group" Group
-- ----------------------------------------------------------------------------
tmnxL2tpTgCfgObjs            OBJECT IDENTIFIER   ::= { tmnxL2tpTgObjs 1 }
tmnxL2tpTgStatObjs           OBJECT IDENTIFIER   ::= { tmnxL2tpTgObjs 2 }
tmnxL2tpTgOpObjs             OBJECT IDENTIFIER   ::= { tmnxL2tpTgObjs 3 }

--
--      The L2TP Tunnel Group Configuration Table
--

tmnxL2tpTgCfgTableLastCh OBJECT-TYPE
    SYNTAX      TimeStamp
    MAX-ACCESS  read-only
    STATUS      current
    DESCRIPTION
        "The value of the object tmnxL2tpTgCfgTableLastCh indicates
         the value of sysUpTime at the time of the last modification of
         an entry in the tmnxL2tpTgCfgTable."
    ::= { tmnxL2tpObjs 11 }

tmnxL2tpTgCfgTable   OBJECT-TYPE
    SYNTAX      SEQUENCE OF TmnxL2tpTgCfgEntry
    MAX-ACCESS  not-accessible
    STATUS      current
    DESCRIPTION
       "The L2TP Tunnel configuration table
        contains objects to configure L2TP Tunnel Groups."
    ::= { tmnxL2tpTgCfgObjs 2 }

tmnxL2tpTgCfgEntry   OBJECT-TYPE
        SYNTAX          TmnxL2tpTgCfgEntry
        MAX-ACCESS      not-accessible
        STATUS          current
        DESCRIPTION
       "Each conceptual row represents a Layer Two Tunneling Protocol
        Tunnel Group.

        Entries in this table can be created or deleted via SNMP operations."
    INDEX { vRtrID,
            tmnxL2tpTgCfgName }
    ::= { tmnxL2tpTgCfgTable 1 }

TmnxL2tpTgCfgEntry ::= 
    SEQUENCE {
        tmnxL2tpTgCfgName                TmnxL2tpTunnelGroupName,
        tmnxL2tpTgCfgRowStatus           RowStatus,
        tmnxL2tpTgCfgLastMgmtChange      TimeStamp,
        tmnxL2tpTgCfgDescription         TItemDescription,
        tmnxL2tpTgCfgAdminState          TmnxAdminState,
        tmnxL2tpTgCfgSecret              TmnxL2tpAuthSecret,
        tmnxL2tpTgCfgHelloInterval       TmnxL2tpTunnelHelloInterval,
        tmnxL2tpTgCfgIdleTO              TmnxL2tpTunnelIdleTO,
        tmnxL2tpTgCfgDestructTO          TmnxL2tpTunnelDestructTO,
        tmnxL2tpTgCfgMaxRetxEstab        TmnxL2tpTunnelMaxRetx,
        tmnxL2tpTgCfgMaxRetxNotEstab     TmnxL2tpTunnelMaxRetx,
        tmnxL2tpTgCfgSessionLimit        TmnxL2tpTunnelSessionLimit,
        tmnxL2tpTgCfgAvpHiding           TmnxL2tpAvpHidingMode,
        tmnxL2tpTgCfgSessionAssignMethod TmnxL2tpSessionAssignMethod,
        tmnxL2tpTgCfgLocalName           TmnxL2tpHostNameOrEmpty,
        tmnxL2tpTgCfgDoChallenge         TmnxL2tpDoChallenge,
        tmnxL2tpTgCfgReceiveWindowSize   TmnxL2tpReceiveWindowSize,
        tmnxL2tpTgCfgIsaGrpId            TmnxL2tpIsaGrpIdOrZero,
        tmnxL2tpTgCfgAddrType            InetAddressType,
        tmnxL2tpTgCfgAddr                InetAddress,
        tmnxL2tpTgCfgLoadBalanceMethod   TmnxL2tpIsaMdaLoadBalanceMethod,
        tmnxL2tpTgCfgAccountingPolicy    TNamedItemOrEmpty
    }
        
tmnxL2tpTgCfgName OBJECT-TYPE
    SYNTAX      TmnxL2tpTunnelGroupName
    MAX-ACCESS  not-accessible
    STATUS      current
    DESCRIPTION
       "The value of the object tmnxL2tpTgCfgName specifies the string to
        identify this Layer Two Tunneling Protocol Tunnel Group."
    ::= { tmnxL2tpTgCfgEntry 1 }

tmnxL2tpTgCfgRowStatus OBJECT-TYPE
    SYNTAX      RowStatus
    MAX-ACCESS  read-create
    STATUS      current
    DESCRIPTION
       "The value of tmnxL2tpTgCfgRowStatus specifies the row status of
        this row."
    ::= { tmnxL2tpTgCfgEntry 2 }

tmnxL2tpTgCfgLastMgmtChange OBJECT-TYPE
    SYNTAX      TimeStamp
    MAX-ACCESS  read-only
    STATUS      current
    DESCRIPTION
        "The value of tmnxL2tpTgCfgLastMgmtChange indicates the sysUpTime at
         the time of the most recent management-initiated change to this
         table row."
    ::= { tmnxL2tpTgCfgEntry 3 }

tmnxL2tpTgCfgDescription OBJECT-TYPE
    SYNTAX      TItemDescription
    MAX-ACCESS  read-create
    STATUS      current
    DESCRIPTION
       "The value of tmnxL2tpTgCfgDescription specifies the
        description of this Layer Two Tunneling Protocol Tunnel Group."
    DEFVAL { "" }
    ::= { tmnxL2tpTgCfgEntry 4 }

tmnxL2tpTgCfgAdminState OBJECT-TYPE
    SYNTAX      TmnxAdminState
    MAX-ACCESS  read-create
    STATUS      current
    DESCRIPTION
       "The value of tmnxL2tpTgCfgAdminState specifies the
        administrative state of this Layer Two Tunneling Protocol Tunnel Group."
    DEFVAL { outOfService }
    ::= { tmnxL2tpTgCfgEntry 5 }

tmnxL2tpTgCfgSecret OBJECT-TYPE
    SYNTAX      TmnxL2tpAuthSecret
    MAX-ACCESS  read-create
    STATUS      current
    DESCRIPTION
       "The value of the object tmnxL2tpTgCfgSecret specifies
        the password to be used for the authentication of the tunnels in this
        Layer Two Tunneling Protocol Tunnel Group.

        For any given tunnel in this group, the value of tmnxL2tpTgCfgSecret
        can be overruled with the value of tmnxL2tpTuCfgSecret.

        This value overrules the value of the object tmnxL2tpSecret of the 
        virtual router this tunnel group belongs to.
        
        This object will always return an empty string on a read."
    DEFVAL { ''H }
    ::= { tmnxL2tpTgCfgEntry 6 }

tmnxL2tpTgCfgHelloInterval OBJECT-TYPE
    SYNTAX      TmnxL2tpTunnelHelloInterval
    UNITS       "seconds"
    MAX-ACCESS  read-create
    STATUS      current
    DESCRIPTION
       "The value of tmnxL2tpTgCfgHelloInterval specifies
        the time interval between two consecutive tunnel Hello messages.

        A value of '-1' specifies that the keepalive function is disabled.

        A value of '-2' specifies that the value must be set to the actual
        value of the object tmnxL2tpHelloInterval."
    DEFVAL    { -2 }
        ::= { tmnxL2tpTgCfgEntry 7 }

tmnxL2tpTgCfgIdleTO OBJECT-TYPE
    SYNTAX      TmnxL2tpTunnelIdleTO
    UNITS       "seconds"
    MAX-ACCESS  read-create
    STATUS      current
    DESCRIPTION
       "The value of tmnxL2tpTgCfgIdleTO specifies
        the period of time that an established tunnel with no active sessions 
        will persist before being disconnected.

        A value of -1 leaves the tunnel up indefinitely.

        A value of '-2' specifies that the value must be set to the actual
        value of the object tmnxL2tpIdleTO."
    DEFVAL    { -2 }
        ::= { tmnxL2tpTgCfgEntry 8 }

tmnxL2tpTgCfgDestructTO OBJECT-TYPE
    SYNTAX      TmnxL2tpTunnelDestructTO
    UNITS       "seconds"
    MAX-ACCESS  read-create
    STATUS      current
    DESCRIPTION
       "The value of tmnxL2tpTgCfgDestructTO specifies
        the period of time that the data of a disconnected tunnel 
        will persist before being removed.

        A value of '-2' specifies that the value must be set to the actual
        value of the object tmnxL2tpDestructTO."
    DEFVAL    { -2 }
        ::= { tmnxL2tpTgCfgEntry 9 }

tmnxL2tpTgCfgMaxRetxEstab OBJECT-TYPE
    SYNTAX      TmnxL2tpTunnelMaxRetx
    MAX-ACCESS  read-create
    STATUS      current
    DESCRIPTION
       "The value of tmnxL2tpTgCfgMaxRetxEstab specifies
        the number of retries allowed for established tunnels before their
        control connection goes down.

        A value of '-2' specifies that the value must be set to the actual
        value of the object tmnxL2tpMaxRetxEstab."
    DEFVAL    { -2 }
        ::= { tmnxL2tpTgCfgEntry 10 }

tmnxL2tpTgCfgMaxRetxNotEstab OBJECT-TYPE
    SYNTAX      TmnxL2tpTunnelMaxRetx
    MAX-ACCESS  read-create
    STATUS      current
    DESCRIPTION
       "The value of tmnxL2tpTgCfgMaxRetxNotEstab specifies
        the number of retries allowed for unestablished tunnels before their
        control connection goes down.

        A value of '-2' specifies that the value must be set to the actual
        value of the object tmnxL2tpMaxRetxNotEstab."
    DEFVAL    { -2 }
        ::= { tmnxL2tpTgCfgEntry 11 }

tmnxL2tpTgCfgSessionLimit OBJECT-TYPE
    SYNTAX      TmnxL2tpTunnelSessionLimit
    MAX-ACCESS  read-create
    STATUS      current
    DESCRIPTION
       "The value of tmnxL2tpTgCfgSessionLimit specifies
        the maximum number of sessions in this Layer Two Tunneling Protocol 
        Tunnel Group.

        A value of '-2' specifies that the value must be set to the actual
        value of the object tmnxL2tpGroupSessionLimit."
    DEFVAL    { -2 }
        ::= { tmnxL2tpTgCfgEntry 12 }

tmnxL2tpTgCfgAvpHiding OBJECT-TYPE
    SYNTAX      TmnxL2tpAvpHidingMode
    MAX-ACCESS  read-create
    STATUS      current
    DESCRIPTION
       "The value of the object tmnxL2tpTgCfgAvpHiding specifies
        the method to be used for the authentication of the tunnels in this
        Layer Two Tunneling Protocol Tunnel Group.

        The value 'default' specifies that the value must be set to the actual
        value of the object tmnxL2tpAvpHiding."
    REFERENCE
       "RFC 2661 Layer Two Tunneling Protocol 'L2TP', 
        section 4.3 Hiding of AVP Attribute Values."
    DEFVAL { default }
    ::= { tmnxL2tpTgCfgEntry 13 }

tmnxL2tpTgCfgSessionAssignMethod OBJECT-TYPE
    SYNTAX      TmnxL2tpSessionAssignMethod
    MAX-ACCESS  read-create
    STATUS      current
    DESCRIPTION
       "The value of the object tmnxL2tpTgCfgSessionAssignMethod specifies
        the method to be used for the authentication of the tunnels in this
        Layer Two Tunneling Protocol Tunnel Group.

        The value 'default' specifies that the value must be set to the actual
        value of the object tmnxL2tpSessionAssignMethod."
    DEFVAL { default }
    ::= { tmnxL2tpTgCfgEntry 14 }  

tmnxL2tpTgCfgLocalName OBJECT-TYPE
    SYNTAX      TmnxL2tpHostNameOrEmpty
    MAX-ACCESS  read-create
    STATUS      current
    DESCRIPTION
       "The value of the object tmnxL2tpTgCfgLocalName specifies
        the host name used by this system for the tunnels in this
        Layer Two Tunneling Protocol Tunnel Group during the authentication 
        phase of tunnel establishment.

        This object is related to the RADIUS attribute Tunnel-Client-Auth-ID.

        It can be used to distinguish tunnels.
        
        An empty string specifies that the value of the object 
        tmnxL2tpLocalName is used."
    REFERENCE
       "RFC 2868 RADIUS Attributes for Tunnel Protocol Support
        section 3.9."
    DEFVAL { ''H }
    ::= { tmnxL2tpTgCfgEntry 15 }

tmnxL2tpTgCfgDoChallenge OBJECT-TYPE
    SYNTAX      TmnxL2tpDoChallenge
    MAX-ACCESS  read-create
    STATUS      current
    DESCRIPTION
       "The value of the object tmnxL2tpTgCfgDoChallenge specifies
        when challenge-response is to be used for the authentication of 
        the tunnels in this Layer Two Tunneling Protocol Tunnel Group.

        The value 'default' specifies that the value must be set to the actual
        value of the object tmnxL2tpDoChallenge."
    DEFVAL { default }
    ::= { tmnxL2tpTgCfgEntry 16 }  

tmnxL2tpTgCfgReceiveWindowSize OBJECT-TYPE
    SYNTAX      TmnxL2tpReceiveWindowSize
    MAX-ACCESS  read-create
    STATUS      current
    DESCRIPTION
       "The value of the object tmnxL2tpTgCfgReceiveWindowSize specifies
        the Receive Window Size of the tunnels in this L2TP Tunnel Group.
        
        The value zero specifies that the value must be set to the actual
        value of the object tmnxL2tpReceiveWindowSize."
    DEFVAL { 0 }
    ::= { tmnxL2tpTgCfgEntry 17 }  

tmnxL2tpTgCfgIsaGrpId OBJECT-TYPE
    SYNTAX      TmnxL2tpIsaGrpIdOrZero
    MAX-ACCESS  read-create
    STATUS      current
    DESCRIPTION
       "The value of tmnxL2tpTgCfgIsaGrpId specifies the
        L2TP Integrated Service Adaptor group for the tunnels
        in this L2TP Tunnel Group."
    DEFVAL { 0 }
    ::= { tmnxL2tpTgCfgEntry 19 }

tmnxL2tpTgCfgAddrType OBJECT-TYPE
    SYNTAX      InetAddressType
    MAX-ACCESS  read-create
    STATUS      current
    DESCRIPTION 
       "The value of tmnxL2tpTgCfgAddrType specifies the
        address type of tmnxL2tpTgCfgAddr.

        The value 'unknown' specifies that the value must be set to the actual
        value of the object tmnxL2tpAddrType.
       "
    DEFVAL { unknown }
    ::= { tmnxL2tpTgCfgEntry 20 }

tmnxL2tpTgCfgAddr OBJECT-TYPE
    SYNTAX      InetAddress (SIZE(0|4|16))
    MAX-ACCESS  read-create
    STATUS      current
    DESCRIPTION 
       "The value of tmnxL2tpTgCfgAddr specifies the local IP
        address of the tunnels in this L2TP Tunnel Group.

        The value ''H specifies that the value must be set to the actual
        value of the object tmnxL2tpAddr.
       "
    DEFVAL { ''H }  
    ::= { tmnxL2tpTgCfgEntry 21 }

tmnxL2tpTgCfgLoadBalanceMethod OBJECT-TYPE
    SYNTAX      TmnxL2tpIsaMdaLoadBalanceMethod
    MAX-ACCESS  read-create
    STATUS      current
    DESCRIPTION
       "The value of the object tmnxL2tpTgCfgLoadBalanceMethod specifies
        the method to be used for load-balancing sessions across ISA MDA
        in this Layer Two Tunneling Protocol Tunnel Group.
        
        The value 'default' is not allowed."
    DEFVAL { perSession }
    ::= { tmnxL2tpTgCfgEntry 25 }  

tmnxL2tpTgCfgAccountingPolicy OBJECT-TYPE
    SYNTAX      TNamedItemOrEmpty
    MAX-ACCESS  read-create
    STATUS      current
    DESCRIPTION
       "The value of the object tmnxL2tpTgCfgAccountingPolicy specifies
        the RADIUS accounting policy to be used in this Layer Two Tunneling 
        Protocol Tunnel Group.
        
        It refers to a conceptual row in the tmnxL2tpApTable.
        
        The value of tmnxL2tpTgCfgAccountingPolicy can be overruled by
         a non-empty value of tmnxL2tpTuCfgAccountingPolicy.
        
        An empty string specifies that the value of tmnxL2tpAccountingPolicy
        must be used."
    DEFVAL { ''H }
    ::= { tmnxL2tpTgCfgEntry 26 }

--
--      The L2TP LNS Tunnel Group PPP Configuration Table
--
--  Augments the tmnxL2tpTgCfgTable.
--
--  The use of the AUGMENTS clause implies a one-to-one dependent relationship
--  between the base table, tmnxL2tpTgCfgTable, and the augmenting table,
--  tmnxL2tpLnsTgPppTable. This in effect extends the tmnxL2tpTgCfgTable
--  with additional columns. Creation (or deletion) of a row in the
--  tmnxL2tpTgCfgTable results in the same fate for the row in the
--  tmnxL2tpLnsTgPppTable.
-- 

tmnxL2tpLnsTgPppTableLastCh OBJECT-TYPE
    SYNTAX      TimeStamp
    MAX-ACCESS  read-only
    STATUS      current
    DESCRIPTION
        "The value of the object tmnxL2tpLnsTgPppTableLastCh indicates
         the value of sysUpTime at the time of the last modification of
         an entry in the tmnxL2tpLnsTgPppTable."
    ::= { tmnxL2tpObjs 18 }

tmnxL2tpLnsTgPppTable   OBJECT-TYPE
    SYNTAX      SEQUENCE OF TmnxL2tpLnsTgPppEntry
    MAX-ACCESS  not-accessible
    STATUS      current
    DESCRIPTION
       "The L2TP Tunnel configuration table
        contains objects to configure PPP (Point to Point Protocol) 
        on L2TP LNS Tunnel Groups.
        
        Entries in this table are automatically created and deleted by the
        system."
    ::= { tmnxL2tpTgCfgObjs 3 }

tmnxL2tpLnsTgPppEntry   OBJECT-TYPE
        SYNTAX          TmnxL2tpLnsTgPppEntry
        MAX-ACCESS      not-accessible
        STATUS          current
        DESCRIPTION
       "Each conceptual row represents PPP information about 
        a Layer Two Tunneling Protocol LNS Tunnel Group."
    AUGMENTS { tmnxL2tpTgCfgEntry }
    ::= { tmnxL2tpLnsTgPppTable 1 }

TmnxL2tpLnsTgPppEntry ::= 
    SEQUENCE {
        tmnxL2tpLnsTgPppLastMgmtChange   TimeStamp,
        tmnxL2tpLnsTgPppAuthPlcy         TNamedItemOrEmpty,
        tmnxL2tpLnsTgPppAuthProtocol     TmnxL2tpPppAuthentication,
        tmnxL2tpLnsTgPppUserDb           TNamedItemOrEmpty,
        tmnxL2tpLnsTgPppDefaultService   TmnxServId,
        tmnxL2tpLnsTgPppDefaultGroupIf   TNamedItemOrEmpty,
        tmnxL2tpLnsTgPppProxyLcp         TmnxAlwaysOrNever,
        tmnxL2tpLnsTgPppProxyAuth        TmnxAlwaysOrNever,
        tmnxL2tpLnsTgPppMtu              TmnxL2tpPppMtu,
        tmnxL2tpLnsTgPppLcpKaInterval    TmnxL2tpLcpKaInterval,
        tmnxL2tpLnsTgPppLcpKaHoldUp      TmnxL2tpLcpKaHoldUpMplier,
        tmnxL2tpLnsTgPppIpcpSubnetNeg    TmnxAlwaysOrNever,
        tmnxL2tpLnsTgPppLcpIgnoreMagic   TmnxAlwaysOrNever,
        tmnxL2tpLnsTgPppMinChapChall     Unsigned32,
        tmnxL2tpLnsTgPppMaxChapChall     Unsigned32
    }
        
tmnxL2tpLnsTgPppLastMgmtChange OBJECT-TYPE
    SYNTAX      TimeStamp
    MAX-ACCESS  read-only
    STATUS      current
    DESCRIPTION
        "The value of tmnxL2tpLnsTgPppLastMgmtChange indicates the sysUpTime at
         the time of the most recent management-initiated change to this
         table row."
    ::= { tmnxL2tpLnsTgPppEntry 1 }

tmnxL2tpLnsTgPppAuthPlcy OBJECT-TYPE
    SYNTAX      TNamedItemOrEmpty
    MAX-ACCESS  read-create
    STATUS      current
    DESCRIPTION
       "The value of the object tmnxL2tpLnsTgPppAuthPlcy specifies
        the authentication policy used by this system for the tunnels in this
        L2TP LNS Tunnel Group during the authentication 
        phase of tunnel establishment.

        An empty string specifies that no authentication policy is used."
    DEFVAL { ''H }
    ::= { tmnxL2tpLnsTgPppEntry 2 }

tmnxL2tpLnsTgPppAuthProtocol OBJECT-TYPE
    SYNTAX      TmnxL2tpPppAuthentication
    MAX-ACCESS  read-create
    STATUS      current
    DESCRIPTION
       "The value of the object tmnxL2tpLnsTgPppAuthProtocol specifies
        for the tunnels in this  L2TP LNS Tunnel Group 
        what PPP authentication protocol(s) will be negotiated during the LCP 
        phase.

        The value 'default' is not allowed."
    DEFVAL { prefChap }
    ::= { tmnxL2tpLnsTgPppEntry 3 }

tmnxL2tpLnsTgPppUserDb OBJECT-TYPE
    SYNTAX      TNamedItemOrEmpty
    MAX-ACCESS  read-create
    STATUS      current
    DESCRIPTION
       "The value of the object tmnxL2tpLnsTgPppUserDb specifies
        the local user database to use for PADI or PPP PAP/CHAP based 
        authentication during the authentication phase of tunnel establishment.

        An empty string specifies that no local user database is used."
    DEFVAL { ''H }
    ::= { tmnxL2tpLnsTgPppEntry 4 }

tmnxL2tpLnsTgPppDefaultService OBJECT-TYPE
    SYNTAX      TmnxServId
    MAX-ACCESS  read-create
    STATUS      current
    DESCRIPTION
       "The value of tmnxL2tpLnsTgPppDefaultService specifies the
        service ID of the service where the PPP sessions are established
        when the authentication server does not specify the service ID."
    DEFVAL { 0 }
    ::= { tmnxL2tpLnsTgPppEntry 5 }

tmnxL2tpLnsTgPppDefaultGroupIf OBJECT-TYPE
    SYNTAX      TNamedItemOrEmpty
    MAX-ACCESS  read-create
    STATUS      current
    DESCRIPTION
       "The value of tmnxL2tpLnsTgPppDefaultGroupIf specifies the
        group interface where the PPP sessions are established
        when the authentication server does not specify the group interface."
    DEFVAL { "" }
    ::= { tmnxL2tpLnsTgPppEntry 6 }

tmnxL2tpLnsTgPppProxyLcp OBJECT-TYPE
    SYNTAX      TmnxAlwaysOrNever
    MAX-ACCESS  read-create
    STATUS      current
    DESCRIPTION
       "The value of tmnxL2tpLnsTgPppProxyLcp specifies 
        if this system re-uses the result of the Link Control Protocol (LCP) 
        negotiation done by the proxy (LAC).
         
        If the value of this object is 'always', the Proxy LCP AVPs received from
        the LAC are used to initiate the LCP on this system.
        
        If the value of this object is 'never', this system restarts the LCP
        negotiation with the remote system."
    REFERENCE
       "RFC 2661 Layer Two Tunneling Protocol 'L2TP', 
        section 4.4.5 Proxy LCP and Authentication AVPs."
    DEFVAL { never }
    ::= { tmnxL2tpLnsTgPppEntry 7 }

tmnxL2tpLnsTgPppProxyAuth OBJECT-TYPE
    SYNTAX      TmnxAlwaysOrNever
    MAX-ACCESS  read-create
    STATUS      current
    DESCRIPTION
       "The value of tmnxL2tpLnsTgPppProxyAuth specifies 
        if this system re-uses the authentication done by the proxy (LAC).
         
        If the value of this object is 'always', the Authentication AVPs received 
        from the LAC are accepted.
        
        If the value of this object is 'never', this system restarts the 
        authentication of the remote system."
    REFERENCE
       "RFC 2661 Layer Two Tunneling Protocol 'L2TP', 
        section 4.4.5 Proxy LCP and Authentication AVPs."
    DEFVAL { never }
    ::= { tmnxL2tpLnsTgPppEntry 8 }

tmnxL2tpLnsTgPppMtu OBJECT-TYPE
    SYNTAX      TmnxL2tpPppMtu
    MAX-ACCESS  read-create
    STATUS      current
    DESCRIPTION
       "The value of tmnxL2tpLnsTgPppMtu specifies the
        MTU (Maximum Transmission Unit) for the tunnels
        in this L2TP LNS Tunnel Group.
        
         The value zero is not allowed."
    DEFVAL { 1500 }
    ::= { tmnxL2tpLnsTgPppEntry 9 }

tmnxL2tpLnsTgPppLcpKaInterval OBJECT-TYPE
    SYNTAX      TmnxL2tpLcpKaInterval
    UNITS       "seconds"
    MAX-ACCESS  read-create
    STATUS      current
    DESCRIPTION
       "The value of tmnxL2tpLnsTgPppLcpKaInterval specifies 
        for the tunnels in this L2TP LNS Tunnel Group
        the time interval in seconds at which LCP echo requests are transmitted.
        
        The value '0' is not allowed."
    DEFVAL { 30 }
    ::= { tmnxL2tpLnsTgPppEntry 10 }

tmnxL2tpLnsTgPppLcpKaHoldUp OBJECT-TYPE
    SYNTAX      TmnxL2tpLcpKaHoldUpMplier
    MAX-ACCESS  read-create
    STATUS      current
    DESCRIPTION
       "The value of tmnxL2tpLnsTgPppLcpKaHoldUp specifies 
        for the tunnels in this L2TP LNS Tunnel Group
        how many LCP keepalive messages can be missed before the related 
        session is brought down.
        
        The value '0' is not allowed."
    DEFVAL { 3 }
    ::= { tmnxL2tpLnsTgPppEntry 11 }

tmnxL2tpLnsTgPppIpcpSubnetNeg OBJECT-TYPE
    SYNTAX      TmnxAlwaysOrNever
    MAX-ACCESS  read-create
    STATUS      current
    DESCRIPTION
       "The value of tmnxL2tpLnsTgPppIpcpSubnetNeg specifies 
        for the tunnels in this L2TP LNS Tunnel Group
        if IPCP subnet negotiation is enabled."
    DEFVAL { never }
    ::= { tmnxL2tpLnsTgPppEntry 13 }

tmnxL2tpLnsTgPppLcpIgnoreMagic OBJECT-TYPE
    SYNTAX      TmnxAlwaysOrNever
    MAX-ACCESS  read-create
    STATUS      current
    DESCRIPTION
       "The value of tmnxL2tpLnsTgPppLcpIgnoreMagic specifies 
        for the tunnels in this L2TP LNS Tunnel Group
        if checking the Magic-Number field in LCP Echo-Request and 
        Echo-Reply messages is skipped.
         
        If the value of tmnxL2tpLnsTgPppLcpIgnoreMagic is equal to 'never',
        checking is performed.
         
        If the value of tmnxL2tpLnsTgPppLcpIgnoreMagic is equal to 'always',
        checking is not performed."
    REFERENCE
       "RFC 1661 PPP section 6.4. Magic-Number."
    DEFVAL { never }
    ::= { tmnxL2tpLnsTgPppEntry 20 }

tmnxL2tpLnsTgPppMinChapChall OBJECT-TYPE
    SYNTAX      Unsigned32 (8..64)
    MAX-ACCESS  read-create
    STATUS      current
    DESCRIPTION
        "The value of tmnxL2tpLnsTgPppMinChapChall specifies the minimum
         length of the CHAP challenge generated by the system.
         
         Set the value of this object together with the value
         of tmnxL2tpLnsTgPppMaxChapChall.
         
         The value of tmnxL2tpLnsTgPppMaxChapChall must be equal to zero
         while the value of this object is equal to zero."
    DEFVAL { 32 }
    ::= { tmnxL2tpLnsTgPppEntry 21 }

tmnxL2tpLnsTgPppMaxChapChall OBJECT-TYPE
    SYNTAX      Unsigned32 (8..64)
    MAX-ACCESS  read-create
    STATUS      current
    DESCRIPTION
        "The value of tmnxL2tpLnsTgPppMaxChapChall specifies the maximum
         length of the CHAP challenge generated by the system.
         
         Set the value of this object together with the value
         of tmnxL2tpLnsTgPppMinChapChall.
         
         The value of tmnxL2tpLnsTgPppMinChapChall must be equal to zero
         while the value of this object is equal to zero."
    DEFVAL { 64 }
    ::= { tmnxL2tpLnsTgPppEntry 22 }

--
--      The L2TP Tunnel Group MLPPP Configuration Table
--
--  Augments the tmnxL2tpTgCfgTable.
--
--  The use of the AUGMENTS clause implies a one-to-one dependent relationship
--  between the base table, tmnxL2tpTgCfgTable, and the augmenting table,
--  tmnxL2tpTgMlpppTable. This in effect extends the tmnxL2tpTgCfgTable
--  with additional columns. Creation (or deletion) of a row in the
--  tmnxL2tpTgCfgTable results in the same fate for the row in the
--  tmnxL2tpTgMlpppTable.
-- 

tmnxL2tpTgMlpppTable   OBJECT-TYPE
    SYNTAX      SEQUENCE OF TmnxL2tpTgMlpppEntry
    MAX-ACCESS  not-accessible
    STATUS      current
    DESCRIPTION
       "The L2TP Tunnel configuration table
        contains objects to configure MLPPP (Multi Link Point to Point Protocol) 
        on L2TP Tunnel Groups.
        
        Entries in this table are automatically created and deleted by the
        system."
    ::= { tmnxL2tpTgCfgObjs 4 }

tmnxL2tpTgMlpppEntry   OBJECT-TYPE
        SYNTAX          TmnxL2tpTgMlpppEntry
        MAX-ACCESS      not-accessible
        STATUS          current
        DESCRIPTION
       "Each conceptual row represents MLPPP information about 
        a Layer Two Tunneling Protocol LNS Tunnel Group."
    AUGMENTS { tmnxL2tpTgCfgEntry }
    ::= { tmnxL2tpTgMlpppTable 1 }

TmnxL2tpTgMlpppEntry ::= 
    SEQUENCE {
        tmnxL2tpTgMlpppLastMgmtChange    TimeStamp,
        tmnxL2tpTgMlpppAdminState        TmnxAdminState,
        tmnxL2tpTgMlpppMaxLinks          Unsigned32,
        tmnxL2tpTgMlpppInterleave        TmnxAlwaysOrNever,
        tmnxL2tpTgMlpppMaxFragDelay      TmnxL2tpMlpppMaxFragDelay,
        tmnxL2tpTgMlpppReassemblyTo      TmnxL2tpMlpppReassemblyTimeout,
        tmnxL2tpTgMlpppShortSeqNumberRx  TmnxAlwaysOrNever,
        tmnxL2tpTgMlpppEpClass           TmnxL2tpMlpppEndpointClass,
        tmnxL2tpTgMlpppEpIpv4Address     InetAddressIPv4,
        tmnxL2tpTgMlpppEpMacAddress      MacAddress        
    }
        
tmnxL2tpTgMlpppLastMgmtChange OBJECT-TYPE
    SYNTAX      TimeStamp
    MAX-ACCESS  read-only
    STATUS      current
    DESCRIPTION
        "The value of tmnxL2tpTgMlpppLastMgmtChange indicates the sysUpTime at
         the time of the most recent management-initiated change to this
         table row."
    ::= { tmnxL2tpTgMlpppEntry 1 }

tmnxL2tpTgMlpppAdminState OBJECT-TYPE
    SYNTAX      TmnxAdminState
    MAX-ACCESS  read-create
    STATUS      current
    DESCRIPTION
       "The value of tmnxL2tpTgMlpppAdminState specifies the
        administrative state of MLPPP for this 
        Layer Two Tunneling Protocol Tunnel Group."
    DEFVAL { outOfService }
    ::= { tmnxL2tpTgMlpppEntry 2 }

tmnxL2tpTgMlpppMaxLinks OBJECT-TYPE
    SYNTAX      Unsigned32 (1..8)
    MAX-ACCESS  read-create
    STATUS      current
    DESCRIPTION
       "The value of the object tmnxL2tpTgMlpppMaxLinks specifies
        the maximum number of MLPPP links.
        
        The value of this object is only relevant for tunnels where this system
        performs the LNS role."
    DEFVAL { 1 }
    ::= { tmnxL2tpTgMlpppEntry 3 }

tmnxL2tpTgMlpppInterleave OBJECT-TYPE
    SYNTAX      TmnxAlwaysOrNever
    MAX-ACCESS  read-create
    STATUS      current
    DESCRIPTION
       "The value of tmnxL2tpTgMlpppInterleave specifies 
        if this system applies Link Fragmentation and Interleaving to the
        traffic sent from the LNS to the LAC.
         
        If the value of this object is 'always', downstream traffic is
        fragmented and interleaved, meaning that (non-fragmented) realtime 
        traffic is interleaved with fragments of non-realtime traffic.
        
        If the value of this object is 'never', downstream traffic is only
        fragmented but not reordered according to priority.
        
        The value of this object is only relevant for tunnels where this system
        performs the LNS role."
    DEFVAL { never }
    ::= { tmnxL2tpTgMlpppEntry 4 }

tmnxL2tpTgMlpppMaxFragDelay OBJECT-TYPE
    SYNTAX      TmnxL2tpMlpppMaxFragDelay
    UNITS       "milliseconds"
    MAX-ACCESS  read-create
    STATUS      current
    DESCRIPTION
       "The value of tmnxL2tpTgMlpppMaxFragDelay specifies the
        maximum delay for fragments for the tunnels
        in this L2TP LNS Tunnel Group.
        
        The value zero means 'no fragmentation'.
        
        The value of this object is only relevant for tunnels where this system
        performs the LNS role."
    DEFVAL { 0 }
    ::= { tmnxL2tpTgMlpppEntry 5 }

tmnxL2tpTgMlpppReassemblyTo OBJECT-TYPE
    SYNTAX      TmnxL2tpMlpppReassemblyTimeout (100|1000)
    UNITS       "milliseconds"
    MAX-ACCESS  read-create
    STATUS      current
    DESCRIPTION
       "The value of tmnxL2tpTgMlpppReassemblyTo specifies the
        reassembly timeout for fragments for the tunnels
        in this L2TP LNS Tunnel Group.
        
        The value zero is not allowed.
        
        The value of this object is only relevant for tunnels where this system
        performs the LNS role."
    DEFVAL { 1000 }
    ::= { tmnxL2tpTgMlpppEntry 6 }

tmnxL2tpTgMlpppShortSeqNumberRx OBJECT-TYPE
    SYNTAX      TmnxAlwaysOrNever
    MAX-ACCESS  read-create
    STATUS      current
    DESCRIPTION
       "The value of tmnxL2tpTgMlpppShortSeqNumberRx specifies 
        if this system requests to receive short sequence numbers from the peer.
         
        If the value of this object is 'always', this system includes 
        the Short Sequence Number Header Format Option in its LCP configuration
        options.
        
        If the value of this object is 'never', this system does not includes 
        the Short Sequence Number Header Format Option in its LCP configuration
        options.
        
        The value of this object is only relevant for tunnels where this system
        performs the LNS role."
        REFERENCE
           "RFC 1990 The PPP Multilink Protocol (MP)
            section 5.1.2."
    DEFVAL { never }
    ::= { tmnxL2tpTgMlpppEntry 7 }

tmnxL2tpTgMlpppEpClass OBJECT-TYPE
    SYNTAX      TmnxL2tpMlpppEndpointClass
    MAX-ACCESS  read-create
    STATUS      current
    DESCRIPTION
       "The value of tmnxL2tpTgMlpppEpClass specifies the
        type of endpoint.
        
        If the value of 'tmnxL2tpTgMlpppEpClass' is equal to 'ipv4Address',
        the address for the MLPPP Endpoint Discriminator Option is taken from
        tmnxL2tpTgMlpppEpIpv4Address.
        
        If the value of 'tmnxL2tpTgMlpppEpClass' is equal to 'macAddress',
        the address for the MLPPP Endpoint Discriminator Option is taken from
        tmnxL2tpTgMlpppEpMacAddress.
        
        If the value of 'tmnxL2tpTgMlpppEpClass' is equal to 'default',
        the MLPPP Endpoint Discriminator Option must not be transmitted.
        
        A value other than 'default' is only relevant for tunnels 
        where this system performs the LNS role."
    REFERENCE
       "RFC 1990 The PPP Multilink Protocol (MP), 
        section 5.1.3 Endpoint Discriminator Option."
    DEFVAL { default }
    ::= { tmnxL2tpTgMlpppEntry 8 }

tmnxL2tpTgMlpppEpIpv4Address OBJECT-TYPE
    SYNTAX      InetAddressIPv4
    MAX-ACCESS  read-create
    STATUS      current
    DESCRIPTION
       "The value of tmnxL2tpTgMlpppEpIpv4Address specifies the
        class 2 address to use in the MLPPP Endpoint Discriminator Option.
        
        While the value of tmnxL2tpTgMlpppEpClass is equal to 'ipv4Address',
        a value of all zeroes specifies that the system IP address be used;
        otherwise, it means that no address is specified."
    REFERENCE
       "RFC 1990 The PPP Multilink Protocol (MP), 
        section 5.1.3 Endpoint Discriminator Option."
    DEFVAL { ''H }  
    ::= { tmnxL2tpTgMlpppEntry 9 }

tmnxL2tpTgMlpppEpMacAddress OBJECT-TYPE
    SYNTAX      MacAddress
    MAX-ACCESS  read-create
    STATUS      current
    DESCRIPTION
       "The value of tmnxL2tpTgMlpppEpMacAddress specifies the
        class 3 address to use in the MLPPP Endpoint Discriminator Option.
        
        While the value of tmnxL2tpTgMlpppEpClass is equal to 'macAddress',
        a value of all zeroes specifies that the system MAC address be used;
        otherwise, it means that no address is specified."
    REFERENCE
       "RFC 1990 The PPP Multilink Protocol (MP), 
        section 5.1.3 Endpoint Discriminator Option."
    DEFVAL { ''H }  
        ::= { tmnxL2tpTgMlpppEntry 10 }

--
--      The L2TP Extended Tunnel Group Configuration Table
--
--  Augments the tmnxL2tpTgCfgTable.
--
--  The use of the AUGMENTS clause implies a one-to-one dependent relationship
--  between the base table, tmnxL2tpTgCfgTable, and the augmenting table,
--  tmnxL2tpTgXtTable. This in effect extends the tmnxL2tpTgCfgTable
--  with additional columns. Creation (or deletion) of a row in the
--  tmnxL2tpTgCfgTable results in the same fate for the row in the
--  tmnxL2tpTgXtTable.
-- 

tmnxL2tpTgXtTableLastCh OBJECT-TYPE
    SYNTAX      TimeStamp
    MAX-ACCESS  read-only
    STATUS      current
    DESCRIPTION
        "The value of the object tmnxL2tpTgXtTableLastCh indicates
         the value of sysUpTime at the time of the last modification of
         an entry in the tmnxL2tpTgXtTable."
    ::= { tmnxL2tpObjs 24 }
    
tmnxL2tpTgXtTable   OBJECT-TYPE
    SYNTAX      SEQUENCE OF TmnxL2tpTgXtEntry
    MAX-ACCESS  not-accessible
    STATUS      current
    DESCRIPTION
       "The L2TP Extended Tunnel configuration table
        contains more objects to configure L2TP Tunnel Groups.
        
        Entries in this table are automatically created and deleted by the
        system."
    ::= { tmnxL2tpTgCfgObjs 5 }

tmnxL2tpTgXtEntry   OBJECT-TYPE
        SYNTAX          TmnxL2tpTgXtEntry
        MAX-ACCESS      not-accessible
        STATUS          current
        DESCRIPTION
       "Each conceptual row represents information about 
        a Layer Two Tunneling Protocol Tunnel Group."
    AUGMENTS { tmnxL2tpTgCfgEntry }
    ::= { tmnxL2tpTgXtTable 1 }

TmnxL2tpTgXtEntry ::= 
    SEQUENCE {
        tmnxL2tpTgXtLastMgmtChange       TimeStamp,
        tmnxL2tpTgXtDfBitLac             TmnxAlwaysNeverOrDefault
    }
        
tmnxL2tpTgXtLastMgmtChange OBJECT-TYPE
    SYNTAX      TimeStamp
    MAX-ACCESS  read-only
    STATUS      current
    DESCRIPTION
        "The value of tmnxL2tpTgXtLastMgmtChange indicates the sysUpTime at
         the time of the most recent management-initiated change to this
         table row."
    ::= { tmnxL2tpTgXtEntry 1 }

tmnxL2tpTgXtDfBitLac OBJECT-TYPE
    SYNTAX      TmnxAlwaysNeverOrDefault
    MAX-ACCESS  read-create
    STATUS      current
    DESCRIPTION
       "The value of tmnxL2tpTgXtDfBitLac specifies 
        if this system applies Link Fragmentation and Interleaving to the
        traffic sent from the LNS to the LAC.
         
        If the value of this object is 'always', downstream traffic is
        fragmented and interleaved, meaning that (non-fragmented) realtime 
        traffic is interleaved with fragments of non-realtime traffic.
        
        If the value of this object is 'never', downstream traffic is only
        fragmented but not reordered according to priority.
        
        The value 'default' specifies that the actual value must be used
        of the object tmnxL2tpXtDfBitLac.
        
        The value of this object is only relevant for tunnels where this system
        performs the LAC role."
    DEFVAL { default }
    ::= { tmnxL2tpTgXtEntry 4 }

-- --------------------------------------------------------
--  tmnxL2tpTgStatTable (read-only)
-- --------------------------------------------------------

tmnxL2tpTgStatTable OBJECT-TYPE
    SYNTAX      SEQUENCE OF TmnxL2tpTgStatEntry
    MAX-ACCESS  not-accessible
    STATUS      current
    DESCRIPTION
        "The tmnxL2tpTgStatTable contains status and statistics information 
         about Layer Two Tunneling Protocol Tunnel Groups.
         
         The tmnxL2tpTgStatTable has an entry for each L2TP Tunnel Group."
    ::= { tmnxL2tpTgStatObjs 1 }

tmnxL2tpTgStatEntry OBJECT-TYPE
    SYNTAX      TmnxL2tpTgStatEntry
    MAX-ACCESS  not-accessible
    STATUS      current
    DESCRIPTION
        "Each row entry contains status and statistics about 
         an L2TP tunnel group.

         Rows are created or removed automatically by the system."
    INDEX { vRtrID,
            tmnxL2tpTgStatName }
    ::= { tmnxL2tpTgStatTable 1 }

TmnxL2tpTgStatEntry ::= 
    SEQUENCE {
        tmnxL2tpTgStatName               TmnxL2tpTunnelGroupName,
        tmnxL2tpTgStatState              TmnxL2tpTgOperState,
        tmnxL2tpTgStatCleared            TimeStamp,
        tmnxL2tpTgStatTotalTunnels       Counter32,
        tmnxL2tpTgStatFailedTunnels      Counter32,
        tmnxL2tpTgStatFailedTuAuth       Counter32,
        tmnxL2tpTgStatActiveTunnels      Gauge32,
        tmnxL2tpTgStatTunnels            Gauge32,
        tmnxL2tpTgStatTotalSessions      Counter32,
        tmnxL2tpTgStatFailedSessions     Counter32,
        tmnxL2tpTgStatActiveSessions     Gauge32,
        tmnxL2tpTgStatSessions           Gauge32,
        tmnxL2tpTgStatControlRxOctets    CounterBasedGauge64,
        tmnxL2tpTgStatControlRxOctetsLw  Gauge32,
        tmnxL2tpTgStatControlRxOctetsHw  Gauge32,
        tmnxL2tpTgStatControlRxPkts      Gauge32,
        tmnxL2tpTgStatControlTxOctets    CounterBasedGauge64,
        tmnxL2tpTgStatControlTxOctetsLw  Gauge32,
        tmnxL2tpTgStatControlTxOctetsHw  Gauge32,
        tmnxL2tpTgStatControlTxPkts      Gauge32,
        tmnxL2tpTgStatErrorTxPkts        Gauge32,
        tmnxL2tpTgStatErrorRxPkts        Gauge32,
        tmnxL2tpTgStatSessionLimit       Gauge32,
        tmnxL2tpTgStatSeAssignMethod     TmnxL2tpSessionAssignMethod
    }

tmnxL2tpTgStatName OBJECT-TYPE
    SYNTAX      TmnxL2tpTunnelGroupName
    MAX-ACCESS  not-accessible
    STATUS      current
    DESCRIPTION
       "The value of the object tmnxL2tpTgStatName indicates the string to
        identify this Layer Two Tunneling Protocol Tunnel Group."
    ::= { tmnxL2tpTgStatEntry 1 }

tmnxL2tpTgStatState   OBJECT-TYPE
    SYNTAX      TmnxL2tpTgOperState
    MAX-ACCESS  read-only
    STATUS      current
    DESCRIPTION
       "The value of tmnxL2tpTgStatState indicates the
        operational state of this Layer Two Tunneling Protocol Tunnel Group."
    ::= { tmnxL2tpTgStatEntry 2 }

tmnxL2tpTgStatCleared   OBJECT-TYPE
    SYNTAX      TimeStamp
    MAX-ACCESS  read-only
    STATUS      current
    DESCRIPTION
        "The value of the object tmnxL2tpTgStatCleared indicates
         the value of sysUpTime when the tunnel group statistics were cleared.
         
         The value zero indicates that the statistics have not been 
         cleared since the last re-initialization of the local network 
         management subsystem."
    ::= { tmnxL2tpTgStatEntry 3 }

tmnxL2tpTgStatTotalTunnels    OBJECT-TYPE
    SYNTAX      Counter32
    MAX-ACCESS  read-only
    STATUS      current
    DESCRIPTION
        "The value of tmnxL2tpTgStatTotalTunnels indicates
         the total number of tunnel set up attempts in this tunnel group
         since the last re-initialization of the local network 
         management subsystem, or the last time the system statistics were 
         cleared."
    ::= { tmnxL2tpTgStatEntry 4 }

tmnxL2tpTgStatFailedTunnels   OBJECT-TYPE
    SYNTAX      Counter32
    MAX-ACCESS  read-only
    STATUS      current
    DESCRIPTION
       "The value of tmnxL2tpTgStatFailedTunnels indicates
        the number of tunnels  in this tunnel group that failed to reach the 
        established state since the last re-initialization of the local network 
        management subsystem, or the last time the system statistics were 
        cleared."
    ::= { tmnxL2tpTgStatEntry 5 }

tmnxL2tpTgStatFailedTuAuth    OBJECT-TYPE
    SYNTAX      Counter32
    MAX-ACCESS  read-only
    STATUS      current
    DESCRIPTION
       "The value of tmnxL2tpTgStatFailedTuAuth indicates
        the number of tunnels  in this tunnel group that failed authentication
        since the last re-initialization of the local network 
        management subsystem, or the last time the system statistics were 
        cleared."
    ::= { tmnxL2tpTgStatEntry 6 }

tmnxL2tpTgStatActiveTunnels   OBJECT-TYPE
    SYNTAX      Gauge32
    MAX-ACCESS  read-only
    STATUS      current
    DESCRIPTION
        "The value of tmnxL2tpTgStatActiveTunnels indicates 
         the number of tunnels currently established in this tunnel group."
    ::= { tmnxL2tpTgStatEntry 7 }

tmnxL2tpTgStatTunnels   OBJECT-TYPE
    SYNTAX      Gauge32
    MAX-ACCESS  read-only
    STATUS      current
    DESCRIPTION
        "The value of tmnxL2tpTgStatTunnels indicates 
         the actual number of tunnels in this tunnel group."
    ::= { tmnxL2tpTgStatEntry 8 }

tmnxL2tpTgStatTotalSessions  OBJECT-TYPE
    SYNTAX      Counter32
    MAX-ACCESS  read-only
    STATUS      current
    DESCRIPTION
       "The value of tmnxL2tpTgStatTotalSessions indicates
        the number of session creation attempts  in this tunnel group
        since the last re-initialization of the local network 
        management subsystem, or the last time the system statistics were 
        cleared."
    ::= { tmnxL2tpTgStatEntry 9 }

tmnxL2tpTgStatFailedSessions  OBJECT-TYPE
    SYNTAX      Counter32
    MAX-ACCESS  read-only
    STATUS      current
    DESCRIPTION
       "The value of tmnxL2tpTgStatFailedSessions indicates
        the number of sessions  in this tunnel group that failed to reach the 
        established state since the last re-initialization of the local network 
        management subsystem, or the last time the system statistics were 
        cleared."
    ::= { tmnxL2tpTgStatEntry 10 }

tmnxL2tpTgStatActiveSessions  OBJECT-TYPE
    SYNTAX      Gauge32
    MAX-ACCESS  read-only
    STATUS      current
    DESCRIPTION
        "The value of tmnxL2tpTgStatActiveSessions indicates 
         the number of sessions currently established  in this tunnel group."
    ::= { tmnxL2tpTgStatEntry 11 }

tmnxL2tpTgStatSessions  OBJECT-TYPE
    SYNTAX      Gauge32
    MAX-ACCESS  read-only
    STATUS      current
    DESCRIPTION
        "The value of tmnxL2tpTgStatSessions indicates 
         the actual number of sessions in this tunnel group."
    ::= { tmnxL2tpTgStatEntry 12 }

tmnxL2tpTgStatControlRxOctets OBJECT-TYPE
    SYNTAX      CounterBasedGauge64
    MAX-ACCESS  read-only
    STATUS      current
    DESCRIPTION
        "The value of tmnxL2tpTgStatControlRxOctets indicates
        the number of control channel octets received by the current tunnels
        in this tunnel group."
    ::= { tmnxL2tpTgStatEntry 13 }

tmnxL2tpTgStatControlRxOctetsLw OBJECT-TYPE
    SYNTAX      Gauge32
    MAX-ACCESS  read-only
    STATUS      current
    DESCRIPTION
        "The value of tmnxL2tpTgStatControlRxOctetsLw indicates
        the lower 32-bits word of the value of tmnxL2tpTgStatControlRxOctets."
    ::= { tmnxL2tpTgStatEntry 14 }

tmnxL2tpTgStatControlRxOctetsHw OBJECT-TYPE
    SYNTAX      Gauge32
    MAX-ACCESS  read-only
    STATUS      current
    DESCRIPTION
        "The value of tmnxL2tpTgStatControlRxOctetsHw indicates
        the higher 32-bits word of the value of tmnxL2tpTgStatControlRxOctets."
    ::= { tmnxL2tpTgStatEntry 15 }

tmnxL2tpTgStatControlRxPkts OBJECT-TYPE
    SYNTAX      Gauge32
    MAX-ACCESS  read-only
    STATUS      current
    DESCRIPTION
        "The value of tmnxL2tpTgStatControlRxPkts indicates
        the accumulated number of control packets  received by
        the current tunnels in this tunnel group."
    ::= { tmnxL2tpTgStatEntry 16 }

tmnxL2tpTgStatControlTxOctets OBJECT-TYPE
    SYNTAX      CounterBasedGauge64
    MAX-ACCESS  read-only
    STATUS      current
    DESCRIPTION
        "The value of tmnxL2tpTgStatControlTxOctets indicates
        the accumulated number of control channel octets that were transmitted  
        to the current tunnel endpoints in this tunnel group."
    ::= { tmnxL2tpTgStatEntry 17 }

tmnxL2tpTgStatControlTxOctetsLw OBJECT-TYPE
    SYNTAX      Gauge32
    MAX-ACCESS  read-only
    STATUS      current
    DESCRIPTION
        "The value of tmnxL2tpTgStatControlTxOctetsLw indicates
        the lower 32-bits word of the value of tmnxL2tpTgStatControlTxOctets."
    ::= { tmnxL2tpTgStatEntry 18 }

tmnxL2tpTgStatControlTxOctetsHw OBJECT-TYPE
    SYNTAX      Gauge32
    MAX-ACCESS  read-only
    STATUS      current
    DESCRIPTION
        "The value of tmnxL2tpTgStatControlTxOctetsHw indicates
        the higher 32-bits word of the value of tmnxL2tpTgStatControlTxOctets."
    ::= { tmnxL2tpTgStatEntry 19 }

tmnxL2tpTgStatControlTxPkts OBJECT-TYPE
    SYNTAX      Gauge32
    MAX-ACCESS  read-only
    STATUS      current
    DESCRIPTION
        "The value of tmnxL2tpTgStatControlTxPkts indicates
        the accumulated number of control packets that were transmitted to 
        the current tunnel endpoints in this tunnel group."
    ::= { tmnxL2tpTgStatEntry 20 }

tmnxL2tpTgStatErrorTxPkts OBJECT-TYPE
    SYNTAX      Gauge32
    MAX-ACCESS  read-only
    STATUS      current
    DESCRIPTION
        "The value of tmnxL2tpTgStatErrorTxPkts indicates
        the accumulated number of packet transmission errors on 
        the current tunnels in this tunnel group."
    ::= { tmnxL2tpTgStatEntry 21 }

tmnxL2tpTgStatErrorRxPkts OBJECT-TYPE
    SYNTAX      Gauge32
    MAX-ACCESS  read-only
    STATUS      current
    DESCRIPTION
        "The value of tmnxL2tpTgStatErrorRxPkts indicates
        the accumulated number of errored packets that were received 
        on the current tunnels in this tunnel group."
    ::= { tmnxL2tpTgStatEntry 22 }

tmnxL2tpTgStatSessionLimit   OBJECT-TYPE
    SYNTAX      Gauge32
    MAX-ACCESS  read-only
    STATUS      current
    DESCRIPTION
        "The value of tmnxL2tpTgStatSessionLimit indicates 
         the actual session limit of this tunnel group."
    ::= { tmnxL2tpTgStatEntry 23 }

tmnxL2tpTgStatSeAssignMethod OBJECT-TYPE
    SYNTAX      TmnxL2tpSessionAssignMethod
    MAX-ACCESS  read-only
    STATUS      current
    DESCRIPTION
       "The value of the object tmnxL2tpTgStatSeAssignMethod indicates
        the latest actual method used for the authentication of 
        the tunnels in this Layer Two Tunneling Protocol Tunnel Group.
        
        Note that the next tunnel that will be set up in this L2TP tunnel group
        may or may not use the same method, since the configuration of the
        RADIUS server may have changed in the meantime."
    ::= { tmnxL2tpTgStatEntry 24 }  

-- --------------------------------------------------------
--  tmnxL2tpTgTuTable (read-only)
-- --------------------------------------------------------

tmnxL2tpTgTuTable OBJECT-TYPE
    SYNTAX      SEQUENCE OF TmnxL2tpTgTuEntry
    MAX-ACCESS  not-accessible
    STATUS      current
    DESCRIPTION
        "The tmnxL2tpTgTuTable contains the set of active tunnels for each
         L2TP Tunnel Group."
    ::= { tmnxL2tpTgStatObjs 2 }

tmnxL2tpTgTuEntry OBJECT-TYPE
    SYNTAX      TmnxL2tpTgTuEntry
    MAX-ACCESS  not-accessible
    STATUS      current
    DESCRIPTION
        "Each row entry contains a tunnel identifier of an L2TP tunnel group.

         Rows are created or removed automatically by the system."
    INDEX { vRtrID,
            tmnxL2tpTgStatName,
            tmnxL2tpTgTuId }
    ::= { tmnxL2tpTgTuTable 1 }

TmnxL2tpTgTuEntry ::= 
    SEQUENCE {
        tmnxL2tpTgTuId                   TmnxL2tpConnectionId
    }

tmnxL2tpTgTuId OBJECT-TYPE
    SYNTAX      TmnxL2tpConnectionId
    MAX-ACCESS  read-only
    STATUS      current
    DESCRIPTION
       "The value of the object tmnxL2tpTgTuId indicates the local  
        identifier of a Layer Two Tunneling Protocol Tunnel.
        
        In L2TP version 2, it is the 16-bit tunnel ID.
        
        In L2TP version 3, it is the 32-bit control connection ID."
    ::= { tmnxL2tpTgTuEntry 1 }

--
--      The L2TP Tunnel Group Operations Drain Table
--
--  Augmentation of the tmnxL2tpTgStatTable
--  Use of AUGMENTS clause implies a one-to-one dependent relationship
--  between the base table, tmnxL2tpTgStatTable, and the augmenting table,
--  tmnxL2tpTgDrainTable. This in effect extends the tmnxL2tpTgStatTable
--  with additional columns. Creation (or deletion) of a row in the
--  tmnxL2tpTgStatTable results in the same fate for the row in the
--  tmnxL2tpTgDrainTable.


tmnxL2tpTgDrainTable   OBJECT-TYPE
    SYNTAX      SEQUENCE OF TmnxL2tpTgDrainEntry
    MAX-ACCESS  not-accessible
    STATUS      current
    DESCRIPTION
       "The tmnxL2tpTgDrainTable has an entry for each 
        active Layer Two Tunneling Protocol Tunnel Group."
    ::= { tmnxL2tpTgOpObjs 1 }

tmnxL2tpTgDrainEntry   OBJECT-TYPE
        SYNTAX          TmnxL2tpTgDrainEntry
        MAX-ACCESS      not-accessible
        STATUS          current
        DESCRIPTION
       "Each conceptual row presents an operations interface to drain
        a Layer Two Tunneling Protocol Tunnel Group.

        After a successful drain operation, the value of the object
        tmnxL2tpTgStatState of this tunnel group is equal to 'drain', and 
        the value of the object tmnxL2tpTuStatusState is equal to 'draining' for
        all the tunnels of this L2TP tunnel group; none of these tunnels accept
        or establish new connections, while existing connections are timing out.

        Entries in this table are created and destroyed by the system."
    AUGMENTS { tmnxL2tpTgStatEntry }
        ::= { tmnxL2tpTgDrainTable 1 }

TmnxL2tpTgDrainEntry ::= 
    SEQUENCE {
        tmnxL2tpTgDrain                  TmnxL2tpActionTypeDrain
    }

tmnxL2tpTgDrain OBJECT-TYPE
    SYNTAX      TmnxL2tpActionTypeDrain
    MAX-ACCESS  read-write
    STATUS      current
    DESCRIPTION
        "Setting this object to 'drain (0)' triggers 
         an attempt to drain this L2TP tunnel group.

         Setting it to 'stopDrain (1)' stops the draining.
         
         Reading this object returns the value 'notApplicable'."
    DEFVAL { notApplicable }
    ::= { tmnxL2tpTgDrainEntry 1 }

-- ----------------------------------------------------------------------------
--      The "L2TP Tunnel" Group
-- ----------------------------------------------------------------------------

tmnxL2tpTuCfgObjs            OBJECT IDENTIFIER   ::= { tmnxL2tpTunnelObjs 1 }
tmnxL2tpTuStatObjs           OBJECT IDENTIFIER   ::= { tmnxL2tpTunnelObjs 2 }
tmnxL2tpTuOpObjs             OBJECT IDENTIFIER   ::= { tmnxL2tpTunnelObjs 3 }

--
--      The L2TP Tunnel Configuration Table
--

tmnxL2tpTuCfgTableLastCh OBJECT-TYPE
    SYNTAX      TimeStamp
    MAX-ACCESS  read-only
    STATUS      current
    DESCRIPTION
        "The value of the object tmnxL2tpTuCfgTableLastCh indicates
         the value of sysUpTime at the time of the last modification of
         an entry in the tmnxL2tpTuCfgTable."
    ::= { tmnxL2tpObjs 12 }

tmnxL2tpTuCfgTable   OBJECT-TYPE
    SYNTAX      SEQUENCE OF TmnxL2tpTuCfgEntry
    MAX-ACCESS  not-accessible
    STATUS      current
    DESCRIPTION
       "The L2TP Tunnel configuration table
        contains objects to configure L2TP Tunnels."
    ::= { tmnxL2tpTuCfgObjs 2 }

tmnxL2tpTuCfgEntry   OBJECT-TYPE
    SYNTAX      TmnxL2tpTuCfgEntry
    MAX-ACCESS  not-accessible
    STATUS      current
    DESCRIPTION
       "Each conceptual row represents a Layer Two Tunneling Protocol
        Tunnel.

        Entries in this table can be created or deleted via SNMP operations."
    INDEX { vRtrID,
            tmnxL2tpTgCfgName, 
            tmnxL2tpTuCfgName }
    ::= { tmnxL2tpTuCfgTable 1 }

TmnxL2tpTuCfgEntry ::= 
    SEQUENCE {
        tmnxL2tpTuCfgName                TNamedItem,
        tmnxL2tpTuCfgRowStatus           RowStatus,
        tmnxL2tpTuCfgLastMgmtChange      TimeStamp,
        tmnxL2tpTuCfgDescription         TItemDescription,
        tmnxL2tpTuCfgAdminState          TmnxAdminState,
        tmnxL2tpTuCfgPreference          TmnxL2tpTunnelPreference,
        tmnxL2tpTuCfgPeerAddrType        InetAddressType,
        tmnxL2tpTuCfgPeerAddr            InetAddress,
        tmnxL2tpTuCfgAddrType            InetAddressType,
        tmnxL2tpTuCfgAddr                InetAddress,
        tmnxL2tpTuCfgLocalName           TmnxL2tpHostNameOrEmpty,
        tmnxL2tpTuCfgRemoteName          TmnxL2tpHostNameOrEmpty,
        tmnxL2tpTuCfgSecret              TmnxL2tpAuthSecret,
        tmnxL2tpTuCfgHelloInterval       TmnxL2tpTunnelHelloInterval,
        tmnxL2tpTuCfgIdleTO              TmnxL2tpTunnelIdleTO,
        tmnxL2tpTuCfgDestructTO          TmnxL2tpTunnelDestructTO,
        tmnxL2tpTuCfgMaxRetxEstab        TmnxL2tpTunnelMaxRetx,
        tmnxL2tpTuCfgMaxRetxNotEstab     TmnxL2tpTunnelMaxRetx,
        tmnxL2tpTuCfgSessionLimit        TmnxL2tpTunnelSessionLimit,
        tmnxL2tpTuCfgAvpHiding           TmnxL2tpAvpHidingMode,
        tmnxL2tpTuCfgAutoEstab           TruthValue,
        tmnxL2tpTuCfgDoChallenge         TmnxL2tpDoChallenge,
        tmnxL2tpTuCfgReceiveWindowSize   TmnxL2tpReceiveWindowSize,
        tmnxL2tpTuCfgIsaGrpId            TmnxL2tpIsaGrpIdOrZero,
        tmnxL2tpTuCfgLoadBalanceMethod   TmnxL2tpIsaMdaLoadBalanceMethod,
        tmnxL2tpTuCfgAccountingPolicy    TNamedItemOrEmpty
    }
        
tmnxL2tpTuCfgName OBJECT-TYPE
    SYNTAX      TNamedItem
    MAX-ACCESS  not-accessible
    STATUS      current
    DESCRIPTION
       "The value of the object tmnxL2tpTuCfgName specifies the name of this 
        Layer Two Tunneling Protocol Tunnel."
    ::= { tmnxL2tpTuCfgEntry 1 }

tmnxL2tpTuCfgRowStatus OBJECT-TYPE
    SYNTAX      RowStatus
    MAX-ACCESS  read-create
    STATUS      current
    DESCRIPTION
       "The value of tmnxL2tpTuCfgRowStatus specifies the row status of
        this row."
    ::= { tmnxL2tpTuCfgEntry 2 }

tmnxL2tpTuCfgLastMgmtChange OBJECT-TYPE
    SYNTAX      TimeStamp
    MAX-ACCESS  read-only
    STATUS      current
    DESCRIPTION
        "The value of tmnxL2tpTuCfgLastMgmtChange indicates the sysUpTime at
         the time of the most recent management-initiated change to this
         table row."
    ::= { tmnxL2tpTuCfgEntry 3 }

tmnxL2tpTuCfgDescription OBJECT-TYPE
    SYNTAX      TItemDescription
    MAX-ACCESS  read-create
    STATUS      current
    DESCRIPTION
       "The value of tmnxL2tpTuCfgDescription specifies the
        description of this Layer Two Tunneling Protocol Tunnel."
    DEFVAL { "" }
    ::= { tmnxL2tpTuCfgEntry 4 }

tmnxL2tpTuCfgAdminState OBJECT-TYPE
    SYNTAX      TmnxAdminState
    MAX-ACCESS  read-create
    STATUS      current
    DESCRIPTION
       "The value of tmnxL2tpTuCfgAdminState specifies the
        administrative state of this Layer Two Tunneling Protocol Tunnel."
    DEFVAL { outOfService }
    ::= { tmnxL2tpTuCfgEntry 5 }

tmnxL2tpTuCfgPreference OBJECT-TYPE
    SYNTAX      TmnxL2tpTunnelPreference
    MAX-ACCESS  read-create
    STATUS      current
    DESCRIPTION
       "The value of tmnxL2tpTuCfgPreference specifies
        the preference of this Layer Two Tunneling Protocol Tunnel.
        
        The value '0' corresponds to the highest preference."
    DEFVAL    { 50 }
        ::= { tmnxL2tpTuCfgEntry 6 }

tmnxL2tpTuCfgPeerAddrType OBJECT-TYPE
    SYNTAX      InetAddressType
    MAX-ACCESS  read-create
    STATUS      current
    DESCRIPTION 
       "The value of tmnxL2tpTuCfgPeerAddrType specifies the
        address type of tmnxL2tpTuCfgPeerAddr."
    DEFVAL { unknown }
    ::= { tmnxL2tpTuCfgEntry 7 }

tmnxL2tpTuCfgPeerAddr OBJECT-TYPE
    SYNTAX      InetAddress (SIZE(0|4|16))
    MAX-ACCESS  read-create
    STATUS      current
    DESCRIPTION 
       "The value of tmnxL2tpTuCfgPeerAddr specifies the IP
        address of the peer."
    DEFVAL { ''H }  
    ::= { tmnxL2tpTuCfgEntry 8 }

tmnxL2tpTuCfgAddrType OBJECT-TYPE
    SYNTAX      InetAddressType
    MAX-ACCESS  read-create
    STATUS      current
    DESCRIPTION 
       "The value of tmnxL2tpTuCfgAddrType specifies the
        address type of tmnxL2tpTuCfgAddr.
        
        The value 'unknown' specifies that the value must be set to the actual
        value of the object tmnxL2tpTgCfgAddrType."
    DEFVAL { unknown }
    ::= { tmnxL2tpTuCfgEntry 9 }

tmnxL2tpTuCfgAddr OBJECT-TYPE
    SYNTAX      InetAddress (SIZE(0|4|16))
    MAX-ACCESS  read-create
    STATUS      current
    DESCRIPTION 
       "The value of tmnxL2tpTuCfgAddr specifies the local IP
        address of this Layer Two Tunneling Protocol Tunnel.
        
        The value ''H specifies that the value must be set to the actual
        value of the object tmnxL2tpTgCfgAddr."
    DEFVAL { ''H }  
    ::= { tmnxL2tpTuCfgEntry 10 }

tmnxL2tpTuCfgLocalName OBJECT-TYPE
    SYNTAX      TmnxL2tpHostNameOrEmpty
    MAX-ACCESS  read-create
    STATUS      current
    DESCRIPTION
       "The value of the object tmnxL2tpTuCfgLocalName specifies
        the host name used by this system 
        during the authentication phase of tunnel establishment.

        This object is related to the RADIUS attribute Tunnel-Client-Auth-ID.

        It can be used to distinguish tunnels.
        
        An empty string specifies that the value of the object 
        tmnxL2tpTgCfgLocalName is used."
    REFERENCE
       "RFC 2868 RADIUS Attributes for Tunnel Protocol Support
        section 3.9."
    DEFVAL { ''H }
    ::= { tmnxL2tpTuCfgEntry 11 }

tmnxL2tpTuCfgRemoteName OBJECT-TYPE
    SYNTAX      TmnxL2tpHostNameOrEmpty
    MAX-ACCESS  read-create
    STATUS      current
    DESCRIPTION
       "The value of the object tmnxL2tpTuCfgRemoteName specifies
        a string to be compared to the host name used by the tunnel peer 
        during the authentication phase of tunnel establishment.

        This object is related to the RADIUS attribute Tunnel-Server-Auth-ID.

        It can be used to distinguish tunnels."
    REFERENCE
       "RFC 2868 RADIUS Attributes for Tunnel Protocol Support
        section 3.10."
    DEFVAL { ''H }
    ::= { tmnxL2tpTuCfgEntry 12 }

tmnxL2tpTuCfgSecret OBJECT-TYPE
    SYNTAX      TmnxL2tpAuthSecret
    MAX-ACCESS  read-create
    STATUS      current
    DESCRIPTION
       "The value of the object tmnxL2tpTuCfgSecret specifies
        the password to be used for the authentication of this
        Layer Two Tunneling Protocol Tunnel.

        This value overrules the value of the object tmnxL2tpTgCfgSecret of the 
        tunnel group this tunnel belongs to.

        This object will always return an empty string on a read."
    DEFVAL { ''H }
    ::= { tmnxL2tpTuCfgEntry 13 }

tmnxL2tpTuCfgHelloInterval OBJECT-TYPE
    SYNTAX      TmnxL2tpTunnelHelloInterval
    UNITS       "seconds"
    MAX-ACCESS  read-create
    STATUS      current
    DESCRIPTION
       "The value of tmnxL2tpTuCfgHelloInterval specifies
        the time interval between two consecutive tunnel Hello messages.

        A value of '-1' specifies that the keepalive function is disabled.
        
        A value of '-2' specifies that the value must be set to the actual
        value of the object tmnxL2tpTgCfgHelloInterval."
    DEFVAL    { -2 }
        ::= { tmnxL2tpTuCfgEntry 14 }

tmnxL2tpTuCfgIdleTO OBJECT-TYPE
    SYNTAX      TmnxL2tpTunnelIdleTO
    UNITS       "seconds"
    MAX-ACCESS  read-create
    STATUS      current
    DESCRIPTION
       "The value of tmnxL2tpTuCfgIdleTO specifies
        the period of time that an established tunnel with no active sessions 
        will persist before being disconnected.

        A value of -1 leaves the tunnel up indefinitely.
        
        A value of '-2' specifies that the value must be set to the actual
        value of the object tmnxL2tpTgCfgIdleTO."
    DEFVAL    { -2 }
        ::= { tmnxL2tpTuCfgEntry 15 }

tmnxL2tpTuCfgDestructTO OBJECT-TYPE
    SYNTAX      TmnxL2tpTunnelDestructTO
    UNITS       "seconds"
    MAX-ACCESS  read-create
    STATUS      current
    DESCRIPTION
       "The value of tmnxL2tpTuCfgDestructTO specifies
        the period of time that data of a disconnected tunnel
        will persist before being removed.

        A value of '-2' specifies that the value must be set to the actual
        value of the object tmnxL2tpTgCfgDestructTO."
    DEFVAL    { -2 }
        ::= { tmnxL2tpTuCfgEntry 16 }

tmnxL2tpTuCfgMaxRetxEstab OBJECT-TYPE
    SYNTAX      TmnxL2tpTunnelMaxRetx
    MAX-ACCESS  read-create
    STATUS      current
    DESCRIPTION
       "The value of tmnxL2tpTuCfgMaxRetxEstab specifies
        the number of retries allowed for this
        Layer Two Tunneling Protocol Tunnel while it is established,
        before its control connection goes down."
    DEFVAL    { -2 }
        ::= { tmnxL2tpTuCfgEntry 17 }

tmnxL2tpTuCfgMaxRetxNotEstab OBJECT-TYPE
    SYNTAX      TmnxL2tpTunnelMaxRetx
    MAX-ACCESS  read-create
    STATUS      current
    DESCRIPTION
       "The value of tmnxL2tpTuCfgMaxRetxNotEstab specifies
        the number of retries allowed for this
        Layer Two Tunneling Protocol Tunnel while it is unestablished,
        before its control connection goes down."
    DEFVAL    { -2 }
        ::= { tmnxL2tpTuCfgEntry 18 }

tmnxL2tpTuCfgSessionLimit OBJECT-TYPE
    SYNTAX      TmnxL2tpTunnelSessionLimit
    MAX-ACCESS  read-create
    STATUS      current
    DESCRIPTION
       "The value of tmnxL2tpTuCfgSessionLimit specifies
        the maximum number of sessions allowed in this
        Layer Two Tunneling Protocol Tunnel.

        A value of '-2' specifies that the value must be set to the actual
        value of the object tmnxL2tpTunnelSessionLimit."
    DEFVAL    { -2 }
        ::= { tmnxL2tpTuCfgEntry 19 }

tmnxL2tpTuCfgAvpHiding OBJECT-TYPE
    SYNTAX      TmnxL2tpAvpHidingMode
    MAX-ACCESS  read-create
    STATUS      current
    DESCRIPTION
       "The value of tmnxL2tpTuCfgAvpHiding specifies
        when the H bit in the header of each Attribute Value Pair (AVP) 
        is set for the L2TP control messages related to this 
        Layer Two Tunneling Protocol Tunnel.
        
        The value 'default' specifies that the value must be set to the actual
        value of the object tmnxL2tpTgCfgAvpHiding of the tunnel group this
        tunnel belongs to."
    REFERENCE
       "RFC 2661 Layer Two Tunneling Protocol 'L2TP', 
        section 4.3 Hiding of AVP Attribute Values."
    DEFVAL    { default }
        ::= { tmnxL2tpTuCfgEntry 20 }

tmnxL2tpTuCfgAutoEstab OBJECT-TYPE
    SYNTAX      TruthValue
    MAX-ACCESS  read-create
    STATUS      current
    DESCRIPTION
       "The value of tmnxL2tpTuCfgAutoEstab specifies
        if this Layer Two Tunneling Protocol Tunnel is to be set up
        automatically by the system."
    DEFVAL    { false }
        ::= { tmnxL2tpTuCfgEntry 21 }

tmnxL2tpTuCfgDoChallenge OBJECT-TYPE
    SYNTAX      TmnxL2tpDoChallenge
    MAX-ACCESS  read-create
    STATUS      current
    DESCRIPTION
       "The value of tmnxL2tpTuCfgDoChallenge specifies
        when challenge-response is to be used for the authentication of 
        this Layer Two Tunneling Protocol Tunnel.
        
        The value 'default' specifies that the value must be set to the actual
        value of the object tmnxL2tpTgCfgDoChallenge of the tunnel group this
        tunnel belongs to."
    DEFVAL    { default }
        ::= { tmnxL2tpTuCfgEntry 22 }

tmnxL2tpTuCfgReceiveWindowSize OBJECT-TYPE
    SYNTAX      TmnxL2tpReceiveWindowSize
    MAX-ACCESS  read-create
    STATUS      current
    DESCRIPTION
       "The value of tmnxL2tpTuCfgReceiveWindowSize specifies
        the Receive Window Size for this Layer Two Tunneling Protocol Tunnel.
        
        The value zero specifies that the value must be set to the actual
        value of the object tmnxL2tpTgCfgReceiveWindowSize."
    DEFVAL    { 0 }
        ::= { tmnxL2tpTuCfgEntry 23 }

tmnxL2tpTuCfgIsaGrpId OBJECT-TYPE
    SYNTAX      TmnxL2tpIsaGrpIdOrZero
    MAX-ACCESS  read-create
    STATUS      current
    DESCRIPTION
       "The value of tmnxL2tpTuCfgDoChallenge specifies
        the L2TP Integrated Service Adaptor group of 
        this Layer Two Tunneling Protocol Tunnel.
        
        The value zero specifies that the value must be set to the actual
        value of the object tmnxL2tpTgCfgIsaGrpId of the tunnel group this
        tunnel belongs to."
    DEFVAL    { 0 }
        ::= { tmnxL2tpTuCfgEntry 24 }

tmnxL2tpTuCfgLoadBalanceMethod OBJECT-TYPE
    SYNTAX      TmnxL2tpIsaMdaLoadBalanceMethod
    MAX-ACCESS  read-create
    STATUS      current
    DESCRIPTION
        "The value of the object tmnxL2tpTuCfgLoadBalanceMethod specifies
         the method to be used for load-balancing sessions across ISA MDA
         in this Layer Two Tunneling Protocol Tunnel.
        
        The value 'default' specifies that the value must be set to the actual
        value of the object tmnxL2tpTgCfgLoadBalanceMethod of the tunnel group 
        this tunnel belongs to."
    DEFVAL    { default }
        ::= { tmnxL2tpTuCfgEntry 30 }

tmnxL2tpTuCfgAccountingPolicy OBJECT-TYPE
    SYNTAX      TNamedItemOrEmpty
    MAX-ACCESS  read-create
    STATUS      current
    DESCRIPTION
        "The value of the object tmnxL2tpTuCfgAccountingPolicy specifies
         the RADIUS accounting policy to be used
         in this Layer Two Tunneling Protocol Tunnel.
         
         It refers to a conceptual row in the tmnxL2tpApTable.
         
         An empty string specifies that the value of 
         tmnxL2tpTgCfgAccountingPolicy must be used"
    DEFVAL    { "" }
        ::= { tmnxL2tpTuCfgEntry 31 }

--
--      The L2TP LNS Tunnel PPP Configuration Table
--
--  Augments the tmnxL2tpTuCfgTable.
--
--  The use of the AUGMENTS clause implies a one-to-one dependent relationship
--  between the base table, tmnxL2tpTuCfgTable, and the augmenting table,
--  tmnxL2tpLnsTuPppTable. This in effect extends the tmnxL2tpTuCfgTable
--  with additional columns. Creation (or deletion) of a row in the
--  tmnxL2tpTuCfgTable results in the same fate for the row in the
--  tmnxL2tpLnsTuPppTable.
--  

tmnxL2tpLnsTuPppTableLastCh OBJECT-TYPE
    SYNTAX      TimeStamp
    MAX-ACCESS  read-only
    STATUS      current
    DESCRIPTION
        "The value of the object tmnxL2tpLnsTuPppTableLastCh indicates
         the value of sysUpTime at the time of the last modification of
         an entry in the tmnxL2tpLnsTuPppTable."
    ::= { tmnxL2tpObjs 19 }

tmnxL2tpLnsTuPppTable   OBJECT-TYPE
    SYNTAX      SEQUENCE OF TmnxL2tpLnsTuPppEntry
    MAX-ACCESS  not-accessible
    STATUS      current
    DESCRIPTION
       "The L2TP Tunnel configuration table
        contains objects to configure PPP (Point to Point Protocol) 
        on L2TP LNS Tunnels.
        
        Entries in this table are automatically created and deleted by the
        system."
    ::= { tmnxL2tpTuCfgObjs 3 }

tmnxL2tpLnsTuPppEntry   OBJECT-TYPE
        SYNTAX          TmnxL2tpLnsTuPppEntry
        MAX-ACCESS      not-accessible
        STATUS          current
        DESCRIPTION
       "Each conceptual row represents PPP information about 
        a Layer Two Tunneling Protocol LNS Tunnel configuration."
    AUGMENTS { tmnxL2tpTuCfgEntry }
    ::= { tmnxL2tpLnsTuPppTable 1 }

TmnxL2tpLnsTuPppEntry ::= 
    SEQUENCE {
        tmnxL2tpLnsTuPppLastMgmtChange   TimeStamp,
        tmnxL2tpLnsTuPppAuthPlcy         TNamedItemOrEmpty,
        tmnxL2tpLnsTuPppAuthProtocol     TmnxL2tpPppAuthentication,
        tmnxL2tpLnsTuPppUserDb           TNamedItemOrEmpty,
        tmnxL2tpLnsTuPppDefaultService   TmnxServId,
        tmnxL2tpLnsTuPppDefaultGroupIf   TNamedItemOrEmpty,
        tmnxL2tpLnsTuPppProxyLcp         TmnxAlwaysNeverOrDefault,
        tmnxL2tpLnsTuPppProxyAuth        TmnxAlwaysNeverOrDefault,
        tmnxL2tpLnsTuPppMtu              TmnxL2tpPppMtu,
        tmnxL2tpLnsTuPppLcpKaInterval    TmnxL2tpLcpKaInterval,
        tmnxL2tpLnsTuPppLcpKaHoldUp      TmnxL2tpLcpKaHoldUpMplier,
        tmnxL2tpLnsTuPppIpcpSubnetNeg    TmnxAlwaysNeverOrDefault,
        tmnxL2tpLnsTuPppLcpIgnoreMagic   TmnxAlwaysNeverOrDefault,
        tmnxL2tpLnsTuPppMinChapChall     Unsigned32,
        tmnxL2tpLnsTuPppMaxChapChall     Unsigned32
    }
        
tmnxL2tpLnsTuPppLastMgmtChange OBJECT-TYPE
    SYNTAX      TimeStamp
    MAX-ACCESS  read-only
    STATUS      current
    DESCRIPTION
        "The value of tmnxL2tpLnsTuPppLastMgmtChange indicates the sysUpTime at
         the time of the most recent management-initiated change to this
         table row."
    ::= { tmnxL2tpLnsTuPppEntry 1 }

tmnxL2tpLnsTuPppAuthPlcy OBJECT-TYPE
    SYNTAX      TNamedItemOrEmpty
    MAX-ACCESS  read-create
    STATUS      current
    DESCRIPTION
       "The value of the object tmnxL2tpLnsTuPppAuthPlcy specifies
        the authentication policy used by this system during the authentication 
        phase of session establishment.

        An empty string specifies that the actual value must be used
        of the object tmnxL2tpLnsTgPppAuthPlcy of the tunnel group
        this tunnel configuration belongs to."
    DEFVAL { ''H }
    ::= { tmnxL2tpLnsTuPppEntry 2 }

tmnxL2tpLnsTuPppAuthProtocol OBJECT-TYPE
    SYNTAX      TmnxL2tpPppAuthentication
    MAX-ACCESS  read-create
    STATUS      current
    DESCRIPTION
       "The value of tmnxL2tpLnsTuPppAuthProtocol specifies
        what PPP authentication protocol(s) will be negotiated during the LCP 
        phase for the sessions of this tunnel.
        
        The value zero specifies that the actual value must be used
        of the object tmnxL2tpLnsTgPppAuthProtocol."
    DEFVAL { default }
    ::= { tmnxL2tpLnsTuPppEntry 3 }

tmnxL2tpLnsTuPppUserDb OBJECT-TYPE
    SYNTAX      TNamedItemOrEmpty
    MAX-ACCESS  read-create
    STATUS      current
    DESCRIPTION
       "The value of the object tmnxL2tpLnsTuPppUserDb specifies
        the local user database to use for PADI or PPP PAP/CHAP based 
        authentication during the authentication phase of session establishment.

        An empty string specifies that the actual value must be used
        of the object tmnxL2tpLnsTgPppUserDb of the tunnel group
        this tunnel configuration belongs to."
    DEFVAL { ''H }
    ::= { tmnxL2tpLnsTuPppEntry 4 }

tmnxL2tpLnsTuPppDefaultService OBJECT-TYPE
    SYNTAX      TmnxServId
    MAX-ACCESS  read-create
    STATUS      current
    DESCRIPTION
       "The value of tmnxL2tpLnsTuPppDefaultService specifies the
        service ID of the service where the PPP sessions are established
        when the authentication server does not specify the service ID.
        
        The value zero specifies that that the actual value must be used 
        of the object tmnxL2tpLnsTgPppDefaultService.
        
        If the value of tmnxL2tpLnsTuPppDefaultService is equal to zero, the
        value of tmnxL2tpLnsTuPppDefaultGroupIf must also be equal to zero."
    DEFVAL { 0 }
    ::= { tmnxL2tpLnsTuPppEntry 5 }

tmnxL2tpLnsTuPppDefaultGroupIf OBJECT-TYPE
    SYNTAX      TNamedItemOrEmpty
    MAX-ACCESS  read-create
    STATUS      current
    DESCRIPTION
       "The value of tmnxL2tpLnsTuPppDefaultGroupIf specifies the
        group interface where the PPP sessions are established
        when the authentication server does not specify the group interface.
        
        The empty string specifies that the actual value must be used
        of the object tmnxL2tpLnsTgPppDefaultGroupIf.
        
        If the value of tmnxL2tpLnsTuPppDefaultGroupIf is equal to zero, the
        value of tmnxL2tpLnsTuPppDefaultService must also be equal to zero."
    DEFVAL { "" }
    ::= { tmnxL2tpLnsTuPppEntry 6 }

tmnxL2tpLnsTuPppProxyLcp OBJECT-TYPE
    SYNTAX      TmnxAlwaysNeverOrDefault
    MAX-ACCESS  read-create
    STATUS      current
    DESCRIPTION
       "The value of tmnxL2tpLnsTuPppProxyLcp specifies 
        if this system re-uses the result of the Link Control Protocol (LCP) 
        negotiation done by the proxy (LAC).
         
        If the value of this object is 'always', the Proxy LCP AVPs received 
        from the LAC are used to initiate the LCP on this system.
        
        If the value of this object is 'never', this system restarts the LCP
        negotiation with the remote system.
        
        The value 'default' specifies that the actual value must be used
        of the object tmnxL2tpLnsTgPppProxyLcp."
    REFERENCE
       "RFC 2661 Layer Two Tunneling Protocol 'L2TP', 
        section 4.4.5 Proxy LCP and Authentication AVPs."
    DEFVAL { default }
    ::= { tmnxL2tpLnsTuPppEntry 7 }

tmnxL2tpLnsTuPppProxyAuth OBJECT-TYPE
    SYNTAX      TmnxAlwaysNeverOrDefault
    MAX-ACCESS  read-create
    STATUS      current
    DESCRIPTION
       "The value of tmnxL2tpLnsTuPppProxyAuth specifies 
        if this system re-uses the authentication done by the proxy (LAC).
         
        If the value of this object is 'always', the Authentication AVPs received 
        from the LAC are accepted.
        
        If the value of this object is 'never', this system restarts the 
        authentication of the remote system.
        
        The value 'default' specifies that the actual value must be used
        of the object tmnxL2tpLnsTgPppProxyAuth."
    REFERENCE
       "RFC 2661 Layer Two Tunneling Protocol 'L2TP', 
        section 4.4.5 Proxy LCP and Authentication AVPs."
    DEFVAL { default }
    ::= { tmnxL2tpLnsTuPppEntry 8 }

tmnxL2tpLnsTuPppMtu OBJECT-TYPE
    SYNTAX      TmnxL2tpPppMtu
    MAX-ACCESS  read-create
    STATUS      current
    DESCRIPTION
       "The value of tmnxL2tpLnsTuPppMtu specifies
        the MTU (Maximum Transmission Unit) for this tunnel.
        
        The value zero specifies that the actual value must be used
        of the object tmnxL2tpLnsTgPppMtu."
    DEFVAL { 0 }
    ::= { tmnxL2tpLnsTuPppEntry 9 }

tmnxL2tpLnsTuPppLcpKaInterval OBJECT-TYPE
    SYNTAX      TmnxL2tpLcpKaInterval
    UNITS       "seconds"
    MAX-ACCESS  read-create
    STATUS      current
    DESCRIPTION
       "The value of tmnxL2tpLnsTuPppLcpKaInterval specifies 
        the time interval in seconds at which LCP echo requests are transmitted
        for this tunnel.
        
        The value zero specifies that the actual value must be used
        of the object tmnxL2tpLnsTgPppLcpKaInterval.
        
        If the value of tmnxL2tpLnsTuPppLcpKaInterval is equal to zero, the
        value of tmnxL2tpLnsTuPppLcpKaHoldUp must also be equal to zero."
    DEFVAL { 0 }
    ::= { tmnxL2tpLnsTuPppEntry 10 }

tmnxL2tpLnsTuPppLcpKaHoldUp OBJECT-TYPE
    SYNTAX      TmnxL2tpLcpKaHoldUpMplier
    MAX-ACCESS  read-create
    STATUS      current
    DESCRIPTION
       "The value of tmnxL2tpLnsTuPppLcpKaHoldUp specifies
        how many LCP keepalive messages can be missed before the related 
        session is brought down.
        
        The value zero specifies that the actual value must be used
        of the object tmnxL2tpLnsTgPppLcpKaHoldUp.
        
        If the value of tmnxL2tpLnsTuPppLcpKaHoldUp is equal to zero, the
        value of tmnxL2tpLnsTuPppLcpKaInterval must also be equal to zero."
    DEFVAL { 0 }
    ::= { tmnxL2tpLnsTuPppEntry 11 }

tmnxL2tpLnsTuPppIpcpSubnetNeg OBJECT-TYPE
    SYNTAX      TmnxAlwaysNeverOrDefault
    MAX-ACCESS  read-create
    STATUS      current
    DESCRIPTION
       "The value of tmnxL2tpLnsTuPppIpcpSubnetNeg specifies 
        if IPCP subnet negotiation is enabled."
    DEFVAL { default }
    ::= { tmnxL2tpLnsTuPppEntry 13 }

tmnxL2tpLnsTuPppLcpIgnoreMagic OBJECT-TYPE
    SYNTAX      TmnxAlwaysNeverOrDefault
    MAX-ACCESS  read-create
    STATUS      current
    DESCRIPTION
       "The value of tmnxL2tpLnsTuPppLcpIgnoreMagic specifies 
        if checking the Magic-Number field in LCP Echo-Request and 
        Echo-Reply messages is skipped.
         
        If the value of tmnxL2tpLnsTuPppLcpIgnoreMagic is equal to 'never',
        checking is performed.
         
        If the value of tmnxL2tpLnsTuPppLcpIgnoreMagic is equal to 'always',
        checking is not performed.

        The value 'default' specifies that the actual value must be used
        of the object tmnxL2tpLnsTgPppLcpIgnoreMagic."
    REFERENCE
       "RFC 1661 PPP section 6.4. Magic-Number."
    DEFVAL { default }
    ::= { tmnxL2tpLnsTuPppEntry 14 }

tmnxL2tpLnsTuPppMinChapChall OBJECT-TYPE
    SYNTAX      Unsigned32 (0|8..64)
    MAX-ACCESS  read-create
    STATUS      current
    DESCRIPTION
        "The value of tmnxL2tpLnsTuPppMinChapChall specifies the minimum
         length of the CHAP challenge generated by the system.
         
         The value zero specifies that the actual value must be used
         of the object tmnxL2tpLnsTgPppMinChapChall.
         
         Set the value of this object together with the value
         of tmnxL2tpLnsTuPppMaxChapChall."
    DEFVAL { 0 }
    ::= { tmnxL2tpLnsTuPppEntry 15 }

tmnxL2tpLnsTuPppMaxChapChall OBJECT-TYPE
    SYNTAX      Unsigned32 (0|8..64)
    MAX-ACCESS  read-create
    STATUS      current
    DESCRIPTION
        "The value of tmnxL2tpLnsTuPppMaxChapChall specifies the maximum
         length of the CHAP challenge generated by the system.
         
         The value zero specifies that the actual value must be used
         of the object tmnxL2tpLnsTgPppMaxChapChall.
         
         Set the value of this object together with the value
         of tmnxL2tpLnsTuPppMinChapChall."
    DEFVAL { 0 }
    ::= { tmnxL2tpLnsTuPppEntry 16 }

--
--      The L2TP LNS Tunnel PPP Configuration Table
--
--  Augments the tmnxL2tpTuCfgTable.
--
--  The use of the AUGMENTS clause implies a one-to-one dependent relationship
--  between the base table, tmnxL2tpTuCfgTable, and the augmenting table,
--  tmnxL2tpTuMlpppTable. This in effect extends the tmnxL2tpTuCfgTable
--  with additional columns. Creation (or deletion) of a row in the
--  tmnxL2tpTuCfgTable results in the same fate for the row in the
--  tmnxL2tpTuMlpppTable.
--  

tmnxL2tpTuMlpppTable OBJECT-TYPE
    SYNTAX      SEQUENCE OF TmnxL2tpTuMlpppEntry
    MAX-ACCESS  not-accessible
    STATUS      current
    DESCRIPTION
       "The L2TP Tunnel configuration table
        contains objects to configure MLPPP  
        on L2TP Tunnels.
        
        Entries in this table are automatically created and deleted by the
        system."
    ::= { tmnxL2tpTuCfgObjs 4 }

tmnxL2tpTuMlpppEntry   OBJECT-TYPE
        SYNTAX          TmnxL2tpTuMlpppEntry
        MAX-ACCESS      not-accessible
        STATUS          current
        DESCRIPTION
       "Each conceptual row represents MLPPP information about 
        a Layer Two Tunneling Protocol LNS Tunnel configuration."
    AUGMENTS { tmnxL2tpTuCfgEntry }
    ::= { tmnxL2tpTuMlpppTable 1 }

TmnxL2tpTuMlpppEntry ::= 
    SEQUENCE {
        tmnxL2tpTuMlpppLastMgmtChange    TimeStamp,
        tmnxL2tpTuMlpppAdminState        TmnxAdminState,
        tmnxL2tpTuMlpppMaxLinks          Unsigned32,
        tmnxL2tpTuMlpppInterleave        TmnxAlwaysNeverOrDefault,
        tmnxL2tpTuMlpppMaxFragDelay      TmnxL2tpMlpppMaxFragDelay,
        tmnxL2tpTuMlpppReassemblyTo      TmnxL2tpMlpppReassemblyTimeout,
        tmnxL2tpTuMlpppShortSeqNumberRx  TmnxAlwaysNeverOrDefault,
        tmnxL2tpTuMlpppEpClass           TmnxL2tpMlpppEndpointClass,
        tmnxL2tpTuMlpppEpIpv4Address     InetAddressIPv4,
        tmnxL2tpTuMlpppEpMacAddress      MacAddress
        
    }
        
tmnxL2tpTuMlpppLastMgmtChange OBJECT-TYPE
    SYNTAX      TimeStamp
    MAX-ACCESS  read-only
    STATUS      current
    DESCRIPTION
        "The value of tmnxL2tpTuMlpppLastMgmtChange indicates the sysUpTime at
         the time of the most recent management-initiated change to this
         table row."
    ::= { tmnxL2tpTuMlpppEntry 1 }

tmnxL2tpTuMlpppAdminState OBJECT-TYPE
    SYNTAX      TmnxAdminState
    MAX-ACCESS  read-create
    STATUS      current
    DESCRIPTION
       "The value of tmnxL2tpTuMlpppAdminState specifies the
        administrative state of MLPPP for this 
        Layer Two Tunneling Protocol Tunnel.
        
        The value 'noop' specifies that the actual value must be used 
        of the object tmnxL2tpTgMlpppAdminState of the tunnel group 
        this tunnel configuration belongs to."
    DEFVAL { noop }
    ::= { tmnxL2tpTuMlpppEntry 2 }

tmnxL2tpTuMlpppMaxLinks OBJECT-TYPE
    SYNTAX      Unsigned32 (0|1..8)
    MAX-ACCESS  read-create
    STATUS      current
    DESCRIPTION
       "The value of the object tmnxL2tpTuMlpppMaxLinks specifies
        the maximum number of MLPPP links.
        
        The value of this object is only relevant for tunnels where this system
        performs the LNS role.
        
        The value zero specifies that the actual value must be used
        of the object tmnxL2tpTgMlpppMaxLinks of the tunnel group
        this tunnel configuration belongs to."
    DEFVAL { 0 }
    ::= { tmnxL2tpTuMlpppEntry 3 }

tmnxL2tpTuMlpppInterleave OBJECT-TYPE
    SYNTAX      TmnxAlwaysNeverOrDefault
    MAX-ACCESS  read-create
    STATUS      current
    DESCRIPTION
       "The value of tmnxL2tpTuMlpppInterleave specifies 
        if this system applies Link Fragmentation and Interleaving to the
        traffic sent from the LNS to the LAC.
         
        If the value of this object is 'always', downstream traffic is
        fragmented and interleaved, meaning that (non-fragmented) realtime 
        traffic is interleaved with fragments of non-realtime traffic.
        
        If the value of this object is 'never', downstream traffic is only
        fragmented but not reordered according to priority.
        
        The value 'default' specifies that the actual value must be used
        of the object tmnxL2tpTgMlpppInterleave.
                
        The value of this object is only relevant for tunnels where this system
        performs the LNS role."
    DEFVAL { default }
    ::= { tmnxL2tpTuMlpppEntry 4 }

tmnxL2tpTuMlpppMaxFragDelay OBJECT-TYPE
    SYNTAX      TmnxL2tpMlpppMaxFragDelay
    UNITS       "milliseconds"
    MAX-ACCESS  read-create
    STATUS      current
    DESCRIPTION
       "The value of tmnxL2tpTuMlpppMaxFragDelay specifies the
        maximum delay of fragments for this L2TP Tunnel.
                
        The value zero specifies that the actual value must be used
        of the object tmnxL2tpTgMlpppMaxFragDelay of the tunnel group
        this tunnel configuration belongs to.
        
        The value of this object is only relevant for tunnels where this system
        performs the LNS role."
    DEFVAL { 0 }
    ::= { tmnxL2tpTuMlpppEntry 5 }

tmnxL2tpTuMlpppReassemblyTo OBJECT-TYPE
    SYNTAX      TmnxL2tpMlpppReassemblyTimeout
    UNITS       "milliseconds"
    MAX-ACCESS  read-create
    STATUS      current
    DESCRIPTION
       "The value of tmnxL2tpTuMlpppReassemblyTo specifies the
        reassembly timeout for fragments for this L2TP Tunnel.
        
        The value zero specifies that the actual value must be used
        of the object tmnxL2tpTgMlpppReassemblyTo of the tunnel group
        this tunnel configuration belongs to.
        
        The value of this object is only relevant for tunnels where this system
        performs the LNS role."
    DEFVAL { 0 }
    ::= { tmnxL2tpTuMlpppEntry 6 }

tmnxL2tpTuMlpppShortSeqNumberRx OBJECT-TYPE
    SYNTAX      TmnxAlwaysNeverOrDefault
    MAX-ACCESS  read-create
    STATUS      current
    DESCRIPTION
       "The value of tmnxL2tpTuMlpppShortSeqNumberRx specifies 
        if this system requests to receive short sequence numbers from the peer.
         
        If the value of this object is 'always', this system includes 
        the Short Sequence Number Header Format Option in its LCP configuration
        options.
        
        If the value of this object is 'never', this system does not includes 
        the Short Sequence Number Header Format Option in its LCP configuration
        options.
        
        The value of this object is only relevant for tunnels where this system
        performs the LNS role."
        REFERENCE
           "RFC 1990 The PPP Multilink Protocol (MP)
            section 5.1.2."
    DEFVAL { default }
    ::= { tmnxL2tpTuMlpppEntry 7 }

tmnxL2tpTuMlpppEpClass OBJECT-TYPE
    SYNTAX      TmnxL2tpMlpppEndpointClass
    MAX-ACCESS  read-create
    STATUS      current
    DESCRIPTION
       "The value of tmnxL2tpTuMlpppEpClass specifies the
        type of endpoint.
        
        If the value of 'tmnxL2tpTuMlpppEpClass' is equal to 'ipv4Address',
        the address for the MLPPP Endpoint Discriminator Option is taken from
        tmnxL2tpTuMlpppEpIpv4Address.
        
        If the value of 'tmnxL2tpTuMlpppEpClass' is equal to 'macAddress',
        the address for the MLPPP Endpoint Discriminator Option is taken from
        tmnxL2tpTuMlpppEpMacAddress.
        
        The value 'default' specifies that the actual value must be used
        of the object tmnxL2tpTgMlpppEpClass of the tunnel group
        this tunnel configuration belongs to.
        
        A value other than 'default' is only relevant for tunnels 
        where this system performs the LNS role."
    REFERENCE
       "RFC 1990 The PPP Multilink Protocol (MP), 
        section 5.1.3 Endpoint Discriminator Option."
    DEFVAL { default }
    ::= { tmnxL2tpTuMlpppEntry 8 }

tmnxL2tpTuMlpppEpIpv4Address OBJECT-TYPE
    SYNTAX      InetAddressIPv4
    MAX-ACCESS  read-create
    STATUS      current
    DESCRIPTION
       "The value of tmnxL2tpTuMlpppEpIpv4Address specifies the
        class 2 address to use in the MLPPP Endpoint Discriminator Option.
        
        While the value of tmnxL2tpTuMlpppEpClass is equal to 'ipv4Address',
        a value of all zeroes specifies that the system IP address be used;
        otherwise, it means that no address is specified."
    REFERENCE
       "RFC 1990 The PPP Multilink Protocol (MP), 
        section 5.1.3 Endpoint Discriminator Option."
    DEFVAL { ''H }  
    ::= { tmnxL2tpTuMlpppEntry 9 }

tmnxL2tpTuMlpppEpMacAddress OBJECT-TYPE
    SYNTAX      MacAddress
    MAX-ACCESS  read-create
    STATUS      current
    DESCRIPTION
       "The value of tmnxL2tpTuMlpppEpMacAddress specifies the
        class 3 address to use in the MLPPP Endpoint Discriminator Option.
        
        While the value of tmnxL2tpTuMlpppEpClass is equal to 'macAddress',
        a value of all zeroes specifies that the system MAC address be used;
        otherwise, it means that no address is specified."
    REFERENCE
       "RFC 1990 The PPP Multilink Protocol (MP), 
        section 5.1.3 Endpoint Discriminator Option."
    DEFVAL { ''H }  
        ::= { tmnxL2tpTuMlpppEntry 10 }

--
--      The L2TP Extended Tunnel Configuration Table
--
--  Augments the tmnxL2tpTuCfgTable.
--
--  The use of the AUGMENTS clause implies a one-to-one dependent relationship
--  between the base table, tmnxL2tpTuCfgTable, and the augmenting table,
--  tmnxL2tpTuXtTable. This in effect extends the tmnxL2tpTuCfgTable
--  with additional columns. Creation (or deletion) of a row in the
--  tmnxL2tpTuCfgTable results in the same fate for the row in the
--  tmnxL2tpTuXtTable.
--  

tmnxL2tpTuXtTableLastCh OBJECT-TYPE
    SYNTAX      TimeStamp
    MAX-ACCESS  read-only
    STATUS      current
    DESCRIPTION
        "The value of the object tmnxL2tpTuXtTableLastCh indicates
         the value of sysUpTime at the time of the last modification of
         an entry in the tmnxL2tpTuXtTable."
    ::= { tmnxL2tpObjs 25 }
    
tmnxL2tpTuXtTable OBJECT-TYPE
    SYNTAX      SEQUENCE OF TmnxL2tpTuXtEntry
    MAX-ACCESS  not-accessible
    STATUS      current
    DESCRIPTION
       "The L2TP Tunnel configuration table
        contains more objects to configure L2TP Tunnels.
        
        Entries in this table are automatically created and deleted by the
        system."
    ::= { tmnxL2tpTuCfgObjs 5 }

tmnxL2tpTuXtEntry   OBJECT-TYPE
        SYNTAX          TmnxL2tpTuXtEntry
        MAX-ACCESS      not-accessible
        STATUS          current
        DESCRIPTION
       "Each conceptual row represents MLPPP information about 
        a Layer Two Tunneling Protocol Tunnel configuration."
    AUGMENTS { tmnxL2tpTuCfgEntry }
    ::= { tmnxL2tpTuXtTable 1 }

TmnxL2tpTuXtEntry ::= 
    SEQUENCE {
        tmnxL2tpTuXtLastMgmtChange    TimeStamp,
        tmnxL2tpTuXtDfBitLac          TmnxAlwaysNeverOrDefault       
    }
        
tmnxL2tpTuXtLastMgmtChange OBJECT-TYPE
    SYNTAX      TimeStamp
    MAX-ACCESS  read-only
    STATUS      current
    DESCRIPTION
        "The value of tmnxL2tpTuXtLastMgmtChange indicates the sysUpTime at
         the time of the most recent management-initiated change to this
         table row."
    ::= { tmnxL2tpTuXtEntry 1 }

tmnxL2tpTuXtDfBitLac OBJECT-TYPE
    SYNTAX      TmnxAlwaysNeverOrDefault
    MAX-ACCESS  read-create
    STATUS      current
    DESCRIPTION
       "The value of tmnxL2tpTuXtDfBitLac specifies 
        if this system sets the DF (Don't Fragment) bit in the IP header
        of the data traffic sent from the LAC to the LNS using this
        tunnel.
         
        If the value of this object is 'always', the DF bit is set
        in upstream traffic.
        
        If the value of this object is 'never', the DF bit is cleared
        in upstream traffic.
        
        The value 'default' specifies that the actual value must be used
        of the object tmnxL2tpTgXtDfBitLac.
        
        The value of this object is only relevant for tunnels where this system
        performs the LAC role."
    DEFVAL { default }  
    ::= { tmnxL2tpTuXtEntry 2 }

--
--      The L2TP Tunnel Status Table
--

tmnxL2tpTuStatusTableLastCh OBJECT-TYPE
    SYNTAX      TimeStamp
    MAX-ACCESS  read-only
    STATUS      current
    DESCRIPTION
        "The value of the object tmnxL2tpTuStatusTableLastCh indicates
         the value of sysUpTime at the time of the last modification of
         an entry in the tmnxL2tpTuStatusTable."
    ::= { tmnxL2tpObjs 13 }

tmnxL2tpTuStatusTable   OBJECT-TYPE
    SYNTAX      SEQUENCE OF TmnxL2tpTuStatusEntry
    MAX-ACCESS  not-accessible
    STATUS      current
    DESCRIPTION
       "The tmnxL2tpTuStatusTable has an entry for each 
        Layer Two Tunneling Protocol Tunnel."
    ::= { tmnxL2tpTuStatObjs 2 }

tmnxL2tpTuStatusEntry   OBJECT-TYPE
    SYNTAX      TmnxL2tpTuStatusEntry
    MAX-ACCESS  not-accessible
    STATUS      current
    DESCRIPTION
       "Each conceptual row represents a Layer Two Tunneling Protocol
        Tunnel.

        Entries in this table are created and destroyed by the system."
    INDEX { vRtrID,
            tmnxL2tpTuStatusId }
    ::= { tmnxL2tpTuStatusTable 1 }

TmnxL2tpTuStatusEntry ::= 
    SEQUENCE {
        tmnxL2tpTuStatusId               TmnxL2tpConnectionId,
        tmnxL2tpTuStatusState            TmnxL2tpTuOperState,
        tmnxL2tpTuStatusTunnelId         TmnxL2tpTunnelId,
        tmnxL2tpTuStatusPreference       TmnxL2tpTunnelPreference,
        tmnxL2tpTuStatusPeerAddrType     InetAddressType,
        tmnxL2tpTuStatusPeerAddr         InetAddress,
        tmnxL2tpTuStatusAddrType         InetAddressType,
        tmnxL2tpTuStatusAddr             InetAddress,
        tmnxL2tpTuStatusLocalName        TmnxL2tpHostNameOrEmpty,
        tmnxL2tpTuStatusRemoteName       TmnxL2tpHostNameOrEmpty,
        tmnxL2tpTuStatusAssignmentId     TmnxL2tpTunnelNameOrEmpty,
        tmnxL2tpTuStatusHelloInterval    TmnxL2tpTunnelHelloInterval,
        tmnxL2tpTuStatusIdleTO           TmnxL2tpTunnelIdleTO,
        tmnxL2tpTuStatusDestructTO       TmnxL2tpTunnelDestructTO,
        tmnxL2tpTuStatusMaxRetxEstab     TmnxL2tpTunnelMaxRetx,
        tmnxL2tpTuStatusMaxRetxNotEstab  TmnxL2tpTunnelMaxRetx,
        tmnxL2tpTuStatusSessionLimit     TmnxL2tpTunnelSessionLimit,
        tmnxL2tpTuStatusAvpHiding        TmnxL2tpAvpHidingMode,
        tmnxL2tpTuStatusGroupName        TmnxL2tpTunnelGroupNameOrEmpty,
        tmnxL2tpTuStatusRemoteTunnelId   TmnxL2tpTunnelId,
        tmnxL2tpTuStatusRemoteConnId     TmnxL2tpConnectionId,
        tmnxL2tpTuStatusTransportType    TmnxL2tpTransportType,
        tmnxL2tpTuStatusUdpPort          InetPortNumber,
        tmnxL2tpTuStatusRemoteUdpPort    InetPortNumber,
        tmnxL2tpTuStatusStartTime        TimeStamp,
        tmnxL2tpTuStatusEstabTime        TimeStamp,
        tmnxL2tpTuStatusIdleTime         TimeStamp,
        tmnxL2tpTuStatusClosedTime       TimeStamp,
        tmnxL2tpTuStatusStopCcnResult    TmnxL2tpStopCcnResult,
        tmnxL2tpTuStatusGeneralError     TmnxL2tpGeneralError,
        tmnxL2tpTuStatusErrorMessage     TmnxL2tpErrorMessage,
        tmnxL2tpTuStatusDoChallenge      TmnxL2tpDoChallenge,
        tmnxL2tpTuStatusRws              Unsigned32,
        tmnxL2tpTuStatusTxDestAddrType   InetAddressType,
        tmnxL2tpTuStatusTxDestAddr       InetAddress,
        tmnxL2tpTuStatusRxSrcAddrType    InetAddressType,
        tmnxL2tpTuStatusRxSrcAddr        InetAddress,
        tmnxL2tpTuStatusAccountingPolicy TNamedItemOrEmpty,
        tmnxL2tpTuStatusSelBlacklstState INTEGER, 
        tmnxL2tpTuStatusSelBlacklstTime  TimeStamp,
        tmnxL2tpTuStatSelBlacklstTimeRem Unsigned32,
        tmnxL2tpTuStatusTxDestUdpPort    InetPortNumber,
        tmnxL2tpTuStatusRxSrcUdpPort     InetPortNumber,
        tmnxL2tpTuStatusDfBitLac         TruthValue
    }

tmnxL2tpTuStatusId OBJECT-TYPE
    SYNTAX      TmnxL2tpConnectionId
    MAX-ACCESS  not-accessible
    STATUS      current
    DESCRIPTION
       "The value of the object tmnxL2tpTuStatusId indicates the local  
        identifier of this Layer Two Tunneling Protocol Tunnel.
        
        In L2TP version 2, it contains the 16-bit tunnel ID in the high-order
        bits.
        
        In L2TP version 3, it is the 32-bit control connection ID."
    ::= { tmnxL2tpTuStatusEntry 1 }

tmnxL2tpTuStatusState OBJECT-TYPE
    SYNTAX      TmnxL2tpTuOperState
    MAX-ACCESS  read-only
    STATUS      current
    DESCRIPTION
       "The value of tmnxL2tpTuStatusState indicates the
        operational state of this Layer Two Tunneling Protocol Tunnel."
    ::= { tmnxL2tpTuStatusEntry 2 }

tmnxL2tpTuStatusTunnelId OBJECT-TYPE
    SYNTAX      TmnxL2tpTunnelId
    MAX-ACCESS  read-only
    STATUS      current
    DESCRIPTION
       "The value of the object tmnxL2tpTuStatusTunnelId indicates the  
        local identifier of this Layer Two Tunneling Protocol Tunnel, 
        when L2TP version 2 is used.
        
        In L2TP version 3, it is equal to zero."
    ::= { tmnxL2tpTuStatusEntry 3 }

tmnxL2tpTuStatusPreference OBJECT-TYPE
    SYNTAX      TmnxL2tpTunnelPreference
    MAX-ACCESS  read-only
    STATUS      current
    DESCRIPTION
       "The value of tmnxL2tpTuStatusPreference indicates
        the preference of this Layer Two Tunneling Protocol Tunnel.
        
        The value '0' corresponds to the highest preference."
        ::= { tmnxL2tpTuStatusEntry 4 }

tmnxL2tpTuStatusPeerAddrType OBJECT-TYPE
    SYNTAX      InetAddressType
    MAX-ACCESS  read-only
    STATUS      current
    DESCRIPTION 
       "The value of tmnxL2tpTuStatusPeerAddrType indicates the
        address type of tmnxL2tpTuStatusPeerAddr."
    ::= { tmnxL2tpTuStatusEntry 5 }

tmnxL2tpTuStatusPeerAddr OBJECT-TYPE
    SYNTAX      InetAddress (SIZE(0|4|16))
    MAX-ACCESS  read-only
    STATUS      current
    DESCRIPTION 
       "The value of tmnxL2tpTuStatusPeerAddr indicates the IP
        address of the peer."
    ::= { tmnxL2tpTuStatusEntry 6 }

tmnxL2tpTuStatusAddrType OBJECT-TYPE
    SYNTAX      InetAddressType
    MAX-ACCESS  read-only
    STATUS      current
    DESCRIPTION 
       "The value of tmnxL2tpTuStatusAddrType indicates the
        address type of tmnxL2tpTuStatusAddr."
    ::= { tmnxL2tpTuStatusEntry 7 }

tmnxL2tpTuStatusAddr OBJECT-TYPE
    SYNTAX      InetAddress (SIZE(0|4|16))
    MAX-ACCESS  read-only
    STATUS      current
    DESCRIPTION 
       "The value of tmnxL2tpTuStatusAddr indicates the local IP
        address of this Layer Two Tunneling Protocol Tunnel."
    ::= { tmnxL2tpTuStatusEntry 8 }

tmnxL2tpTuStatusLocalName OBJECT-TYPE
    SYNTAX      TmnxL2tpHostNameOrEmpty
    MAX-ACCESS  read-only
    STATUS      current
    DESCRIPTION
       "The value of the object tmnxL2tpTuStatusLocalName indicates
        the host name used by this system 
        during the authentication phase of tunnel establishment.

        This object is related to the RADIUS attribute Tunnel-Client-Auth-ID.

        It can be used to distinguish tunnels."
    REFERENCE
       "RFC 2868 RADIUS Attributes for Tunnel Protocol Support
        section 3.9."
    ::= { tmnxL2tpTuStatusEntry 9 }

tmnxL2tpTuStatusRemoteName OBJECT-TYPE
    SYNTAX      TmnxL2tpHostNameOrEmpty
    MAX-ACCESS  read-only
    STATUS      current
    DESCRIPTION
       "The value of the object tmnxL2tpTuStatusRemoteName indicates
        a string that is compared to the host name used by the tunnel peer 
        during the authentication phase of tunnel establishment.

        This object is related to the RADIUS attribute Tunnel-Server-Auth-ID.

        It can be used to distinguish tunnels."
    REFERENCE
       "RFC 2868 RADIUS Attributes for Tunnel Protocol Support
        section 3.10."
    ::= { tmnxL2tpTuStatusEntry 10 }

tmnxL2tpTuStatusAssignmentId OBJECT-TYPE
    SYNTAX      TmnxL2tpTunnelNameOrEmpty
    MAX-ACCESS  read-only
    STATUS      current
    DESCRIPTION
       "The value of the object tmnxL2tpTuStatusAssignmentId indicates
        a string that distinguishes this Layer Two Tunneling Protocol Tunnel.

        This object is related to the RADIUS attribute Tunnel-Assignment-ID.

        If this tunnel corresponds to an entry in the tmnxL2tpTuCfgTable, the
        value of this object is equal to the value of the object 
        tmnxL2tpTuCfgName."
    REFERENCE
       "RFC 2868 RADIUS Attributes for Tunnel Protocol Support
        section 3.7."
    ::= { tmnxL2tpTuStatusEntry 11 }

tmnxL2tpTuStatusHelloInterval OBJECT-TYPE
    SYNTAX      TmnxL2tpTunnelHelloInterval
    UNITS       "seconds"
    MAX-ACCESS  read-only
    STATUS      current
    DESCRIPTION
       "The value of tmnxL2tpTuStatusHelloInterval indicates
        the time interval between two consecutive tunnel Hello messages.

        A value of '-1' indicates that the keepalive function is disabled."
        ::= { tmnxL2tpTuStatusEntry 13 }

tmnxL2tpTuStatusIdleTO OBJECT-TYPE
    SYNTAX      TmnxL2tpTunnelIdleTO
    UNITS       "seconds"
    MAX-ACCESS  read-only
    STATUS      current
    DESCRIPTION
       "The value of tmnxL2tpTuStatusIdleTO indicates
        the period of time that this Layer Two Tunneling Protocol Tunnel  
        will persist while it has no active sessions before being disconnected.

        A value of -1 indicates that the tunnel will not be disconnected when
        it has no more active sessions."
        ::= { tmnxL2tpTuStatusEntry 14 }

tmnxL2tpTuStatusDestructTO OBJECT-TYPE
    SYNTAX      TmnxL2tpTunnelDestructTO
    UNITS       "seconds"
    MAX-ACCESS  read-only
    STATUS      current
    DESCRIPTION
       "The value of tmnxL2tpTuStatusIdleTO indicates
        the period of time that data of this Layer Two Tunneling Protocol   
        Tunnel will persist after it is disconnected."
        ::= { tmnxL2tpTuStatusEntry 15 }

tmnxL2tpTuStatusMaxRetxEstab OBJECT-TYPE
    SYNTAX      TmnxL2tpTunnelMaxRetx
    MAX-ACCESS  read-only
    STATUS      current
    DESCRIPTION
       "The value of tmnxL2tpTuStatusMaxRetxEstab indicates
        the number of retries allowed for this
        Layer Two Tunneling Protocol Tunnel while it is established,
        before its control connection goes down."
        ::= { tmnxL2tpTuStatusEntry 16 }

tmnxL2tpTuStatusMaxRetxNotEstab OBJECT-TYPE
    SYNTAX      TmnxL2tpTunnelMaxRetx
    MAX-ACCESS  read-only
    STATUS      current
    DESCRIPTION
       "The value of tmnxL2tpTuStatusMaxRetxNotEstab indicates
        the number of retries allowed for this
        Layer Two Tunneling Protocol Tunnel while it is unestablished,
        before its control connection goes down."
        ::= { tmnxL2tpTuStatusEntry 17 }

tmnxL2tpTuStatusSessionLimit OBJECT-TYPE
    SYNTAX      TmnxL2tpTunnelSessionLimit
    MAX-ACCESS  read-only
    STATUS      current
    DESCRIPTION
       "The value of tmnxL2tpTuStatusSessionLimit indicates
        the maximum number of sessions allowed in this
        Layer Two Tunneling Protocol Tunnel."
        ::= { tmnxL2tpTuStatusEntry 18 }

tmnxL2tpTuStatusAvpHiding OBJECT-TYPE
    SYNTAX      TmnxL2tpAvpHidingMode
    MAX-ACCESS  read-only
    STATUS      current
    DESCRIPTION
       "The value of tmnxL2tpTuStatusAvpHiding indicates
        when the H bit in the header of each Attribute Value Pair (AVP) 
        is set for the L2TP control messages related to this 
        Layer Two Tunneling Protocol Tunnel."
    REFERENCE
       "RFC 2661 Layer Two Tunneling Protocol 'L2TP', 
        section 4.3 Hiding of AVP Attribute Values."
        ::= { tmnxL2tpTuStatusEntry 19 }

tmnxL2tpTuStatusGroupName OBJECT-TYPE
    SYNTAX      TmnxL2tpTunnelGroupNameOrEmpty
    MAX-ACCESS  read-only
    STATUS      current
    DESCRIPTION
       "The value of tmnxL2tpTuStatusGroupName indicates the
        name of the tunnel group where this Layer Two Tunneling Protocol Tunnel
         belongs to."
    ::= { tmnxL2tpTuStatusEntry 20 }

tmnxL2tpTuStatusRemoteTunnelId OBJECT-TYPE
    SYNTAX      TmnxL2tpTunnelId
    MAX-ACCESS  read-only
    STATUS      current
    DESCRIPTION
       "The value of the object tmnxL2tpTuStatusRemoteTunnelId indicates the  
        identifier of this Layer Two Tunneling Protocol Tunnel used by the 
        tunnel peer, when L2TP version 2 is used.
        
        In L2TP version 3, it is equal to zero."
    ::= { tmnxL2tpTuStatusEntry 21 }

tmnxL2tpTuStatusRemoteConnId OBJECT-TYPE
    SYNTAX      TmnxL2tpConnectionId
    MAX-ACCESS  read-only
    STATUS      current
    DESCRIPTION
       "The value of the object tmnxL2tpTuStatusRemoteConnId indicates the  
        identifier of this Layer Two Tunneling Protocol Tunnel used by the 
        tunnel peer."
    ::= { tmnxL2tpTuStatusEntry 22 }

tmnxL2tpTuStatusTransportType OBJECT-TYPE
    SYNTAX      TmnxL2tpTransportType
    MAX-ACCESS  read-only
    STATUS      current
    DESCRIPTION
       "The value of the object tmnxL2tpTuStatusTransportType indicates
        the transport type used for the messages of this
        Layer Two Tunneling Protocol Tunnel."
    ::= { tmnxL2tpTuStatusEntry 23 }

tmnxL2tpTuStatusUdpPort OBJECT-TYPE
    SYNTAX      InetPortNumber
    MAX-ACCESS  read-only
    STATUS      current
    DESCRIPTION 
       "The value of tmnxL2tpTuStatusAddr indicates the local UDP
        port of this Layer Two Tunneling Protocol Tunnel."
    ::= { tmnxL2tpTuStatusEntry 24 }

tmnxL2tpTuStatusRemoteUdpPort OBJECT-TYPE
    SYNTAX      InetPortNumber
    MAX-ACCESS  read-only
    STATUS      current
    DESCRIPTION 
       "The value of the object tmnxL2tpTuStatusRemoteUdpPort indicates the  
        UDP port of this Layer Two Tunneling Protocol Tunnel used by the 
        tunnel peer."
    ::= { tmnxL2tpTuStatusEntry 25 }

tmnxL2tpTuStatusStartTime OBJECT-TYPE
    SYNTAX      TimeStamp
    MAX-ACCESS  read-only
    STATUS      current
    DESCRIPTION 
        "The value of the object tmnxL2tpTuStatusStartTime indicates
         the value of sysUpTime when this Layer Two Tunneling Protocol Tunnel
         entered either the state 'waitReply' or 'waitConn'."
    ::= { tmnxL2tpTuStatusEntry 26 }

tmnxL2tpTuStatusEstabTime OBJECT-TYPE
    SYNTAX      TimeStamp
    MAX-ACCESS  read-only
    STATUS      current
    DESCRIPTION 
        "The value of the object tmnxL2tpTuStatusEstabTime indicates
         the value of sysUpTime when this Layer Two Tunneling Protocol Tunnel
         entered the state 'established'.
         
         The value zero means that this tunnel has not been established yet."
    ::= { tmnxL2tpTuStatusEntry 27 }

tmnxL2tpTuStatusIdleTime OBJECT-TYPE
    SYNTAX      TimeStamp
    MAX-ACCESS  read-only
    STATUS      current
    DESCRIPTION 
        "The value of the object tmnxL2tpTuStatusIdleTime indicates
         the value of sysUpTime when this Layer Two Tunneling Protocol Tunnel
         entered the state 'idle'.
         
         The value zero means that this tunnel has not become idle yet."
    ::= { tmnxL2tpTuStatusEntry 28 }

tmnxL2tpTuStatusClosedTime OBJECT-TYPE
    SYNTAX      TimeStamp
    MAX-ACCESS  read-only
    STATUS      current
    DESCRIPTION 
        "The value of the object tmnxL2tpTuStatusClosedTime indicates
         the value of sysUpTime when this Layer Two Tunneling Protocol Tunnel
         entered one of the closed states.
         
         The value zero means that this tunnel has not been closed yet."
    ::= { tmnxL2tpTuStatusEntry 29 }

tmnxL2tpTuStatusStopCcnResult OBJECT-TYPE
    SYNTAX      TmnxL2tpStopCcnResult
    MAX-ACCESS  read-only
    STATUS      current
    DESCRIPTION
       "The value of tmnxL2tpTuStatusStopCcnResult indicates
        the result of a StopCCN (Stop-Control-Connection-Notification) message 
        related to this Layer Two Tunneling Protocol Tunnel."
    REFERENCE
       "RFC 2661 Layer Two Tunneling Protocol 'L2TP', 
        section 4.4.2 Result and Error Codes."
        ::= { tmnxL2tpTuStatusEntry 30 }

tmnxL2tpTuStatusGeneralError OBJECT-TYPE
    SYNTAX      TmnxL2tpGeneralError
    MAX-ACCESS  read-only
    STATUS      current
    DESCRIPTION
       "The value of tmnxL2tpTuStatusGeneralError indicates
        an general error related to this Layer Two Tunneling Protocol Tunnel."
    REFERENCE
       "RFC 2661 Layer Two Tunneling Protocol 'L2TP', 
        section 4.4.2 Result and Error Codes."
        ::= { tmnxL2tpTuStatusEntry 31 }

tmnxL2tpTuStatusErrorMessage OBJECT-TYPE
    SYNTAX      TmnxL2tpErrorMessage
    MAX-ACCESS  read-only
    STATUS      current
    DESCRIPTION
       "The value of the object tmnxL2tpTuStatusErrorMessage indicates
        describes an error related to this Layer Two Tunneling Protocol Tunnel."
    REFERENCE
       "RFC 2661 Layer Two Tunneling Protocol 'L2TP', 
        section 4.4.2 Result and Error Codes."
    ::= { tmnxL2tpTuStatusEntry 32 }

tmnxL2tpTuStatusDoChallenge OBJECT-TYPE
    SYNTAX      TmnxL2tpDoChallenge
    MAX-ACCESS  read-only
    STATUS      current
    DESCRIPTION
       "The value of tmnxL2tpTuStatusDoChallenge indicates
        when challenge-response is used for the authentication of 
        this Layer Two Tunneling Protocol Tunnel."
        ::= { tmnxL2tpTuStatusEntry 33 }

tmnxL2tpTuStatusRws OBJECT-TYPE
    SYNTAX      Unsigned32
    UNITS       "seconds"
    MAX-ACCESS  read-only
    STATUS      current
    DESCRIPTION
       "The value of tmnxL2tpTuStatusRws indicates
        the actual Receive Window Size of this Layer Two Tunneling Protocol 
        Tunnel."
        ::= { tmnxL2tpTuStatusEntry 34 }

tmnxL2tpTuStatusTxDestAddrType OBJECT-TYPE
    SYNTAX      InetAddressType
    MAX-ACCESS  read-only
    STATUS      current
    DESCRIPTION 
       "The value of tmnxL2tpTuStatusTxDestAddrType indicates the
        address type of tmnxL2tpTuStatusTxDestAddr."
    ::= { tmnxL2tpTuStatusEntry 35 }

tmnxL2tpTuStatusTxDestAddr OBJECT-TYPE
    SYNTAX      InetAddress (SIZE(0|4|16))
    MAX-ACCESS  read-only
    STATUS      current
    DESCRIPTION 
       "The value of tmnxL2tpTuStatusTxDestAddr indicates the destination IP
        address used while transmitting L2TP control messages for
        this Layer Two Tunneling Protocol Tunnel.
        
        The destination address can be different from the value of the
        object tmnxL2tpTuStatusPeerAddr in case the value of the object
        tmnxL2tpPeerAddrChangePlcy is equal to 'accept'."
    ::= { tmnxL2tpTuStatusEntry 36 }

tmnxL2tpTuStatusRxSrcAddrType OBJECT-TYPE
    SYNTAX      InetAddressType
    MAX-ACCESS  read-only
    STATUS      current
    DESCRIPTION 
       "The value of tmnxL2tpTuStatusRxSrcAddrType indicates the
        address type of tmnxL2tpTuStatusRxSrcAddr."
    ::= { tmnxL2tpTuStatusEntry 37 }

tmnxL2tpTuStatusRxSrcAddr OBJECT-TYPE
    SYNTAX      InetAddress (SIZE(0|4|16))
    MAX-ACCESS  read-only
    STATUS      current
    DESCRIPTION 
       "The value of tmnxL2tpTuStatusRxSrcAddr indicates the source IP
        address found in L2TP control messages received for this 
        Layer Two Tunneling Protocol Tunnel.
        
        The source address can be different from the value of the object
        tmnxL2tpTuStatusAddr in case the value of the object
        tmnxL2tpPeerAddrChangePlcy is equal to 'accept' or 'ignore'."
    ::= { tmnxL2tpTuStatusEntry 38 }

tmnxL2tpTuStatusAccountingPolicy OBJECT-TYPE
    SYNTAX      TNamedItemOrEmpty
    MAX-ACCESS  read-only
    STATUS      current
    DESCRIPTION 
       "The value of tmnxL2tpTuStatusAccountingPolicy indicates 
        the RADIUS accounting policy of this 
        Layer Two Tunneling Protocol Tunnel."
    ::= { tmnxL2tpTuStatusEntry 40 }

tmnxL2tpTuStatusSelBlacklstState OBJECT-TYPE
    SYNTAX  INTEGER {
                notBlacklisted (0),
                blacklisted    (1),
                selectable     (2)
            }
    MAX-ACCESS  read-only
    STATUS      current
    DESCRIPTION
       "The value of tmnxL2tpTuStatusSelBlacklstState indicates if this 
        tunnel is deemed reachable or not.

        A value of 'notBlacklisted(0)' indicates the tunnel is not in the
        tunnel-selection-blacklist and is thus deemed reachable.

        A value of 'blacklisted(1)' indicates the tunnel is currently in the
        tunnel-selection-blacklist and is thus deemed unreachable. The tunnel
        will remain there until the timeout specified in 
        tmnxL2tpXtTuSelBlacklistMaxTime has expired.

        A value of 'selectable(2)' indicates the tunnel has been in the
        tunnel-selection-blacklist for the time specified in
        tmnxL2tpXtTuSelBlacklistMaxTime and can now be selected for a single
        session, after which the reachability of the tunnel will be 
        reevaluated."
    ::= { tmnxL2tpTuStatusEntry 41 }

tmnxL2tpTuStatusSelBlacklstTime OBJECT-TYPE
    SYNTAX      TimeStamp
    MAX-ACCESS  read-only
    STATUS      current
    DESCRIPTION
       "The value of tmnxL2tpTuStatusSelBlacklstTime indicates when the tunnel
        was put in the tunnel-selection-blacklist.

        If the tunnel is currently not in the tunnel-selection-blacklist,
        tmnxL2tpTuStatusSelBlacklstTime will be set to zero."
    ::= { tmnxL2tpTuStatusEntry 42 }

tmnxL2tpTuStatSelBlacklstTimeRem OBJECT-TYPE
    SYNTAX      Unsigned32
    UNITS       "seconds"
    MAX-ACCESS  read-only
    STATUS      current
    DESCRIPTION
       "The value of tmnxL2tpTuStatSelBlacklstTimeRem indicates the remaining
        time the tunnel will remain in the tunnel-selection-blacklist.

        If the tunnel is currently not in the tunnel-selection-blacklist,
        tmnxL2tpTuStatSelBlacklstTimeRem will be set to zero."
    ::= { tmnxL2tpTuStatusEntry 43 }

tmnxL2tpTuStatusTxDestUdpPort OBJECT-TYPE
    SYNTAX      InetPortNumber
    MAX-ACCESS  read-only
    STATUS      current
    DESCRIPTION 
       "The value of tmnxL2tpTuStatusTxDestUdpPort indicates the destination
        UDP port used while transmitting L2TP control messages for
        this Layer Two Tunneling Protocol Tunnel.
        
        The destination UDP port can be different from the value of the
        object tmnxL2tpTuStatusRemoteUdpPort in case the peer used a different
        source UDP port in its Start-Control-Connection-Reply
        than the destination UDP port in the Start-Control-Connection-Request."
    REFERENCE
       "RFC 2661 Layer Two Tunneling Protocol 'L2TP', 
        section 8.1 L2TP over UDP/IP."
    ::= { tmnxL2tpTuStatusEntry 44 }

tmnxL2tpTuStatusRxSrcUdpPort OBJECT-TYPE
    SYNTAX      InetPortNumber
    MAX-ACCESS  read-only
    STATUS      current
    DESCRIPTION 
       "The value of tmnxL2tpTuStatusRxSrcUdpPort indicates the source
        UDP port found in L2TP control messages received for this 
        Layer Two Tunneling Protocol Tunnel.
        
        The source UDP port can be different from the value of the object
        tmnxL2tpTuStatusRemoteUdpPort in case the peer used a different source UDP port 
        - in its Start-Control-Connection-Reply, or
        - in any control message, while the value of the object tmnxL2tpPeerAddrChangePlcy
          is equal to 'ignore'."
    REFERENCE
       "RFC 2661 Layer Two Tunneling Protocol 'L2TP', 
        section 8.1 L2TP over UDP/IP."
    ::= { tmnxL2tpTuStatusEntry 45 }

tmnxL2tpTuStatusDfBitLac OBJECT-TYPE
    SYNTAX      TruthValue
    MAX-ACCESS  read-only
    STATUS      current
    DESCRIPTION
       "The value of tmnxL2tpTuStatusDfBitLac indicates
        if this system, while performing the LAC role,
        sets the DF (Don't Fragment) bit in the IP header
        of the data traffic transmitted with this Layer Two Tunneling Protocol Tunnel."
        ::= { tmnxL2tpTuStatusEntry 46 }

--
--      The L2TP Tunnel Statistics Table
--
--  Augmentation of the tmnxL2tpTuStatusTable
--  Use of AUGMENTS clause implies a one-to-one dependent relationship
--  between the base table, tmnxL2tpTuStatusTable, and the augmenting table,
--  tmnxL2tpTuStatsTable. This in effect extends the tmnxL2tpTuStatusTable
--  with additional columns. Creation (or deletion) of a row in the
--  tmnxL2tpTuStatusTable results in the same fate for the row in the
--  tmnxL2tpTuStatsTable.


tmnxL2tpTuStatsTable   OBJECT-TYPE
    SYNTAX      SEQUENCE OF TmnxL2tpTuStatsEntry
    MAX-ACCESS  not-accessible
    STATUS      current
    DESCRIPTION
       "The tmnxL2tpTuStatsTable has an entry for each 
        Layer Two Tunneling Protocol Tunnel."
    ::= { tmnxL2tpTuStatObjs 3 }

tmnxL2tpTuStatsEntry   OBJECT-TYPE
    SYNTAX          TmnxL2tpTuStatsEntry
    MAX-ACCESS      not-accessible
    STATUS          current
    DESCRIPTION
       "Each conceptual row represents statistics information of
        a Layer Two Tunneling Protocol Tunnel.

        Entries in this table are created and destroyed by the system."
    AUGMENTS { tmnxL2tpTuStatusEntry }
        ::= { tmnxL2tpTuStatsTable 1 }

TmnxL2tpTuStatsEntry ::= 
    SEQUENCE {
        tmnxL2tpTuStatsLastCleared       TimeStamp,
        tmnxL2tpTuStatsTotalSessions     Counter32,
        tmnxL2tpTuStatsFailedSessions    Counter32,
        tmnxL2tpTuStatsActiveSessions    Gauge32,
        tmnxL2tpTuStatsSessions          Gauge32,
        tmnxL2tpTuStatsControlRxOctets   Counter64,
        tmnxL2tpTuStatsControlRxOctetsLw Counter32,
        tmnxL2tpTuStatsControlRxOctetsHw Counter32,
        tmnxL2tpTuStatsControlRxPkts     Counter32,
        tmnxL2tpTuStatsControlTxOctets   Counter64,
        tmnxL2tpTuStatsControlTxOctetsLw Counter32,
        tmnxL2tpTuStatsControlTxOctetsHw Counter32,
        tmnxL2tpTuStatsControlTxPkts     Counter32,
        tmnxL2tpTuStatsErrorTxPkts       Counter32,
        tmnxL2tpTuStatsErrorRxPkts       Counter32,
        tmnxL2tpTuStatsFsmMsgAccepted    Counter32,
        tmnxL2tpTuStatsFsmMsgDuplicateRx Counter32,
        tmnxL2tpTuStatsFsmMsgOutOfWndwRx Counter32,
        tmnxL2tpTuStatsQLengthUnsentMax  Gauge32,
        tmnxL2tpTuStatsQLengthUnsentCur  Gauge32,
        tmnxL2tpTuStatsQLengthAckMax     Gauge32,
        tmnxL2tpTuStatsQLengthAckCur     Gauge32,
        tmnxL2tpTuStatsWindowSizeCur     Gauge32
    }

tmnxL2tpTuStatsLastCleared OBJECT-TYPE
    SYNTAX      TimeStamp
    MAX-ACCESS  read-only
    STATUS      current
    DESCRIPTION 
       "The value of the object tmnxL2tpTuStatsLastCleared indicates
        the value of sysUpTime when the contents of this conceptual row were 
        cleared for the last time.
         
        The value zero means that the contents of this conceptual row have not 
        yet been cleared."
    ::= { tmnxL2tpTuStatsEntry 1 }

tmnxL2tpTuStatsTotalSessions  OBJECT-TYPE
    SYNTAX      Counter32
    MAX-ACCESS  read-only
    STATUS      current
    DESCRIPTION
       "The value of tmnxL2tpTuStatsTotalSessions indicates
        the number of session creation attempts in this tunnel
        since the last re-initialization of the local network 
        management subsystem, or the last time the tunnel statistics were 
        cleared."
    ::= { tmnxL2tpTuStatsEntry 2 }

tmnxL2tpTuStatsFailedSessions  OBJECT-TYPE
    SYNTAX      Counter32
    MAX-ACCESS  read-only
    STATUS      current
    DESCRIPTION
       "The value of tmnxL2tpTuStatsFailedSessions indicates
        the number of sessions in this tunnel that failed to reach the 
        established state since the last re-initialization of the local network 
        management subsystem, or the last time the tunnel statistics were 
        cleared."
    ::= { tmnxL2tpTuStatsEntry 3 }

tmnxL2tpTuStatsActiveSessions  OBJECT-TYPE
    SYNTAX      Gauge32
    MAX-ACCESS  read-only
    STATUS      current
    DESCRIPTION
       "The value of tmnxL2tpTuStatsActiveSessions indicates 
        the number of sessions currently established in this tunnel."
    ::= { tmnxL2tpTuStatsEntry 4 }

tmnxL2tpTuStatsSessions  OBJECT-TYPE
    SYNTAX      Gauge32
    MAX-ACCESS  read-only
    STATUS      current
    DESCRIPTION
       "The value of tmnxL2tpTuStatsSessions indicates 
        the actual number of sessions in this tunnel."
    ::= { tmnxL2tpTuStatsEntry 5 }

tmnxL2tpTuStatsControlRxOctets OBJECT-TYPE
    SYNTAX      Counter64
    MAX-ACCESS  read-only
    STATUS      current
    DESCRIPTION
       "The value of tmnxL2tpTuStatsControlRxOctets indicates
        the number of control channel octets received in this tunnel
        since the last re-initialization of the local network 
        management subsystem, or the last time the tunnel statistics were 
        cleared."
    ::= { tmnxL2tpTuStatsEntry 6 }

tmnxL2tpTuStatsControlRxOctetsLw OBJECT-TYPE
    SYNTAX      Counter32
    MAX-ACCESS  read-only
    STATUS      current
    DESCRIPTION
       "The value of tmnxL2tpTuStatsControlRxOctetsLw indicates
        the lower 32-bits word of the value of tmnxL2tpTuStatsControlRxOctets."
    ::= { tmnxL2tpTuStatsEntry 7 }

tmnxL2tpTuStatsControlRxOctetsHw OBJECT-TYPE
    SYNTAX      Counter32
    MAX-ACCESS  read-only
    STATUS      current
    DESCRIPTION
       "The value of tmnxL2tpTuStatsControlRxOctetsHw indicates
        the higher 32-bits word of the value of tmnxL2tpTuStatsControlRxOctets."
    ::= { tmnxL2tpTuStatsEntry 8 }

tmnxL2tpTuStatsControlRxPkts OBJECT-TYPE
    SYNTAX      Counter32
    MAX-ACCESS  read-only
    STATUS      current
    DESCRIPTION
       "The value of tmnxL2tpTuStatsControlRxPkts indicates
        the number of control packets received by this tunnel
        since the last re-initialization of the local network 
        management subsystem, or the last time the tunnel statistics were 
        cleared."
    ::= { tmnxL2tpTuStatsEntry 9 }

tmnxL2tpTuStatsControlTxOctets OBJECT-TYPE
    SYNTAX      Counter64
    MAX-ACCESS  read-only
    STATUS      current
    DESCRIPTION
       "The value of tmnxL2tpTuStatsControlTxOctets indicates
        the number of control channel octets that were transmitted  
        to the current tunnel endpoints in this tunnel
        since the last re-initialization of the local network 
        management subsystem, or the last time the tunnel statistics were 
        cleared."
    ::= { tmnxL2tpTuStatsEntry 10 }

tmnxL2tpTuStatsControlTxOctetsLw OBJECT-TYPE
    SYNTAX      Counter32
    MAX-ACCESS  read-only
    STATUS      current
    DESCRIPTION
       "The value of tmnxL2tpTuStatsControlTxOctetsLw indicates
        the lower 32-bits word of the value of tmnxL2tpTuStatsControlTxOctets."
    ::= { tmnxL2tpTuStatsEntry 11 }

tmnxL2tpTuStatsControlTxOctetsHw OBJECT-TYPE
    SYNTAX      Counter32
    MAX-ACCESS  read-only
    STATUS      current
    DESCRIPTION
       "The value of tmnxL2tpTuStatsControlTxOctetsHw indicates
        the higher 32-bits word of the value of tmnxL2tpTuStatsControlTxOctets."
    ::= { tmnxL2tpTuStatsEntry 12 }

tmnxL2tpTuStatsControlTxPkts OBJECT-TYPE
    SYNTAX      Counter32
    MAX-ACCESS  read-only
    STATUS      current
    DESCRIPTION
       "The value of tmnxL2tpTuStatsControlTxOctets indicates
        the number of control packets that were transmitted to 
        the current tunnel endpoints in this tunnel
        since the last re-initialization of the local network 
        management subsystem, or the last time the tunnel statistics were 
        cleared."
    ::= { tmnxL2tpTuStatsEntry 13 }

tmnxL2tpTuStatsErrorTxPkts OBJECT-TYPE
    SYNTAX      Counter32
    MAX-ACCESS  read-only
    STATUS      current
    DESCRIPTION
       "The value of tmnxL2tpTuStatsErrorTxPkts indicates
        the number of packet transmission errors on this tunnel
        since the last re-initialization of the local network 
        management subsystem, or the last time the tunnel statistics were 
        cleared."
    ::= { tmnxL2tpTuStatsEntry 14 }

tmnxL2tpTuStatsErrorRxPkts OBJECT-TYPE
    SYNTAX      Counter32
    MAX-ACCESS  read-only
    STATUS      current
    DESCRIPTION
       "The value of tmnxL2tpTuStatsErrorRxPkts indicates
        the number of errored packets that were received on this tunnel
        since the last re-initialization of the local network 
        management subsystem, or the last time the tunnel statistics were 
        cleared."
    ::= { tmnxL2tpTuStatsEntry 15 }

tmnxL2tpTuStatsFsmMsgAccepted OBJECT-TYPE
    SYNTAX      Counter32
    MAX-ACCESS  read-only
    STATUS      current
    DESCRIPTION
       "The value of tmnxL2tpTuStatsFsmMsgAccepted indicates
        the number of Finite State Machine (FSM) messages
        that were accepted on this tunnel
        since the last re-initialization of the local network 
        management subsystem, or the last time the tunnel statistics were 
        cleared."
    ::= { tmnxL2tpTuStatsEntry 16 }

tmnxL2tpTuStatsFsmMsgDuplicateRx OBJECT-TYPE
    SYNTAX      Counter32
    MAX-ACCESS  read-only
    STATUS      current
    DESCRIPTION
       "The value of tmnxL2tpTuStatsFsmMsgDuplicateRx indicates
        the number of Finite State Machine (FSM) duplicate messages
        that were received on this tunnel
        since the last re-initialization of the local network 
        management subsystem, or the last time the tunnel statistics were 
        cleared."
    ::= { tmnxL2tpTuStatsEntry 17 }

tmnxL2tpTuStatsFsmMsgOutOfWndwRx OBJECT-TYPE
    SYNTAX      Counter32
    MAX-ACCESS  read-only
    STATUS      current
    DESCRIPTION
       "The value of tmnxL2tpTuStatsFsmMsgOutOfWndwRx indicates
        the number of Finite State Machine (FSM) messages
        that were received out of the receive window on this tunnel
        since the last re-initialization of the local network 
        management subsystem, or the last time the tunnel statistics were 
        cleared."
    ::= { tmnxL2tpTuStatsEntry 18 }

tmnxL2tpTuStatsQLengthUnsentMax OBJECT-TYPE
    SYNTAX      Gauge32
    MAX-ACCESS  read-only
    STATUS      current
    DESCRIPTION
       "The value of tmnxL2tpTuStatsQLengthUnsentMax indicates
        the the maximum length of the unsent message queue on this tunnel
        since the last re-initialization of the local network 
        management subsystem, or the last time the tunnel statistics were 
        cleared."
    ::= { tmnxL2tpTuStatsEntry 19 }

tmnxL2tpTuStatsQLengthUnsentCur OBJECT-TYPE
    SYNTAX      Gauge32
    MAX-ACCESS  read-only
    STATUS      current
    DESCRIPTION
       "The value of tmnxL2tpTuStatsErrorRxPkts indicates
        the the current length of the unsent message queue on this tunnel."
    ::= { tmnxL2tpTuStatsEntry 20 }

tmnxL2tpTuStatsQLengthAckMax OBJECT-TYPE
    SYNTAX      Gauge32
    MAX-ACCESS  read-only
    STATUS      current
    DESCRIPTION
       "The value of tmnxL2tpTuStatsErrorRxPkts indicates
        the the maximum length of the acknowledged message queue on this tunnel
        since the last re-initialization of the local network 
        management subsystem, or the last time the tunnel statistics were 
        cleared."
    ::= { tmnxL2tpTuStatsEntry 21 }

tmnxL2tpTuStatsQLengthAckCur OBJECT-TYPE
    SYNTAX      Gauge32
    MAX-ACCESS  read-only
    STATUS      current
    DESCRIPTION
       "The value of tmnxL2tpTuStatsErrorRxPkts indicates
        the the current length of the acknowledged message queue on this tunnel."
    ::= { tmnxL2tpTuStatsEntry 22 }

tmnxL2tpTuStatsWindowSizeCur OBJECT-TYPE
    SYNTAX      Gauge32
    MAX-ACCESS  read-only
    STATUS      current
    DESCRIPTION
       "The value of tmnxL2tpTuStatsErrorRxPkts indicates
        the the current size of the receive window on this tunnel."
    ::= { tmnxL2tpTuStatsEntry 23 }

--
--      The L2TP Tunnel Protocol Statistics Table
--

tmnxL2tpTuProtStatsTable   OBJECT-TYPE
    SYNTAX      SEQUENCE OF TmnxL2tpTuProtStatsEntry
    MAX-ACCESS  not-accessible
    STATUS      current
    DESCRIPTION
       "The tmnxL2tpTuProtStatsTable shows protocol statistics information 
        of Layer Two Tunneling Protocol Tunnels."
    ::= { tmnxL2tpTuStatObjs 4 }

tmnxL2tpTuProtStatsEntry   OBJECT-TYPE
    SYNTAX      TmnxL2tpTuProtStatsEntry
    MAX-ACCESS  not-accessible
    STATUS      current
    DESCRIPTION
       "Each conceptual row represents protocol statistics of a specific type.

        Entries in this table are created and destroyed by the system.
         
        Rows are only created where the statistics value is nonzero;
        this allows faster walking through this table; hence, it is recommended
        to perform only get-next-request operations to retrieve information
        from this table."
    INDEX { vRtrID,
            tmnxL2tpTuStatusId,
            tmnxL2tpTuProtStatsType,
            tmnxL2tpTuProtStatsInstance }
    ::= { tmnxL2tpTuProtStatsTable 1 }

TmnxL2tpTuProtStatsEntry ::= 
    SEQUENCE {
        tmnxL2tpTuProtStatsType          TmnxL2tpTuProtStatsType,
        tmnxL2tpTuProtStatsInstance      Unsigned32,
        tmnxL2tpTuProtStatsName          DisplayString,
        tmnxL2tpTuProtStatsVal           Counter32
    }

tmnxL2tpTuProtStatsType OBJECT-TYPE
    SYNTAX      TmnxL2tpTuProtStatsType
    MAX-ACCESS  not-accessible
    STATUS      current
    DESCRIPTION 
       "The value of the object tmnxL2tpTuProtStatsType indicates
        the type of L2TP protocol statistics contained in this conceptual row."
    ::= { tmnxL2tpTuProtStatsEntry 1 }

tmnxL2tpTuProtStatsInstance OBJECT-TYPE
    SYNTAX      Unsigned32 (0..49)
    MAX-ACCESS  not-accessible
    STATUS      current
    DESCRIPTION 
       "The value of the object tmnxL2tpTuProtStatsType indicates
        the instance identifier of the statistics 
        contained in this conceptual row.
        
        For example: if the value of the object tmnxL2tpTuProtStatsType is equal
        to 'outgoingMsgType', the value of tmnxL2tpTuProtStatsInstance is 
        a message identifier, 
        e.g. instance '2' refers to '(SCCRP) Start-Control-Connection-Reply', 
        and the value of tmnxL2tpTuProtStatsVal indicates the number of SCCRP 
        messages transmitted for this tunnel.
        
        Unknown protocol messages are counted with instance zero."
    ::= { tmnxL2tpTuProtStatsEntry 2 }

tmnxL2tpTuProtStatsName OBJECT-TYPE
    SYNTAX      DisplayString (SIZE (1..64))
    MAX-ACCESS  read-only
    STATUS      current
    DESCRIPTION 
       "The value of the object tmnxL2tpTuProtStatsType indicates
        the human-readable identifier of the statistics 
        contained in this conceptual row.
        
        In the same example, the value of tmnxL2tpTuProtStatsName is 
        '(SCCRP) Start-Control-Connection-Reply'."
    ::= { tmnxL2tpTuProtStatsEntry 3 }

tmnxL2tpTuProtStatsVal OBJECT-TYPE
    SYNTAX      Counter32
    MAX-ACCESS  read-only
    STATUS      current
    DESCRIPTION 
       "The value of the object tmnxL2tpTuProtStatsType indicates
        the value of the statistics contained in this conceptual row."
    ::= { tmnxL2tpTuProtStatsEntry 4 }

--
--      The L2TP Tunnel Operations Start Table
--
--  Augmentation of the tmnxL2tpTuCfgTable
--  Use of AUGMENTS clause implies a one-to-one dependent relationship
--  between the base table, tmnxL2tpTuCfgTable, and the augmenting table,
--  tmnxL2tpTuStartTable. This in effect extends the tmnxL2tpTuCfgTable
--  with additional columns. Creation (or deletion) of a row in the
--  tmnxL2tpTuCfgTable results in the same fate for the row in the
--  tmnxL2tpTuStartTable.

tmnxL2tpTuStartTable   OBJECT-TYPE
    SYNTAX      SEQUENCE OF TmnxL2tpTuStartEntry
    MAX-ACCESS  not-accessible
    STATUS      current
    DESCRIPTION
       "The tmnxL2tpTuStartTable has an entry for each 
        Layer Two Tunneling Protocol Tunnel."
    ::= { tmnxL2tpTuOpObjs 1 }

tmnxL2tpTuStartEntry   OBJECT-TYPE
    SYNTAX      TmnxL2tpTuStartEntry
    MAX-ACCESS  not-accessible
    STATUS      current
    DESCRIPTION
       "Each conceptual row presents an operations interface to start
        a Layer Two Tunneling Protocol Tunnel control connection.

        Entries in this table are created and destroyed by the system."
    AUGMENTS { tmnxL2tpTuCfgEntry }
        ::= { tmnxL2tpTuStartTable 1 }

TmnxL2tpTuStartEntry ::= 
    SEQUENCE {
        tmnxL2tpTuStart                  TmnxActionType
    }
        
tmnxL2tpTuStart OBJECT-TYPE
    SYNTAX      TmnxActionType
    MAX-ACCESS  read-write
    STATUS      current
    DESCRIPTION
        "Setting this object to 'doAction (1)' triggers 
         an attempt to start the control connection for this L2TP tunnel.

         Reading this object returns the value 'notApplicable'."
    DEFVAL { notApplicable }
    ::= { tmnxL2tpTuStartEntry 1 }

--
--      The L2TP Tunnel Operations Stop Table
--
--  Augmentation of the tmnxL2tpTuStatusTable
--  Use of AUGMENTS clause implies a one-to-one dependent relationship
--  between the base table, tmnxL2tpTuStatusTable, and the augmenting table,
--  tmnxL2tpTuStopTable. This in effect extends the tmnxL2tpTuStatusTable
--  with additional columns. Creation (or deletion) of a row in the
--  tmnxL2tpTuStatusTable results in the same fate for the row in the
--  tmnxL2tpTuStopTable.


tmnxL2tpTuStopTable   OBJECT-TYPE
    SYNTAX      SEQUENCE OF TmnxL2tpTuStopEntry
    MAX-ACCESS  not-accessible
    STATUS      current
    DESCRIPTION
       "The tmnxL2tpTuStopTable has an entry for each 
        active Layer Two Tunneling Protocol Tunnel."
    ::= { tmnxL2tpTuOpObjs 2 }

tmnxL2tpTuStopEntry   OBJECT-TYPE
        SYNTAX          TmnxL2tpTuStopEntry
        MAX-ACCESS      not-accessible
        STATUS          current
        DESCRIPTION
       "Each conceptual row presents an operations interface to stop
        a Layer Two Tunneling Protocol Tunnel control connection.

        Entries in this table are created and destroyed by the system."
    AUGMENTS { tmnxL2tpTuStatusEntry }
        ::= { tmnxL2tpTuStopTable 1 }

TmnxL2tpTuStopEntry ::= 
    SEQUENCE {
        tmnxL2tpTuStop                  TmnxActionType
    }

tmnxL2tpTuStop OBJECT-TYPE
    SYNTAX      TmnxActionType
    MAX-ACCESS  read-write
    STATUS      current
    DESCRIPTION
        "Setting this object to 'doAction (1)' triggers 
         an attempt to stop the control connection for this L2TP tunnel.

         Reading this object returns the value 'notApplicable'."
    DEFVAL { notApplicable }
    ::= { tmnxL2tpTuStopEntry 1 }

--
--      The L2TP Tunnel Operations Drain Table
--
--  Augmentation of the tmnxL2tpTuStatusTable
--  Use of AUGMENTS clause implies a one-to-one dependent relationship
--  between the base table, tmnxL2tpTuStatusTable, and the augmenting table,
--  tmnxL2tpTuDrainTable. This in effect extends the tmnxL2tpTuStatusTable
--  with additional columns. Creation (or deletion) of a row in the
--  tmnxL2tpTuStatusTable results in the same fate for the row in the
--  tmnxL2tpTuDrainTable.


tmnxL2tpTuDrainTable   OBJECT-TYPE
    SYNTAX      SEQUENCE OF TmnxL2tpTuDrainEntry
    MAX-ACCESS  not-accessible
    STATUS      current
    DESCRIPTION
       "The tmnxL2tpTuDrainTable has an entry for each 
        active Layer Two Tunneling Protocol Tunnel."
    ::= { tmnxL2tpTuOpObjs 3 }

tmnxL2tpTuDrainEntry   OBJECT-TYPE
        SYNTAX          TmnxL2tpTuDrainEntry
        MAX-ACCESS      not-accessible
        STATUS          current
        DESCRIPTION
       "Each conceptual row presents an operations interface to drain
        a Layer Two Tunneling Protocol Tunnel.

        After a successful drain operation, the value of the object
        tmnxL2tpTuStatusState of this tunnel is equal to 'draining'; this 
        tunnel does not accept or establish new connections, while existing 
        connections are timing out.

        Entries in this table are created and destroyed by the system."
    AUGMENTS { tmnxL2tpTuStatusEntry }
        ::= { tmnxL2tpTuDrainTable 1 }

TmnxL2tpTuDrainEntry ::= 
    SEQUENCE {
        tmnxL2tpTuDrain                  TmnxL2tpActionTypeDrain
    }

tmnxL2tpTuDrain OBJECT-TYPE
    SYNTAX      TmnxL2tpActionTypeDrain
    MAX-ACCESS  read-write
    STATUS      current
    DESCRIPTION
        "Setting this object to 'drain (0)' triggers 
         an attempt to drain this L2TP tunnel.

         Setting it to 'stopDrain (1)' stops the draining.
         
         Reading this object returns the value 'notApplicable'."
    DEFVAL { notApplicable }
    ::= { tmnxL2tpTuDrainEntry 1 }

-- ----------------------------------------------------------------------------
--      The "L2TP Peer" Group
-- ----------------------------------------------------------------------------

tmnxL2tpPeerStatObjs            OBJECT IDENTIFIER   ::= { tmnxL2tpPeerObjs 1 }
tmnxL2tpPeerOpObjs              OBJECT IDENTIFIER   ::= { tmnxL2tpPeerObjs 2 }

--
--      The L2TP Peer Status and Statistics Table
--

tmnxL2tpPeerStatTable   OBJECT-TYPE
    SYNTAX      SEQUENCE OF TmnxL2tpPeerStatEntry
    MAX-ACCESS  not-accessible
    STATUS      current
    DESCRIPTION
       "The tmnxL2tpPeerStatTable contains status and statistics information
        about L2TP peers."
    ::= { tmnxL2tpPeerStatObjs 1 }

tmnxL2tpPeerStatEntry   OBJECT-TYPE
    SYNTAX      TmnxL2tpPeerStatEntry
    MAX-ACCESS  not-accessible
    STATUS      current
    DESCRIPTION
        "Each row entry represents status and statistics information about
         a particular L2TP peer.

         Rows are created or removed automatically by the system."
    INDEX { vRtrID,
            tmnxL2tpTuStatusTransportType,
            tmnxL2tpTuStatusPeerAddrType,
            tmnxL2tpTuStatusPeerAddr,
            tmnxL2tpTuStatusRemoteUdpPort
    }
    ::= { tmnxL2tpPeerStatTable 1 }

TmnxL2tpPeerStatEntry ::= 
    SEQUENCE {
        tmnxL2tpPeerStatRole             INTEGER,
        tmnxL2tpPeerStatActiveTunnels    Gauge32,
        tmnxL2tpPeerStatTunnels          Gauge32,
        tmnxL2tpPeerStatActiveSessions   Gauge32,
        tmnxL2tpPeerStatSessions         Gauge32,
        tmnxL2tpPeerStatDraining         TruthValue,
        tmnxL2tpPeerStatUnreachable      INTEGER,
        tmnxL2tpPeerStatUnreachableTime  TimeStamp,
        tmnxL2tpPeerStatControlRxOct     Counter64,
        tmnxL2tpPeerStatControlRxOctLw   Counter32,
        tmnxL2tpPeerStatControlRxOctHw   Counter32,
        tmnxL2tpPeerStatControlRxPkts    Counter32,
        tmnxL2tpPeerStatControlTxOct     Counter64,
        tmnxL2tpPeerStatControlTxOctLw   Counter32,
        tmnxL2tpPeerStatControlTxOctHw   Counter32,
        tmnxL2tpPeerStatControlTxPkts    Counter32,
        tmnxL2tpPeerStatErrorTxPkts      Counter32,
        tmnxL2tpPeerStatErrorRxPkts      Counter32,
        tmnxL2tpPeerStatMsgAccepted      Counter32,
        tmnxL2tpPeerStatMsgDuplicateRx   Counter32,
        tmnxL2tpPeerStatMsgOutOfWndwRx   Counter32,
        tmnxL2tpPeerStatRolesCapability  TmnxL2tpRoles,
        tmnxL2tpPeerStatRoles            TmnxL2tpRoles,
        tmnxL2tpPeerStatUnreachTimeRem   Unsigned32,
        tmnxL2tpPeerStatLastCleared      TimeStamp
    }

tmnxL2tpPeerStatRole   OBJECT-TYPE
    SYNTAX      INTEGER {
                    roleLAC (1),
                    roleLNS (2)
                }
    MAX-ACCESS  read-only
    STATUS      obsolete
    DESCRIPTION
       "The value of tmnxL2tpPeerStatRole indicates the
        role of this system in relation to the peer."
    ::= { tmnxL2tpPeerStatEntry 1 }

tmnxL2tpPeerStatActiveTunnels   OBJECT-TYPE
    SYNTAX      Gauge32
    MAX-ACCESS  read-only
    STATUS      current
    DESCRIPTION
        "The value of tmnxL2tpPeerStatActiveTunnels indicates 
         the number of tunnels associated with this peer that are 
         currently established."
    ::= { tmnxL2tpPeerStatEntry 2 }

tmnxL2tpPeerStatTunnels   OBJECT-TYPE
    SYNTAX      Gauge32
    MAX-ACCESS  read-only
    STATUS      current
    DESCRIPTION
        "The value of tmnxL2tpPeerStatTunnels indicates 
         the actual number of tunnels associated with this peer."
    ::= { tmnxL2tpPeerStatEntry 3 }
tmnxL2tpPeerStatActiveSessions  OBJECT-TYPE
    SYNTAX      Gauge32
    MAX-ACCESS  read-only
    STATUS      current
    DESCRIPTION
        "The value of tmnxL2tpPeerStatActiveSessions indicates 
         the number of sessions associated with this peer that are
         currently established."
    ::= { tmnxL2tpPeerStatEntry 4 }

tmnxL2tpPeerStatSessions  OBJECT-TYPE
    SYNTAX      Gauge32
    MAX-ACCESS  read-only
    STATUS      current
    DESCRIPTION
        "The value of tmnxL2tpPeerStatSessions indicates 
         the actual number of sessions associated with this peer."
    ::= { tmnxL2tpPeerStatEntry 5 }

tmnxL2tpPeerStatDraining   OBJECT-TYPE
    SYNTAX      TruthValue
    MAX-ACCESS  read-only
    STATUS      current
    DESCRIPTION
       "The value of tmnxL2tpPeerStatDraining indicates 
        if this peer is being drained."
    ::= { tmnxL2tpPeerStatEntry 6 }

tmnxL2tpPeerStatUnreachable   OBJECT-TYPE
    SYNTAX      INTEGER {
                 unreachable (1),
                 reachable   (2),
                 selectable  (3),
                 blacklisted (4)
            }
    MAX-ACCESS  read-only
    STATUS      current
    DESCRIPTION
       "The value of tmnxL2tpPeerStatUnreachable indicates if this 
        tunnel is deemed reachable or not.

        A value of 'blacklisted(4)' indicates the peer has been deemed
        unreachable and has been put in the tunnel-selection-blacklist.

        A value of 'selectable(2)' indicates the peer has been deemed
        unreachable for the time specified in tmnxL2tpXtTuSelBlacklistMaxTime
        and can now be selected for a single session, after which the
        reachability of the peer will be reevaluated."
    ::= { tmnxL2tpPeerStatEntry 7 }

tmnxL2tpPeerStatUnreachableTime OBJECT-TYPE
    SYNTAX      TimeStamp
    MAX-ACCESS  read-only
    STATUS      current
    DESCRIPTION 
       "The value of the object tmnxL2tpPeerStatUnreachableTime indicates
        the value of sysUpTime when the this peer was deemed unreachable
        for the last time.
         
        The value zero means that this peer has not been deemed unreachable yet."
    ::= { tmnxL2tpPeerStatEntry 8 }

tmnxL2tpPeerStatControlRxOct OBJECT-TYPE
    SYNTAX      Counter64
    MAX-ACCESS  read-only
    STATUS      current
    DESCRIPTION
       "The value of tmnxL2tpPeerStatControlRxOct indicates
        the number of control channel octets received in this tunnel
        since the last re-initialization of the local network 
        management subsystem, or the last time the tunnel statistics were 
        cleared."
    ::= { tmnxL2tpPeerStatEntry 9 }

tmnxL2tpPeerStatControlRxOctLw OBJECT-TYPE
    SYNTAX      Counter32
    MAX-ACCESS  read-only
    STATUS      current
    DESCRIPTION
       "The value of tmnxL2tpPeerStatControlRxOctLw indicates
        the lower 32-bits word of the value of tmnxL2tpPeerStatControlRxOct."
    ::= { tmnxL2tpPeerStatEntry 10 }

tmnxL2tpPeerStatControlRxOctHw OBJECT-TYPE
    SYNTAX      Counter32
    MAX-ACCESS  read-only
    STATUS      current
    DESCRIPTION
       "The value of tmnxL2tpPeerStatControlRxOctHw indicates
        the higher 32-bits word of the value of tmnxL2tpPeerStatControlRxOct."
    ::= { tmnxL2tpPeerStatEntry 11 }

tmnxL2tpPeerStatControlRxPkts OBJECT-TYPE
    SYNTAX      Counter32
    MAX-ACCESS  read-only
    STATUS      current
    DESCRIPTION
       "The value of tmnxL2tpPeerStatControlRxPkts indicates
        the number of control packets received by this tunnel
        since the last re-initialization of the local network 
        management subsystem, or the last time the tunnel statistics were 
        cleared."
    ::= { tmnxL2tpPeerStatEntry 12 }

tmnxL2tpPeerStatControlTxOct OBJECT-TYPE
    SYNTAX      Counter64
    MAX-ACCESS  read-only
    STATUS      current
    DESCRIPTION
       "The value of tmnxL2tpPeerStatControlTxOct indicates
        the number of control channel octets that were transmitted  
        to the current tunnel endpoints in this tunnel
        since the last re-initialization of the local network 
        management subsystem, or the last time the tunnel statistics were 
        cleared."
    ::= { tmnxL2tpPeerStatEntry 13 }

tmnxL2tpPeerStatControlTxOctLw OBJECT-TYPE
    SYNTAX      Counter32
    MAX-ACCESS  read-only
    STATUS      current
    DESCRIPTION
       "The value of tmnxL2tpPeerStatControlTxOctLw indicates
        the lower 32-bits word of the value of tmnxL2tpPeerStatControlTxOct."
    ::= { tmnxL2tpPeerStatEntry 14 }

tmnxL2tpPeerStatControlTxOctHw OBJECT-TYPE
    SYNTAX      Counter32
    MAX-ACCESS  read-only
    STATUS      current
    DESCRIPTION
       "The value of tmnxL2tpPeerStatControlTxOctHw indicates
        the higher 32-bits word of the value of tmnxL2tpPeerStatControlTxOct."
    ::= { tmnxL2tpPeerStatEntry 15 }

tmnxL2tpPeerStatControlTxPkts OBJECT-TYPE
    SYNTAX      Counter32
    MAX-ACCESS  read-only
    STATUS      current
    DESCRIPTION
       "The value of tmnxL2tpPeerStatControlTxOct indicates
        the number of control packets that were transmitted to 
        the current tunnel endpoints in this tunnel
        since the last re-initialization of the local network 
        management subsystem, or the last time the tunnel statistics were 
        cleared."
    ::= { tmnxL2tpPeerStatEntry 16 }

tmnxL2tpPeerStatErrorTxPkts OBJECT-TYPE
    SYNTAX      Counter32
    MAX-ACCESS  read-only
    STATUS      current
    DESCRIPTION
       "The value of tmnxL2tpPeerStatErrorTxPkts indicates
        the number of packet transmission errors on this tunnel
        since the last re-initialization of the local network 
        management subsystem, or the last time the tunnel statistics were 
        cleared."
    ::= { tmnxL2tpPeerStatEntry 17 }

tmnxL2tpPeerStatErrorRxPkts OBJECT-TYPE
    SYNTAX      Counter32
    MAX-ACCESS  read-only
    STATUS      current
    DESCRIPTION
       "The value of tmnxL2tpPeerStatErrorRxPkts indicates
        the number of errored packets that were received on this tunnel
        since the last re-initialization of the local network 
        management subsystem, or the last time the tunnel statistics were 
        cleared."
    ::= { tmnxL2tpPeerStatEntry 18 }

tmnxL2tpPeerStatMsgAccepted OBJECT-TYPE
    SYNTAX      Counter32
    MAX-ACCESS  read-only
    STATUS      current
    DESCRIPTION
       "The value of tmnxL2tpPeerStatMsgAccepted indicates
        the number of Finite State Machine (FSM) messages
        that were accepted from this peer
        since the last re-initialization of the local network 
        management subsystem, or the last time the tunnel statistics were 
        cleared."
    ::= { tmnxL2tpPeerStatEntry 19 }

tmnxL2tpPeerStatMsgDuplicateRx OBJECT-TYPE
    SYNTAX      Counter32
    MAX-ACCESS  read-only
    STATUS      current
    DESCRIPTION
       "The value of tmnxL2tpPeerStatMsgDuplicateRx indicates
        the number of Finite State Machine (FSM) duplicate messages
        that were received from this peer
        since the last re-initialization of the local network 
        management subsystem, or the last time the tunnel statistics were 
        cleared."
    ::= { tmnxL2tpPeerStatEntry 20 }

tmnxL2tpPeerStatMsgOutOfWndwRx OBJECT-TYPE
    SYNTAX      Counter32
    MAX-ACCESS  read-only
    STATUS      current
    DESCRIPTION
       "The value of tmnxL2tpPeerStatMsgOutOfWndwRx indicates
        the number of Finite State Machine (FSM) messages
        that were received out of the receive window from this peer
        since the last re-initialization of the local network 
        management subsystem, or the last time the tunnel statistics were 
        cleared."
    ::= { tmnxL2tpPeerStatEntry 21 }

tmnxL2tpPeerStatRolesCapability   OBJECT-TYPE
    SYNTAX      TmnxL2tpRoles
    MAX-ACCESS  read-only
    STATUS      current
    DESCRIPTION
       "The value of tmnxL2tpPeerStatRolesCapability indicates the
        roles that this system could perform in relation to the peer."
    ::= { tmnxL2tpPeerStatEntry 22 }

tmnxL2tpPeerStatRoles   OBJECT-TYPE
    SYNTAX      TmnxL2tpRoles
    MAX-ACCESS  read-only
    STATUS      current
    DESCRIPTION
       "The value of tmnxL2tpPeerStatRole indicates the
        actual roles of this system in relation to the peer."
    ::= { tmnxL2tpPeerStatEntry 23 }

tmnxL2tpPeerStatUnreachTimeRem OBJECT-TYPE
    SYNTAX      Unsigned32
    UNITS       "seconds"
    MAX-ACCESS  read-only
    STATUS      current
    DESCRIPTION
       "The value of tmnxL2tpPeerStatUnreachTimeRem indicates the remaining
        time the peer will remain in the tunnel-selection-blacklist.

        If the peer is currently not in the tunnel-selection-blacklist,
        tmnxL2tpPeerStatUnreachTimeRem will be set to zero."
    ::= { tmnxL2tpPeerStatEntry 24 }
        
tmnxL2tpPeerStatLastCleared OBJECT-TYPE
    SYNTAX      TimeStamp
    MAX-ACCESS  read-only
    STATUS      current
    DESCRIPTION 
       "The value of the object tmnxL2tpPeerStatLastCleared indicates
        the value of sysUpTime when the contents of this conceptual row were 
        cleared for the last time.
         
        The value zero means that the contents of this conceptual row have not 
        yet been cleared."
    ::= { tmnxL2tpPeerStatEntry 99 }
    
--
--      The L2TP Peer Tunnels Table
--

tmnxL2tpPeerTuTable   OBJECT-TYPE
    SYNTAX      SEQUENCE OF TmnxL2tpPeerTuEntry
    MAX-ACCESS  not-accessible
    STATUS      current
    DESCRIPTION
       "The tmnxL2tpPeerTuTable contains the set of active tunnels for each
        L2TP peer."
    ::= { tmnxL2tpPeerStatObjs 2 }

tmnxL2tpPeerTuEntry   OBJECT-TYPE
    SYNTAX      TmnxL2tpPeerTuEntry
    MAX-ACCESS  not-accessible
    STATUS      current
    DESCRIPTION
        "Each row entry contains a tunnel identifier of an L2TP peer.

         Rows are created or removed automatically by the system."
    INDEX { vRtrID,
            tmnxL2tpTuStatusTransportType,
            tmnxL2tpTuStatusPeerAddrType,
            tmnxL2tpTuStatusPeerAddr,
            tmnxL2tpTuStatusRemoteUdpPort,
            tmnxL2tpPeerTuId
    }
    ::= { tmnxL2tpPeerTuTable 1 }

TmnxL2tpPeerTuEntry ::= 
    SEQUENCE {
        tmnxL2tpPeerTuId                 TmnxL2tpConnectionId
    }

tmnxL2tpPeerTuId OBJECT-TYPE
    SYNTAX      TmnxL2tpConnectionId
    MAX-ACCESS  read-only
    STATUS      current
    DESCRIPTION
       "The value of the object tmnxL2tpPeerTuId indicates the local  
        identifier of a Layer Two Tunneling Protocol Tunnel."
    ::= { tmnxL2tpPeerTuEntry 1 }

--
--      The L2TP Peer Protocol Statistics Table
--

tmnxL2tpPeerProtStatsTable   OBJECT-TYPE
    SYNTAX      SEQUENCE OF TmnxL2tpPeerProtStatsEntry
    MAX-ACCESS  not-accessible
    STATUS      current
    DESCRIPTION
       "The tmnxL2tpPeerProtStatsTable contains protocol statistics information
        about L2TP peers."
    ::= { tmnxL2tpPeerStatObjs 3 }

tmnxL2tpPeerProtStatsEntry   OBJECT-TYPE
    SYNTAX      TmnxL2tpPeerProtStatsEntry
    MAX-ACCESS  not-accessible
    STATUS      current
    DESCRIPTION
       "Each conceptual row represents protocol statistics of a specific type
        for a specific L2TP peer.

        Entries in this table are created and destroyed by the system.
         
        Rows are only created where the statistics value is nonzero;
        this allows faster walking through this table; hence, it is recommended
        to perform only get-next-request operations to retrieve information
        from this table."
    INDEX { vRtrID,
        tmnxL2tpPeerProtStatsTransport,
        tmnxL2tpPeerProtStatsAddrType,
        tmnxL2tpPeerProtStatsAddr,
        tmnxL2tpPeerProtStatsRemUdpPort,
        tmnxL2tpPeerProtStatsType,
        tmnxL2tpPeerProtStatsInstance
    }
    ::= { tmnxL2tpPeerProtStatsTable 1 }

TmnxL2tpPeerProtStatsEntry ::= 
    SEQUENCE {
        tmnxL2tpPeerProtStatsTransport   TmnxL2tpTransportType,
        tmnxL2tpPeerProtStatsAddrType    InetAddressType,     
        tmnxL2tpPeerProtStatsAddr        InetAddress,         
        tmnxL2tpPeerProtStatsRemUdpPort  InetPortNumber, 
        tmnxL2tpPeerProtStatsType        TmnxL2tpTuProtStatsType,
        tmnxL2tpPeerProtStatsInstance    Unsigned32,
        tmnxL2tpPeerProtStatsName        DisplayString,
        tmnxL2tpPeerProtStatsVal         Counter32
    }

tmnxL2tpPeerProtStatsTransport OBJECT-TYPE
    SYNTAX      TmnxL2tpTransportType
    MAX-ACCESS  not-accessible
    STATUS      current
    DESCRIPTION
       "The value of the object tmnxL2tpTuStatusTransportType indicates
        the transport type used for the messages to this L2TP peer."
    ::= { tmnxL2tpPeerProtStatsEntry 1 }

tmnxL2tpPeerProtStatsAddrType OBJECT-TYPE
    SYNTAX      InetAddressType
    MAX-ACCESS  not-accessible
    STATUS      current
    DESCRIPTION 
       "The value of tmnxL2tpPeerProtStatsAddrType indicates the
        address type of tmnxL2tpPeerProtStatsAddr."
    ::= { tmnxL2tpPeerProtStatsEntry 2 }

tmnxL2tpPeerProtStatsAddr OBJECT-TYPE
    SYNTAX      InetAddress (SIZE(0|4|16))
    MAX-ACCESS  not-accessible
    STATUS      current
    DESCRIPTION 
       "The value of tmnxL2tpPeerProtStatsAddr indicates the IP
        address of the peer."
    ::= { tmnxL2tpPeerProtStatsEntry 3 }

tmnxL2tpPeerProtStatsRemUdpPort OBJECT-TYPE
    SYNTAX      InetPortNumber
    MAX-ACCESS  not-accessible
    STATUS      current
    DESCRIPTION 
       "The value of the object tmnxL2tpPeerProtStatsRemUdpPort indicates the  
        UDP port used by the tunnel peer."
    ::= { tmnxL2tpPeerProtStatsEntry 4 }

tmnxL2tpPeerProtStatsType OBJECT-TYPE
    SYNTAX      TmnxL2tpTuProtStatsType
    MAX-ACCESS  not-accessible
    STATUS      current
    DESCRIPTION 
       "The value of the object tmnxL2tpPeerProtStatsType indicates
        the type of L2TP protocol statistics contained in this conceptual row."
    ::= { tmnxL2tpPeerProtStatsEntry 5 }

tmnxL2tpPeerProtStatsInstance OBJECT-TYPE
    SYNTAX      Unsigned32 (0..49)
    MAX-ACCESS  not-accessible
    STATUS      current
    DESCRIPTION 
       "The value of the object tmnxL2tpPeerProtStatsInstance indicates
        the instance identifier of the statistics 
        contained in this conceptual row.
        
        For example: if the value of the object tmnxL2tpPeerProtStatsType is 
        equal to 'outgoingMsgType', the value of tmnxL2tpPeerProtStatsInstance  
        is a message identifier, 
        e.g. instance '2' refers to '(SCCRP) Start-Control-Connection-Reply', 
        and the value of tmnxL2tpPeerProtStatsVal indicates the number of SCCRP 
        messages transmitted for this tunnel.
        
        Unknown protocol messages are counted with instance zero."
    ::= { tmnxL2tpPeerProtStatsEntry 6 }

tmnxL2tpPeerProtStatsName OBJECT-TYPE
    SYNTAX      DisplayString (SIZE (1..64))
    MAX-ACCESS  read-only
    STATUS      current
    DESCRIPTION 
       "The value of the object tmnxL2tpPeerProtStatsName indicates
        the human-readable identifier of the statistics 
        contained in this conceptual row.
        
        In the same example, the value of tmnxL2tpPeerProtStatsName is 
        '(SCCRP) Start-Control-Connection-Reply'."
    ::= { tmnxL2tpPeerProtStatsEntry 7 }

tmnxL2tpPeerProtStatsVal OBJECT-TYPE
    SYNTAX      Counter32
    MAX-ACCESS  read-only
    STATUS      current
    DESCRIPTION 
       "The value of the object tmnxL2tpPeerProtStatsVal indicates
        the value of the statistics contained in this conceptual row."
    ::= { tmnxL2tpPeerProtStatsEntry 8 }


--
--      The L2TP Peer Operations Drain Table
--

tmnxL2tpPeerDrainTable   OBJECT-TYPE
    SYNTAX      SEQUENCE OF TmnxL2tpPeerDrainEntry
    MAX-ACCESS  not-accessible
    STATUS      current
    DESCRIPTION
       "The tmnxL2tpPeerDrainTable has an entry for each
        L2TP peer."
    ::= { tmnxL2tpPeerOpObjs 1 }

tmnxL2tpPeerDrainEntry   OBJECT-TYPE
    SYNTAX      TmnxL2tpPeerDrainEntry
    MAX-ACCESS  not-accessible
    STATUS      current
    DESCRIPTION
        "Each row entry presents an operations interface to drain all
         tunnels between this system and a particular L2TP peer.

         Rows are created or removed automatically by the system."
    INDEX { vRtrID,
            tmnxL2tpTuStatusTransportType,
            tmnxL2tpTuStatusPeerAddrType,
            tmnxL2tpTuStatusPeerAddr,
            tmnxL2tpTuStatusRemoteUdpPort
    }
    ::= { tmnxL2tpPeerDrainTable 1 }

TmnxL2tpPeerDrainEntry ::= 
    SEQUENCE {
        tmnxL2tpPeerDrain                TmnxL2tpActionTypeDrain
    }

tmnxL2tpPeerDrain OBJECT-TYPE
    SYNTAX      TmnxL2tpActionTypeDrain
    MAX-ACCESS  read-write
    STATUS      current
    DESCRIPTION
        "Setting this object to 'drain (0)' triggers 
         an attempt to drain all tunnels between this system 
         and a particular L2TP peer.

         Setting it to 'stopDrain (1)' stops the draining.

         Reading this object returns the value 'notApplicable'."
    DEFVAL { notApplicable }
    ::= { tmnxL2tpPeerDrainEntry 1 }

-- ----------------------------------------------------------------------------
--      The "L2TP Session" Group
-- ----------------------------------------------------------------------------

tmnxL2tpSeStatObjs           OBJECT IDENTIFIER   ::= { tmnxL2tpSessionObjs 1 }
tmnxL2tpSeOpObjs             OBJECT IDENTIFIER   ::= { tmnxL2tpSessionObjs 2 }

--
--      The L2TP Session Status Table
--

tmnxL2tpSeStatusTableLastCh OBJECT-TYPE
    SYNTAX      TimeStamp
    MAX-ACCESS  read-only
    STATUS      current
    DESCRIPTION
        "The value of the object tmnxL2tpSeStatusTableLastCh indicates
         the value of sysUpTime at the time of the last modification of
         an entry in the tmnxL2tpSeStatusTable."
    ::= { tmnxL2tpObjs 14 }

tmnxL2tpSeStatusTable   OBJECT-TYPE
    SYNTAX      SEQUENCE OF TmnxL2tpSeStatusEntry
    MAX-ACCESS  not-accessible
    STATUS      current
    DESCRIPTION
       "The tmnxL2tpSeStatusTable has an entry for each 
        Layer Two Tunneling Protocol Session."
    ::= { tmnxL2tpSeStatObjs 1 }

tmnxL2tpSeStatusEntry   OBJECT-TYPE
    SYNTAX      TmnxL2tpSeStatusEntry
    MAX-ACCESS  not-accessible
    STATUS      current
    DESCRIPTION
       "Each conceptual row represents a Layer Two Tunneling Protocol
        Session.

        Entries in this table are created and destroyed by the system."
    INDEX { vRtrID,
            tmnxL2tpSeStatusId }
    ::= { tmnxL2tpSeStatusTable 1 }

TmnxL2tpSeStatusEntry ::= 
    SEQUENCE {
        tmnxL2tpSeStatusId               TmnxL2tpConnectionId,
        tmnxL2tpSeStatusState            TmnxL2tpSeOperState,
        tmnxL2tpSeStatusTunnelId         TmnxL2tpTunnelId,
        tmnxL2tpSeStatusTunnelConnId     TmnxL2tpConnectionId,
        tmnxL2tpSeStatusSessionId        TmnxL2tpSessionId,
        tmnxL2tpSeStatusRemoteTunnelId   TmnxL2tpTunnelId,
        tmnxL2tpSeStatusRemoteSessionId  TmnxL2tpSessionId,
        tmnxL2tpSeStatusRemoteConnId     TmnxL2tpConnectionId,
        tmnxL2tpSeStatusStartTime        TimeStamp,
        tmnxL2tpSeStatusEstabTime        TimeStamp,
        tmnxL2tpSeStatusClosedTime       TimeStamp,
        tmnxL2tpSeStatusCdnResult        TmnxL2tpCdnResult,
        tmnxL2tpSeStatusGeneralError     TmnxL2tpGeneralError,
        tmnxL2tpSeStatusErrorMessage     TmnxL2tpErrorMessage,
        tmnxL2tpSeStatusMlpppBundleIndex Unsigned32
    }
        
tmnxL2tpSeStatusId OBJECT-TYPE
    SYNTAX      TmnxL2tpConnectionId
    MAX-ACCESS  not-accessible
    STATUS      current
    DESCRIPTION
       "The value of the object tmnxL2tpSeStatusId indicates the local  
        identifier of this Layer Two Tunneling Protocol Session.
        
        In L2TP version 2, it contains the 16-bit session ID in the lower order 
        bits and the 16-bit tunnel ID in the higher order bits.
        
        In L2TP version 3, it is the 32-bit session ID."
    ::= { tmnxL2tpSeStatusEntry 1 }

tmnxL2tpSeStatusState OBJECT-TYPE
    SYNTAX      TmnxL2tpSeOperState
    MAX-ACCESS  read-only
    STATUS      current
    DESCRIPTION
       "The value of tmnxL2tpSeStatusState indicates the
        operational state of this Layer Two Tunneling Protocol Session."
    ::= { tmnxL2tpSeStatusEntry 2 }

tmnxL2tpSeStatusTunnelId OBJECT-TYPE
    SYNTAX      TmnxL2tpTunnelId
    MAX-ACCESS  read-only
    STATUS      current
    DESCRIPTION
       "The value of the object tmnxL2tpSeStatusTunnelId indicates the  
        identifier of the L2TP tunnel associated with this Layer Two Tunneling 
        Protocol Session, when L2TP version 2 is used.
        
        In L2TP version 3, it is equal to zero."
    ::= { tmnxL2tpSeStatusEntry 3 }

tmnxL2tpSeStatusTunnelConnId OBJECT-TYPE
    SYNTAX      TmnxL2tpConnectionId
    MAX-ACCESS  read-only
    STATUS      current
    DESCRIPTION
       "The value of the object tmnxL2tpSeStatusTunnelConnId indicates the  
        identifier of the L2TP tunnel associated with this Layer Two Tunneling 
        Protocol Session."
    ::= { tmnxL2tpSeStatusEntry 4 }

tmnxL2tpSeStatusSessionId OBJECT-TYPE
    SYNTAX      TmnxL2tpSessionId
    MAX-ACCESS  read-only
    STATUS      current
    DESCRIPTION
       "The value of the object tmnxL2tpSeStatusSessionId indicates the  
        identifier of this Layer Two Tunneling Protocol Session, when L2TP 
        version 2 is used.
        
        In L2TP version 3, it is equal to zero."
    ::= { tmnxL2tpSeStatusEntry 5 }

tmnxL2tpSeStatusRemoteTunnelId OBJECT-TYPE
    SYNTAX      TmnxL2tpTunnelId
    MAX-ACCESS  read-only
    STATUS      current
    DESCRIPTION
       "The value of the object tmnxL2tpSeStatusRemoteTunnelId indicates the  
        identifier used by the tunnel peer of the L2TP tunnel associated with 
        this Layer Two Tunneling Protocol Session , when L2TP version 2 is used.
        
        In L2TP version 3, it is equal to zero."
    ::= { tmnxL2tpSeStatusEntry 6 }

tmnxL2tpSeStatusRemoteSessionId OBJECT-TYPE
    SYNTAX      TmnxL2tpSessionId
    MAX-ACCESS  read-only
    STATUS      current
    DESCRIPTION
       "The value of the object tmnxL2tpSeStatusRemoteSessionId indicates the  
        identifier of this Layer Two Tunneling Protocol Session used by the 
        tunnel peer, when L2TP version 2 is used.
        
        In L2TP version 3, it is equal to zero."
    ::= { tmnxL2tpSeStatusEntry 7 }

tmnxL2tpSeStatusRemoteConnId OBJECT-TYPE
    SYNTAX      TmnxL2tpConnectionId
    MAX-ACCESS  read-only
    STATUS      current
    DESCRIPTION
       "The value of the object tmnxL2tpSeStatusRemoteConnId indicates the  
        identifier of this Layer Two Tunneling Protocol Session used by the 
        tunnel peer."
    ::= { tmnxL2tpSeStatusEntry 8 }

tmnxL2tpSeStatusStartTime OBJECT-TYPE
    SYNTAX      TimeStamp
    MAX-ACCESS  read-only
    STATUS      current
    DESCRIPTION 
        "The value of the object tmnxL2tpSeStatusStartTime indicates
         the value of sysUpTime when this Layer Two Tunneling Protocol Session
         entered either the state 'idle', 'waitTunnel', 'waitReply' or
         'waitAcceptance'."
    ::= { tmnxL2tpSeStatusEntry 9 }

tmnxL2tpSeStatusEstabTime OBJECT-TYPE
    SYNTAX      TimeStamp
    MAX-ACCESS  read-only
    STATUS      current
    DESCRIPTION 
        "The value of the object tmnxL2tpSeStatusEstabTime indicates
         the value of sysUpTime when this Layer Two Tunneling Protocol Session
         entered the state 'established'.
         
         The value zero means that this session has not been established yet."
    ::= { tmnxL2tpSeStatusEntry 10 }

tmnxL2tpSeStatusClosedTime OBJECT-TYPE
    SYNTAX      TimeStamp
    MAX-ACCESS  read-only
    STATUS      current
    DESCRIPTION 
        "The value of the object tmnxL2tpSeStatusClosedTime indicates
         the value of sysUpTime when this Layer Two Tunneling Protocol Session
         entered one of the closed states.
         
         The value zero means that this session has not been closed yet."
    ::= { tmnxL2tpSeStatusEntry 11 }

tmnxL2tpSeStatusCdnResult OBJECT-TYPE
    SYNTAX      TmnxL2tpCdnResult
    MAX-ACCESS  read-only
    STATUS      current
    DESCRIPTION
       "The value of tmnxL2tpSeStatusCdnResult indicates
        the result of a CDN (Call-Disconnect-Notify) message 
        related to this Layer Two Tunneling Protocol Session."
    REFERENCE
       "RFC 2661 Layer Two Tunneling Protocol 'L2TP', 
        section 4.4.2 Result and Error Codes."
        ::= { tmnxL2tpSeStatusEntry 12 }

tmnxL2tpSeStatusGeneralError OBJECT-TYPE
    SYNTAX      TmnxL2tpGeneralError
    MAX-ACCESS  read-only
    STATUS      current
    DESCRIPTION
       "The value of tmnxL2tpSeStatusGeneralError indicates
        an general error related to this Layer Two Tunneling Protocol Session."
    REFERENCE
       "RFC 2661 Layer Two Tunneling Protocol 'L2TP', 
        section 4.4.2 Result and Error Codes."
        ::= { tmnxL2tpSeStatusEntry 13 }

tmnxL2tpSeStatusErrorMessage OBJECT-TYPE
    SYNTAX      TmnxL2tpErrorMessage
    MAX-ACCESS  read-only
    STATUS      current
    DESCRIPTION
       "The value of the object tmnxL2tpSeStatusErrorMessage
        describes an error related to this Layer Two Tunneling Protocol 
        Session."
    REFERENCE
       "RFC 2661 Layer Two Tunneling Protocol 'L2TP', 
        section 4.4.2 Result and Error Codes."
    ::= { tmnxL2tpSeStatusEntry 14 }

tmnxL2tpSeStatusMlpppBundleIndex OBJECT-TYPE
    SYNTAX      Unsigned32
    MAX-ACCESS  read-only
    STATUS      current
    DESCRIPTION
       "The value of the object tmnxL2tpSeStatusMlpppBundleIndex indicates
        the identifier of the MLPPP Bundle related to this 
        Layer Two Tunneling Protocol Session.
        
        If an MLPPP bundle is associated with this session, the value  
        of tmnxL2tpSeStatusMlpppBundleIndex is equal to the value 
        of tmnxL2tpLacMlpppBundleIndex of the corresponding row in the
        tmnxL2tpLacMlpppBundleTable, in the same virtual router instance.
        
        If no MLPPP bundle is associated with this session, the value of
        this object is equal to zero."
    ::= { tmnxL2tpSeStatusEntry 20 }

--
--      The L2TP LNS Session PPP Status Table
--

tmnxL2tpLnsSePppTableLastCh OBJECT-TYPE
    SYNTAX      TimeStamp
    MAX-ACCESS  read-only
    STATUS      current
    DESCRIPTION
        "The value of the object tmnxL2tpLnsSePppTableLastCh indicates
         the value of sysUpTime at the time of the last update of
         an entry in the tmnxL2tpLnsSePppTable."
    ::= { tmnxL2tpObjs 20 }

tmnxL2tpLnsSePppTable   OBJECT-TYPE
    SYNTAX      SEQUENCE OF TmnxL2tpLnsSePppEntry
    MAX-ACCESS  not-accessible
    STATUS      current
    DESCRIPTION
       "The tmnxL2tpLnsSePppTable has an entry for each 
        Layer Two Tunneling Protocol Session for which this system acts as LNS."
    ::= { tmnxL2tpSeStatObjs 2 }

tmnxL2tpLnsSePppEntry   OBJECT-TYPE
    SYNTAX      TmnxL2tpLnsSePppEntry
    MAX-ACCESS  not-accessible
    STATUS      current
    DESCRIPTION
       "Each conceptual row represents a Layer Two Tunneling Protocol
        Session.

        Entries in this table are created and destroyed by the system.
        
        In release 9.0 and higher, this information
        is in the SUBSCRIBER-MGMT-MIB::tmnxSubPppTable.
        
        The corresponding row in that table can be directly retrieved using
        the value of the object tmnxL2tpLnsSePppSubPppIndex."
    INDEX { vRtrID,
            tmnxL2tpSeStatusId }
    ::= { tmnxL2tpLnsSePppTable 1 }

TmnxL2tpLnsSePppEntry ::= 
    SEQUENCE {
        tmnxL2tpLnsSePppUpTime           TimeTicks,
        tmnxL2tpLnsSePppLcpState         TmnxPppCpState,
        tmnxL2tpLnsSePppIpcpState        TmnxPppCpState,
        tmnxL2tpLnsSePppPppMtu           Unsigned32,
        tmnxL2tpLnsSePppPppAuthProtocol  INTEGER,
        tmnxL2tpLnsSePppPppUserName      TmnxPppoeUserNameOrEmpty,
        tmnxL2tpLnsSePppSubIdent         TmnxSubIdentStringOrEmpty,
        tmnxL2tpLnsSePppOriginSubIdent   TmnxPppoeSessionInfoOrigin,
        tmnxL2tpLnsSePppSubProfString    TmnxSubProfileStringOrEmpty,
        tmnxL2tpLnsSePppSlaProfString    TmnxSlaProfileStringOrEmpty,
        tmnxL2tpLnsSePppAncpString       TmnxAncpStringOrZero,
        tmnxL2tpLnsSePppInterDestId      TmnxSubMgtIntDestIdOrEmpty,
        tmnxL2tpLnsSePppAppProfString    TmnxAppProfileStringOrEmpty,
        tmnxL2tpLnsSePppOriginStrings    TmnxPppoeSessionInfoOrigin,
        tmnxL2tpLnsSePppSessionTimeout   Unsigned32,
        tmnxL2tpLnsSePppIpAddrType       InetAddressType,
        tmnxL2tpLnsSePppIpAddr           InetAddress,
        tmnxL2tpLnsSePppPrimaryDnsType   InetAddressType,
        tmnxL2tpLnsSePppPrimaryDns       InetAddress,
        tmnxL2tpLnsSePppSecondaryDnsType InetAddressType,
        tmnxL2tpLnsSePppSecondaryDns     InetAddress,
        tmnxL2tpLnsSePppPrimaryNbnsType  InetAddressType,
        tmnxL2tpLnsSePppPrimaryNbns      InetAddress,
        tmnxL2tpLnsSePppSecondNbnsType   InetAddressType,
        tmnxL2tpLnsSePppSecondNbns       InetAddress,
        tmnxL2tpLnsSePppOriginIpcpInfo   TmnxPppoeSessionInfoOrigin,
        tmnxL2tpLnsSePppCircuitId        OCTET STRING,
        tmnxL2tpLnsSePppRemoteId         OCTET STRING,
        tmnxL2tpLnsSePppAddressPool      DisplayString,
        tmnxL2tpLnsSePppType             TmnxPppoeSessionType,
        tmnxL2tpLnsSePppSvcId            TmnxServId,
        tmnxL2tpLnsSePppGrpIf            InterfaceIndexOrZero,
        tmnxL2tpLnsSePppL2tpVrtrId       TmnxVRtrIDOrZero,
        tmnxL2tpLnsSePppL2tpConnectionId Unsigned32,
        tmnxL2tpLnsSePppCategoryMapName  TNamedItemOrEmpty,
        tmnxL2tpLnsSePppRadiusClassAttr  OCTET STRING,
        tmnxL2tpLnsSePppRadiusUserName   DisplayString,

        tmnxL2tpLnsSePppIpv6cpState      TmnxPppCpState,
        tmnxL2tpLnsSePppInterfaceId      OCTET STRING,
        tmnxL2tpLnsSePppOriginIpv6cpInfo TmnxPppoeSessionInfoOrigin,
        tmnxL2tpLnsSePppIpv6DnsType      InetAddressType,
        tmnxL2tpLnsSePppIpv6Dns1         InetAddress,
        tmnxL2tpLnsSePppIpv6Dns2         InetAddress,
        tmnxL2tpLnsSePppIpv6DelPfxType   InetAddressType,
        tmnxL2tpLnsSePppIpv6DelPfxLen    InetAddressPrefixLength,
        tmnxL2tpLnsSePppIpv6DelPfx       InetAddress,
        tmnxL2tpLnsSePppIpv6PrefixType   InetAddressType,
        tmnxL2tpLnsSePppIpv6PrefixLen    InetAddressPrefixLength,
        tmnxL2tpLnsSePppIpv6Prefix       InetAddress,
        tmnxL2tpLnsSePppSubPppIndex      Unsigned32
    }
        
tmnxL2tpLnsSePppUpTime OBJECT-TYPE
    SYNTAX      TimeTicks
    MAX-ACCESS  read-only
    STATUS      obsolete
    DESCRIPTION
        "The value of tmnxL2tpLnsSePppUpTime indicates how long (in hundredths
         of a second) that the session already exists in this table."
    ::= { tmnxL2tpLnsSePppEntry 3 }

tmnxL2tpLnsSePppLcpState OBJECT-TYPE
    SYNTAX      TmnxPppCpState
    MAX-ACCESS  read-only
    STATUS      obsolete
    DESCRIPTION
        "The value of tmnxL2tpLnsSePppLcpState indicates the current state of
         the PPP Link Control Protocol of the session."
    ::= { tmnxL2tpLnsSePppEntry 4 }

tmnxL2tpLnsSePppIpcpState OBJECT-TYPE
    SYNTAX      TmnxPppCpState
    MAX-ACCESS  read-only
    STATUS      obsolete
    DESCRIPTION
        "The value of tmnxL2tpLnsSePppIpcpState indicates the current state of
         the PPP IP Control Protocol of the session."
    ::= { tmnxL2tpLnsSePppEntry 5 }

tmnxL2tpLnsSePppPppMtu OBJECT-TYPE
    SYNTAX      Unsigned32
    UNITS       "bytes"
    MAX-ACCESS  read-only
    STATUS      obsolete
    DESCRIPTION
        "The value of tmnxL2tpLnsSePppPppMtu indicates the PPP MTU of the
         session."
    ::= { tmnxL2tpLnsSePppEntry 6 }

tmnxL2tpLnsSePppPppAuthProtocol OBJECT-TYPE
    SYNTAX      INTEGER {
                    none (1),
                    pap  (2),
                    chap (3)
                }
    MAX-ACCESS  read-only
    STATUS      obsolete
    DESCRIPTION
        "The value of tmnxL2tpLnsSePppPppAuthProtocol indicates the
         PPP protocol used to authenticate the session.

         The value 'none' indicates that no PPP authentication was done. The
         value 'pap' indicates that authentication was done via the Password
         Authentication Protocol. The value 'chap' indicates that
         authentication was done via the Challenge-Handshake Authentication
         Protocol."
    ::= { tmnxL2tpLnsSePppEntry 7 }

tmnxL2tpLnsSePppPppUserName OBJECT-TYPE
    SYNTAX      TmnxPppoeUserNameOrEmpty
    MAX-ACCESS  read-only
    STATUS      obsolete
    DESCRIPTION
        "The value of tmnxL2tpLnsSePppPppUserName indicates the user name
         learned during the PPP authentication phase."
    ::= { tmnxL2tpLnsSePppEntry 8 }

tmnxL2tpLnsSePppSubIdent OBJECT-TYPE
    SYNTAX      TmnxSubIdentStringOrEmpty
    MAX-ACCESS  read-only
    STATUS      obsolete
    DESCRIPTION
        "The value of tmnxL2tpLnsSePppSubIdent indicates the subscriber
         applicable for this session.

         The value of tmnxL2tpLnsSePppOriginSubIdent indicates from what
         source this subscriber identification was received."
    ::= { tmnxL2tpLnsSePppEntry 9 }

tmnxL2tpLnsSePppOriginSubIdent OBJECT-TYPE
    SYNTAX      TmnxPppoeSessionInfoOrigin
    MAX-ACCESS  read-only
    STATUS      obsolete
    DESCRIPTION
        "The value of tmnxL2tpLnsSePppOriginSubIdent indicates which source
         provided the subscriber."
    ::= { tmnxL2tpLnsSePppEntry 10 }

tmnxL2tpLnsSePppSubProfString OBJECT-TYPE
    SYNTAX      TmnxSubProfileStringOrEmpty
    MAX-ACCESS  read-only
    STATUS      obsolete
    DESCRIPTION
        "The value of tmnxL2tpLnsSePppSubProfString indicates the subscriber
         profile string applicable for this session.

         The value of tmnxL2tpLnsSePppOriginStrings indicates from what source
         this string was received."
    ::= { tmnxL2tpLnsSePppEntry 11 }

tmnxL2tpLnsSePppSlaProfString OBJECT-TYPE
    SYNTAX      TmnxSlaProfileStringOrEmpty
    MAX-ACCESS  read-only
    STATUS      obsolete
    DESCRIPTION
        "The value of tmnxL2tpLnsSePppSlaProfString indicates the SLA profile
         string applicable for this session.

         The value of tmnxL2tpLnsSePppOriginStrings indicates from what source
         this string was received."
    ::= { tmnxL2tpLnsSePppEntry 12 }

tmnxL2tpLnsSePppAncpString OBJECT-TYPE
    SYNTAX      TmnxAncpStringOrZero
    MAX-ACCESS  read-only
    STATUS      obsolete
    DESCRIPTION
        "The value of tmnxL2tpLnsSePppAncpString indicates the ANCP string
         applicable for this session.

         The value of tmnxL2tpLnsSePppOriginStrings indicates from what source
         this string was received."
    ::= { tmnxL2tpLnsSePppEntry 13 }

tmnxL2tpLnsSePppInterDestId OBJECT-TYPE
    SYNTAX      TmnxSubMgtIntDestIdOrEmpty
    MAX-ACCESS  read-only
    STATUS      obsolete
    DESCRIPTION
        "The value of tmnxL2tpLnsSePppInterDestId indicates the intermediate
         destination identifier applicable for this session.

         The value of tmnxL2tpLnsSePppOriginStrings indicates from what source
         this string was received."
    ::= { tmnxL2tpLnsSePppEntry 14 }

tmnxL2tpLnsSePppAppProfString OBJECT-TYPE
    SYNTAX      TmnxAppProfileStringOrEmpty
    MAX-ACCESS  read-only
    STATUS      obsolete
    DESCRIPTION
        "The value of tmnxL2tpLnsSePppAppProfString indicates the application
         profile string applicable for this session.

         The value of tmnxL2tpLnsSePppOriginStrings indicates from what source
         this string was received."
    ::= { tmnxL2tpLnsSePppEntry 15 }

tmnxL2tpLnsSePppOriginStrings OBJECT-TYPE
    SYNTAX      TmnxPppoeSessionInfoOrigin
    MAX-ACCESS  read-only
    STATUS      obsolete
    DESCRIPTION
        "The value of tmnxL2tpLnsSePppOriginStrings indicates which source
         provided the subscriber identification strings
         (subscriber profile string, SLA profile string, ANCP string,
         intermediate destination identifier and application profile string)."
    ::= { tmnxL2tpLnsSePppEntry 16 }

tmnxL2tpLnsSePppSessionTimeout OBJECT-TYPE
    SYNTAX      Unsigned32 (0..65535)
    UNITS       "seconds"
    MAX-ACCESS  read-only
    STATUS      obsolete
    DESCRIPTION
        "The value of tmnxL2tpLnsSePppSessionTimeout indicates the session
         timeout received from the Radius server (if applicable)."
    ::= { tmnxL2tpLnsSePppEntry 17 }

tmnxL2tpLnsSePppIpAddrType OBJECT-TYPE
    SYNTAX      InetAddressType
    MAX-ACCESS  read-only
    STATUS      obsolete
    DESCRIPTION
        "The value of tmnxL2tpLnsSePppIpAddrType indicates the address type of
         tmnxL2tpLnsSePppIpAddr."
    ::= { tmnxL2tpLnsSePppEntry 18 }

tmnxL2tpLnsSePppIpAddr OBJECT-TYPE
    SYNTAX      InetAddress (SIZE (0|4))
    MAX-ACCESS  read-only
    STATUS      obsolete
    DESCRIPTION
        "The value of tmnxL2tpLnsSePppIpAddr indicates the IP address of the
         session.

         The value of tmnxL2tpLnsSePppOriginIpcpInfo indicates from what
         source this IP address was received."
    ::= { tmnxL2tpLnsSePppEntry 19 }

tmnxL2tpLnsSePppPrimaryDnsType OBJECT-TYPE
    SYNTAX      InetAddressType
    MAX-ACCESS  read-only
    STATUS      obsolete
    DESCRIPTION
        "The value of tmnxL2tpLnsSePppPrimaryDnsType indicates the address
         type of tmnxL2tpLnsSePppPrimaryDns."
    ::= { tmnxL2tpLnsSePppEntry 20 }

tmnxL2tpLnsSePppPrimaryDns OBJECT-TYPE
    SYNTAX      InetAddress (SIZE (0|4))
    MAX-ACCESS  read-only
    STATUS      obsolete
    DESCRIPTION
        "The value of tmnxL2tpLnsSePppPrimaryDns indicates the primary DNS
         server.

         The value of this object is ''H when not applicable.

         The value of tmnxL2tpLnsSePppOriginIpcpInfo indicates from what
         source this IP address was received."
    ::= { tmnxL2tpLnsSePppEntry 21 }

tmnxL2tpLnsSePppSecondaryDnsType OBJECT-TYPE
    SYNTAX      InetAddressType
    MAX-ACCESS  read-only
    STATUS      obsolete
    DESCRIPTION
        "The value of tmnxL2tpLnsSePppSecondaryDnsType indicates the address
         type of tmnxL2tpLnsSePppSecondaryDns."
    ::= { tmnxL2tpLnsSePppEntry 22 }

tmnxL2tpLnsSePppSecondaryDns OBJECT-TYPE
    SYNTAX      InetAddress (SIZE (0|4))
    MAX-ACCESS  read-only
    STATUS      obsolete
    DESCRIPTION
        "The value of tmnxL2tpLnsSePppSecondaryDns indicates the secondary DNS
         server.

         The value of this object is ''H when not applicable.

         The value of tmnxL2tpLnsSePppOriginIpcpInfo indicates from what
         source this IP address was received."
    ::= { tmnxL2tpLnsSePppEntry 23 }

tmnxL2tpLnsSePppPrimaryNbnsType OBJECT-TYPE
    SYNTAX      InetAddressType
    MAX-ACCESS  read-only
    STATUS      obsolete
    DESCRIPTION
        "The value of tmnxL2tpLnsSePppPrimaryNbnsType indicates the address
         type of tmnxL2tpLnsSePppPrimaryNbns."
    ::= { tmnxL2tpLnsSePppEntry 24 }

tmnxL2tpLnsSePppPrimaryNbns OBJECT-TYPE
    SYNTAX      InetAddress (SIZE (0|4))
    MAX-ACCESS  read-only
    STATUS      obsolete
    DESCRIPTION
        "The value of tmnxL2tpLnsSePppPrimaryNbns indicates the primary NBNS
         server.

         The value of this object is ''H when not applicable.

         The value of tmnxL2tpLnsSePppOriginIpcpInfo indicates from what
         source this IP address was received."
    ::= { tmnxL2tpLnsSePppEntry 25 }

tmnxL2tpLnsSePppSecondNbnsType OBJECT-TYPE
    SYNTAX      InetAddressType
    MAX-ACCESS  read-only
    STATUS      obsolete
    DESCRIPTION
        "The value of tmnxL2tpLnsSePppSecondNbnsType indicates the address
         type of tmnxL2tpLnsSePppSecondNbns."
    ::= { tmnxL2tpLnsSePppEntry 26 }

tmnxL2tpLnsSePppSecondNbns OBJECT-TYPE
    SYNTAX      InetAddress (SIZE(0|4))
    MAX-ACCESS  read-only
    STATUS      obsolete
    DESCRIPTION
        "The value of tmnxL2tpLnsSePppSecondNbns indicates the secondary
         NBNS server.

         The value of this object is ''H when not applicable.

         The value of tmnxL2tpLnsSePppOriginIpcpInfo indicates from what
         source this IP address was received."
    ::= { tmnxL2tpLnsSePppEntry 27 }

tmnxL2tpLnsSePppOriginIpcpInfo OBJECT-TYPE
    SYNTAX      TmnxPppoeSessionInfoOrigin
    MAX-ACCESS  read-only
    STATUS      obsolete
    DESCRIPTION
        "The value of tmnxL2tpLnsSePppOriginIpcpInfo indicates which source
         provided the IPCP information (IP, DNS and NBNS addresses)."
    ::= { tmnxL2tpLnsSePppEntry 28 }

tmnxL2tpLnsSePppCircuitId OBJECT-TYPE
    SYNTAX      OCTET STRING (SIZE (0..256))
    MAX-ACCESS  read-only
    STATUS      obsolete
    DESCRIPTION
        "The value of tmnxL2tpLnsSePppCircuitId indicates the value of the
         circuit-id sub-option."
    ::= { tmnxL2tpLnsSePppEntry 29 }

tmnxL2tpLnsSePppRemoteId OBJECT-TYPE
    SYNTAX      OCTET STRING (SIZE (0..256))
    MAX-ACCESS  read-only
    STATUS      obsolete
    DESCRIPTION
        "The value of tmnxL2tpLnsSePppRemoteId indicates the value of the
         remote-id sub-option."
    ::= { tmnxL2tpLnsSePppEntry 30 }

tmnxL2tpLnsSePppAddressPool OBJECT-TYPE
    SYNTAX      DisplayString (SIZE (0..32))
    MAX-ACCESS  read-only
    STATUS      obsolete
    DESCRIPTION
        "The value of tmnxL2tpLnsSePppAddressPool indicates the IP address pool
         which is used to search for an IP address for this session."
    ::= { tmnxL2tpLnsSePppEntry 31 }

tmnxL2tpLnsSePppType OBJECT-TYPE
    SYNTAX      TmnxPppoeSessionType
    MAX-ACCESS  read-only
    STATUS      obsolete
    DESCRIPTION
        "The value of tmnxL2tpLnsSePppType indicates the type of this
         session."
    ::= { tmnxL2tpLnsSePppEntry 32 }

tmnxL2tpLnsSePppSvcId OBJECT-TYPE
    SYNTAX      TmnxServId
    MAX-ACCESS  read-only
    STATUS      obsolete
    DESCRIPTION
        "The value of tmnxL2tpLnsSePppSvcId indicates the service ID of
         the IES/VPRN service to which this session belongs."
    ::= { tmnxL2tpLnsSePppEntry 33 }

tmnxL2tpLnsSePppGrpIf OBJECT-TYPE
    SYNTAX      InterfaceIndexOrZero
    MAX-ACCESS  read-only
    STATUS      obsolete
    DESCRIPTION
        "The value of tmnxL2tpLnsSePppGrpIf indicates the interface index
         of the group-interface to which this session belongs."
    ::= { tmnxL2tpLnsSePppEntry 34 }

tmnxL2tpLnsSePppL2tpVrtrId OBJECT-TYPE
    SYNTAX      TmnxVRtrIDOrZero
    MAX-ACCESS  read-only
    STATUS      obsolete
    DESCRIPTION
        "The value of tmnxL2tpLnsSePppL2tpVrtrId indicates the virtual router 
         ID of the L2TP session associated with this session. 
         
         If there is no L2TP session associated with this session, the value
         of this object is equal to zero."
    ::= { tmnxL2tpLnsSePppEntry 35 }

tmnxL2tpLnsSePppL2tpConnectionId OBJECT-TYPE
    SYNTAX      Unsigned32
    MAX-ACCESS  read-only
    STATUS      obsolete
    DESCRIPTION
        "The value of tmnxL2tpLnsSePppL2tpVrtrId indicates the connection 
         ID of the L2TP session associated with this session.
         
         The values of tmnxL2tpLnsSePppL2tpVrtrId and 
         tmnxL2tpLnsSePppL2tpConnectionId are the index in the table
         TIMETRA-L2TP-MIB::tmnxL2tpSeStatusTable of the L2TP session associated
         with this session. 
         
         If there is no L2TP session associated with this session, the
         value of this object is equal to zero."
    ::= { tmnxL2tpLnsSePppEntry 36 }

tmnxL2tpLnsSePppCategoryMapName OBJECT-TYPE
    SYNTAX      TNamedItemOrEmpty
    MAX-ACCESS  read-only
    STATUS      obsolete
    DESCRIPTION
        "The value of tmnxL2tpLnsSePppCategoryMapName indicates the
         category map name applicable for this session.

         The value of tmnxL2tpLnsSePppOriginStrings indicates from what source
         this string was received."
    ::= { tmnxL2tpLnsSePppEntry 37 }

tmnxL2tpLnsSePppRadiusClassAttr OBJECT-TYPE
    SYNTAX      OCTET STRING (SIZE (0..64))
    MAX-ACCESS  read-only
    STATUS      obsolete
    DESCRIPTION
        "The value of tmnxL2tpLnsSePppRadiusClassAttr indicates the Class
         attribute returned by the RADIUS server in an Access-Accept message.
         
         If no RADIUS authentication is performed for this session, or RADIUS
         did not return this attribute, the value of this object is empty."
    ::= { tmnxL2tpLnsSePppEntry 38 }

tmnxL2tpLnsSePppRadiusUserName OBJECT-TYPE
    SYNTAX      DisplayString (SIZE (0..128))
    MAX-ACCESS  read-only
    STATUS      obsolete
    DESCRIPTION
        "The value of tmnxL2tpLnsSePppRadiusUserName indicates the User-Name
         attribute returned by the RADIUS server in an Access-Accept message.

         If RADIUS did not return this attribute, the value of this object
         is equal to the User-Name attribute sent in the original
         Access-Request message.
         
         If no RADIUS authentication is performed for this session, the value
         of this object is empty."
    ::= { tmnxL2tpLnsSePppEntry 39 }

tmnxL2tpLnsSePppIpv6cpState OBJECT-TYPE
    SYNTAX      TmnxPppCpState
    MAX-ACCESS  read-only
    STATUS      obsolete
    DESCRIPTION
        "The value of tmnxL2tpLnsSePppIpv6cpState indicates the current state of
         the PPP IPv6 Control Protocol of the PPPoE session."
    ::= { tmnxL2tpLnsSePppEntry 40 }

tmnxL2tpLnsSePppInterfaceId OBJECT-TYPE
    SYNTAX      OCTET STRING (SIZE (8))
    MAX-ACCESS  read-only
    STATUS      obsolete
    DESCRIPTION
        "The value of tmnxL2tpLnsSePppInterfaceId indicates the value of the
         remote-id sub-option inserted by the PPPoE intermediate agent."
    ::= { tmnxL2tpLnsSePppEntry 41 }

tmnxL2tpLnsSePppOriginIpv6cpInfo OBJECT-TYPE
    SYNTAX      TmnxPppoeSessionInfoOrigin
    MAX-ACCESS  read-only
    STATUS      obsolete
    DESCRIPTION
        "The value of tmnxL2tpLnsSePppOriginIpv6cpInfo indicates which source
         provided the IPCP information (IP, DNS and NBNS addresses)."
    ::= { tmnxL2tpLnsSePppEntry 42 }

tmnxL2tpLnsSePppIpv6DnsType OBJECT-TYPE
    SYNTAX      InetAddressType
    MAX-ACCESS  read-only
    STATUS      obsolete
    DESCRIPTION
        "The value of tmnxL2tpLnsSePppIpv6DnsType indicates the address
         type of tmnxL2tpLnsSePppIpv6Dns1/2."
    ::= { tmnxL2tpLnsSePppEntry 43 }

tmnxL2tpLnsSePppIpv6Dns1 OBJECT-TYPE
    SYNTAX      InetAddress (SIZE (0|16))
    MAX-ACCESS  read-only
    STATUS      obsolete
    DESCRIPTION
        "The value of tmnxL2tpLnsSePppIpv6Dns1 indicates the primary DNS
         server.

         The value of this object is ''H when not applicable.

         The value of tmnxL2tpLnsSePppOriginIpv6cpInfo indicates from what
         source this IP address was received."
    ::= { tmnxL2tpLnsSePppEntry 44 }

tmnxL2tpLnsSePppIpv6Dns2 OBJECT-TYPE
    SYNTAX      InetAddress (SIZE (0|16))
    MAX-ACCESS  read-only
    STATUS      obsolete
    DESCRIPTION
        "The value of tmnxL2tpLnsSePppIpv6Dns2 indicates the secondary DNS
         server.

         The value of this object is ''H when not applicable.

         The value of tmnxL2tpLnsSePppOriginIpv6cpInfo indicates from what
         source this IP address was received."
    ::= { tmnxL2tpLnsSePppEntry 45 }

tmnxL2tpLnsSePppIpv6DelPfxType OBJECT-TYPE
    SYNTAX      InetAddressType
    MAX-ACCESS  read-only
    STATUS      obsolete
    DESCRIPTION
        "The value of tmnxL2tpLnsSePppIpv6DelPfxType indicates the address
         type of tmnxL2tpLnsSePppIpv6DelPfx."
    ::= { tmnxL2tpLnsSePppEntry 46 }

tmnxL2tpLnsSePppIpv6DelPfxLen OBJECT-TYPE
    SYNTAX      InetAddressPrefixLength (0..128)
    MAX-ACCESS  read-only
    STATUS      obsolete
    DESCRIPTION 
        "The value of tmnxL2tpLnsSePppIpv6DelPfxLen indicates
         the length of tmnxL2tpLnsSePppIpv6DelPfx."
    ::= { tmnxL2tpLnsSePppEntry 47 }

tmnxL2tpLnsSePppIpv6DelPfx OBJECT-TYPE
    SYNTAX      InetAddress (SIZE (0|16))
    MAX-ACCESS  read-only
    STATUS      obsolete
    DESCRIPTION
        "The value of tmnxL2tpLnsSePppIpv6DelPfx indicates the IPv6 prefix
         used for DHCPv6 prefix delegation."
    ::= { tmnxL2tpLnsSePppEntry 48 }

tmnxL2tpLnsSePppIpv6PrefixType OBJECT-TYPE
    SYNTAX      InetAddressType
    MAX-ACCESS  read-only
    STATUS      obsolete
    DESCRIPTION
        "The value of tmnxL2tpLnsSePppIpv6PrefixType indicates the address
         type of tmnxL2tpLnsSePppIpv6Prefix."
    ::= { tmnxL2tpLnsSePppEntry 49 }

tmnxL2tpLnsSePppIpv6PrefixLen OBJECT-TYPE
    SYNTAX      InetAddressPrefixLength (0..128)
    MAX-ACCESS  read-only
    STATUS      obsolete
    DESCRIPTION 
        "The value of tmnxL2tpLnsSePppIpv6PrefixLen indicates
         the length of tmnxL2tpLnsSePppIpv6Prefix."
    ::= { tmnxL2tpLnsSePppEntry 50 }

tmnxL2tpLnsSePppIpv6Prefix OBJECT-TYPE
    SYNTAX      InetAddress (SIZE (0|16))
    MAX-ACCESS  read-only
    STATUS      obsolete
    DESCRIPTION
        "The value of tmnxL2tpLnsSePppIpv6Prefix indicates the IPv6 prefix
         used for stateless address autoconfiguration."
    ::= { tmnxL2tpLnsSePppEntry 51 }

tmnxL2tpLnsSePppSubPppIndex OBJECT-TYPE
    SYNTAX      Unsigned32
    MAX-ACCESS  read-only
    STATUS      current
    DESCRIPTION
        "The value of tmnxL2tpLnsSePppSubPppIndex indicates 
         the local identifier of the subscriber PPP session.
         
         It is the index of the corresponding conceptual row in the
         TIMETRA-SUBSCRIBER-MGMT-MIB::tmnxSubPppTable."
    ::= { tmnxL2tpLnsSePppEntry 52 }

--
--      The L2TP LNS Session PPP Statistics Table
--

tmnxL2tpLnsSePppStatTable   OBJECT-TYPE
    SYNTAX      SEQUENCE OF TmnxL2tpLnsSePppStatEntry
    MAX-ACCESS  not-accessible
    STATUS      obsolete
    DESCRIPTION
       "The tmnxL2tpLnsSePppStatTable has an entry for each 
        Layer Two Tunneling Protocol Session for which this system acts as LNS.
        
        This table is replaced with 
        TIMETRA-SUBSCRIBER-MGMT-MIB::tmnxSubPppStatTable."
    ::= { tmnxL2tpSeStatObjs 3 }

tmnxL2tpLnsSePppStatEntry   OBJECT-TYPE
    SYNTAX      TmnxL2tpLnsSePppStatEntry
    MAX-ACCESS  not-accessible
    STATUS      obsolete
    DESCRIPTION
       "Each conceptual row represents a Layer Two Tunneling Protocol
        Session.

        Entries in this table are created and destroyed by the system."
    INDEX { vRtrID,
            tmnxL2tpSeStatusId }
    ::= { tmnxL2tpLnsSePppStatTable 1 }

TmnxL2tpLnsSePppStatEntry ::= 
    SEQUENCE {
        tmnxL2tpLnsSePppStatRxUnkwnProto Counter32,
        tmnxL2tpLnsSePppStatRxLcpConfRq  Counter32,
        tmnxL2tpLnsSePppStatRxLcpConfAk  Counter32,
        tmnxL2tpLnsSePppStatRxLcpConfNk  Counter32,
        tmnxL2tpLnsSePppStatRxLcpConfRj  Counter32,
        tmnxL2tpLnsSePppStatRxLcpTermRq  Counter32,
        tmnxL2tpLnsSePppStatRxLcpTermAk  Counter32,
        tmnxL2tpLnsSePppStatRxLcpCodeRj  Counter32,
        tmnxL2tpLnsSePppStatRxLcpEchoRq  Counter32,
        tmnxL2tpLnsSePppStatRxLcpEchoRep Counter32,
        tmnxL2tpLnsSePppStatRxLcpProtRj  Counter32,
        tmnxL2tpLnsSePppStatRxLcpDiscRq  Counter32,
        tmnxL2tpLnsSePppStatTxLcpConfRq  Counter32,
        tmnxL2tpLnsSePppStatTxLcpConfAk  Counter32,
        tmnxL2tpLnsSePppStatTxLcpConfNk  Counter32,
        tmnxL2tpLnsSePppStatTxLcpConfRj  Counter32,
        tmnxL2tpLnsSePppStatTxLcpTermRq  Counter32,
        tmnxL2tpLnsSePppStatTxLcpTermAk  Counter32,
        tmnxL2tpLnsSePppStatTxLcpCodeRj  Counter32,
        tmnxL2tpLnsSePppStatTxLcpEchoRq  Counter32,
        tmnxL2tpLnsSePppStatTxLcpEchoRep Counter32,
        tmnxL2tpLnsSePppStatTxLcpProtRj  Counter32,
        tmnxL2tpLnsSePppStatTxLcpDiscRq  Counter32,
        tmnxL2tpLnsSePppStatRxPapAuthRq  Counter32,
        tmnxL2tpLnsSePppStatTxPapAuthAk  Counter32,
        tmnxL2tpLnsSePppStatTxPapAuthNk  Counter32,
        tmnxL2tpLnsSePppStatRxChapResp   Counter32,
        tmnxL2tpLnsSePppStatTxChapChall  Counter32,
        tmnxL2tpLnsSePppStatTxChapSucc   Counter32,
        tmnxL2tpLnsSePppStatTxChapFail   Counter32,
        tmnxL2tpLnsSePppStatRxIpcpConfRq Counter32,
        tmnxL2tpLnsSePppStatRxIpcpConfAk Counter32,
        tmnxL2tpLnsSePppStatRxIpcpConfNk Counter32,
        tmnxL2tpLnsSePppStatRxIpcpConfRj Counter32,
        tmnxL2tpLnsSePppStatRxIpcpTermRq Counter32,
        tmnxL2tpLnsSePppStatRxIpcpTermAk Counter32,
        tmnxL2tpLnsSePppStatRxIpcpCodeRj Counter32,
        tmnxL2tpLnsSePppStatTxIpcpConfRq Counter32,
        tmnxL2tpLnsSePppStatTxIpcpConfAk Counter32,
        tmnxL2tpLnsSePppStatTxIpcpConfNk Counter32,
        tmnxL2tpLnsSePppStatTxIpcpConfRj Counter32,
        tmnxL2tpLnsSePppStatTxIpcpTermRq Counter32,
        tmnxL2tpLnsSePppStatTxIpcpTermAk Counter32,
        tmnxL2tpLnsSePppStatTxIpcpCodeRj Counter32,

        tmnxL2tpLnsSePppStatRxIpv6cpCfRq Counter32,
        tmnxL2tpLnsSePppStatRxIpv6cpCfAk Counter32,
        tmnxL2tpLnsSePppStatRxIpv6cpCfNk Counter32,
        tmnxL2tpLnsSePppStatRxIpv6cpCfRj Counter32,
        tmnxL2tpLnsSePppStatRxIpv6cpTmRq Counter32,
        tmnxL2tpLnsSePppStatRxIpv6cpTmAk Counter32,
        tmnxL2tpLnsSePppStatRxIpv6cpCdRj Counter32,
        tmnxL2tpLnsSePppStatTxIpv6cpCfRq Counter32,
        tmnxL2tpLnsSePppStatTxIpv6cpCfAk Counter32,
        tmnxL2tpLnsSePppStatTxIpv6cpCfNk Counter32,
        tmnxL2tpLnsSePppStatTxIpv6cpCfRj Counter32,
        tmnxL2tpLnsSePppStatTxIpv6cpTmRq Counter32,
        tmnxL2tpLnsSePppStatTxIpv6cpTmAk Counter32,
        tmnxL2tpLnsSePppStatTxIpv6cpCdRj Counter32
    }
        
tmnxL2tpLnsSePppStatRxUnkwnProto OBJECT-TYPE
    SYNTAX      Counter32
    MAX-ACCESS  read-only
    STATUS      obsolete
    DESCRIPTION
        "The value of tmnxL2tpLnsSePppStatRxUnkwnProto indicates the number of
         packets with unknown PPP protocol received for this PPP session."
    ::= { tmnxL2tpLnsSePppStatEntry 2 }

tmnxL2tpLnsSePppStatRxLcpConfRq OBJECT-TYPE
    SYNTAX      Counter32
    MAX-ACCESS  read-only
    STATUS      obsolete
    DESCRIPTION
        "The value of tmnxL2tpLnsSePppStatRxLcpConfRq indicates the number of
         LCP configure requests received for this PPP session."
    ::= { tmnxL2tpLnsSePppStatEntry 3 }

tmnxL2tpLnsSePppStatRxLcpConfAk OBJECT-TYPE
    SYNTAX      Counter32
    MAX-ACCESS  read-only
    STATUS      obsolete
    DESCRIPTION
        "The value of tmnxL2tpLnsSePppStatRxLcpConfAk indicates the number of
         LCP configure acknowledgements received for this PPP session."
    ::= { tmnxL2tpLnsSePppStatEntry 4 }

tmnxL2tpLnsSePppStatRxLcpConfNk OBJECT-TYPE
    SYNTAX      Counter32
    MAX-ACCESS  read-only
    STATUS      obsolete
    DESCRIPTION
        "The value of tmnxL2tpLnsSePppStatRxLcpConfNk indicates the number of
         negative LCP configure acknowledgements received for this PPP
         session."
    ::= { tmnxL2tpLnsSePppStatEntry 5 }

tmnxL2tpLnsSePppStatRxLcpConfRj OBJECT-TYPE
    SYNTAX      Counter32
    MAX-ACCESS  read-only
    STATUS      obsolete
    DESCRIPTION
        "The value of tmnxL2tpLnsSePppStatRxLcpConfRj indicates the number of
         LCP configure rejects received for this PPP session."
    ::= { tmnxL2tpLnsSePppStatEntry 6 }

tmnxL2tpLnsSePppStatRxLcpTermRq OBJECT-TYPE
    SYNTAX      Counter32
    MAX-ACCESS  read-only
    STATUS      obsolete
    DESCRIPTION
        "The value of tmnxL2tpLnsSePppStatRxLcpTermRq indicates the number of
         LCP terminate requests received for this PPP session."
    ::= { tmnxL2tpLnsSePppStatEntry 7 }

tmnxL2tpLnsSePppStatRxLcpTermAk OBJECT-TYPE
    SYNTAX      Counter32
    MAX-ACCESS  read-only
    STATUS      obsolete
    DESCRIPTION
        "The value of tmnxL2tpLnsSePppStatRxLcpTermAk indicates the number of
         LCP terminate acknowledgements received for this PPP session."
    ::= { tmnxL2tpLnsSePppStatEntry 8 }

tmnxL2tpLnsSePppStatRxLcpCodeRj OBJECT-TYPE
    SYNTAX      Counter32
    MAX-ACCESS  read-only
    STATUS      obsolete
    DESCRIPTION
        "The value of tmnxL2tpLnsSePppStatRxLcpCodeRj indicates the number of
         LCP code rejects received for this PPP session."
    ::= { tmnxL2tpLnsSePppStatEntry 9 }

tmnxL2tpLnsSePppStatRxLcpEchoRq OBJECT-TYPE
    SYNTAX      Counter32
    MAX-ACCESS  read-only
    STATUS      obsolete
    DESCRIPTION
        "The value of tmnxL2tpLnsSePppStatRxLcpEchoRq indicates the number of
         LCP echo requests received for this PPP session."
    ::= { tmnxL2tpLnsSePppStatEntry 10 }

tmnxL2tpLnsSePppStatRxLcpEchoRep OBJECT-TYPE
    SYNTAX      Counter32
    MAX-ACCESS  read-only
    STATUS      obsolete
    DESCRIPTION
        "The value of tmnxL2tpLnsSePppStatRxLcpEchoRep indicates the number of
         LCP echo replies received for this PPP session."
    ::= { tmnxL2tpLnsSePppStatEntry 11 }

tmnxL2tpLnsSePppStatRxLcpProtRj OBJECT-TYPE
    SYNTAX      Counter32
    MAX-ACCESS  read-only
    STATUS      obsolete
    DESCRIPTION
        "The value of tmnxL2tpLnsSePppStatRxLcpProtRj indicates the number of
         LCP protocol rejects received for this PPP session."
    ::= { tmnxL2tpLnsSePppStatEntry 12 }

tmnxL2tpLnsSePppStatRxLcpDiscRq OBJECT-TYPE
    SYNTAX      Counter32
    MAX-ACCESS  read-only
    STATUS      obsolete
    DESCRIPTION
        "The value of tmnxL2tpLnsSePppStatRxLcpDiscRq indicates the number of
         LCP discard requests received for this PPP session."
    ::= { tmnxL2tpLnsSePppStatEntry 13 }

tmnxL2tpLnsSePppStatTxLcpConfRq OBJECT-TYPE
    SYNTAX      Counter32
    MAX-ACCESS  read-only
    STATUS      obsolete
    DESCRIPTION
        "The value of tmnxL2tpLnsSePppStatTxLcpConfRq indicates the number of
         LCP configure requests transmitted for this PPP session."
    ::= { tmnxL2tpLnsSePppStatEntry 14 }

tmnxL2tpLnsSePppStatTxLcpConfAk OBJECT-TYPE
    SYNTAX      Counter32
    MAX-ACCESS  read-only
    STATUS      obsolete
    DESCRIPTION
        "The value of tmnxL2tpLnsSePppStatTxLcpConfAk indicates the number of
         LCP configure acknowledgements transmitted for this PPP session."
    ::= { tmnxL2tpLnsSePppStatEntry 15 }

tmnxL2tpLnsSePppStatTxLcpConfNk OBJECT-TYPE
    SYNTAX      Counter32
    MAX-ACCESS  read-only
    STATUS      obsolete
    DESCRIPTION
        "The value of tmnxL2tpLnsSePppStatTxLcpConfNk indicates the number of
         negative LCP configure acknowledgements transmitted for this PPP
         session."
    ::= { tmnxL2tpLnsSePppStatEntry 16 }

tmnxL2tpLnsSePppStatTxLcpConfRj OBJECT-TYPE
    SYNTAX      Counter32
    MAX-ACCESS  read-only
    STATUS      obsolete
    DESCRIPTION
        "The value of tmnxL2tpLnsSePppStatTxLcpConfRj indicates the number of
         LCP configure rejects transmitted for this PPP session."
    ::= { tmnxL2tpLnsSePppStatEntry 17 }

tmnxL2tpLnsSePppStatTxLcpTermRq OBJECT-TYPE
    SYNTAX      Counter32
    MAX-ACCESS  read-only
    STATUS      obsolete
    DESCRIPTION
        "The value of tmnxL2tpLnsSePppStatTxLcpTermRq indicates the number of
         LCP terminate requests transmitted for this PPP session."
    ::= { tmnxL2tpLnsSePppStatEntry 18 }

tmnxL2tpLnsSePppStatTxLcpTermAk OBJECT-TYPE
    SYNTAX      Counter32
    MAX-ACCESS  read-only
    STATUS      obsolete
    DESCRIPTION
        "The value of tmnxL2tpLnsSePppStatTxLcpTermAk indicates the number of
         LCP terminate acknowledgements transmitted for this PPP session."
    ::= { tmnxL2tpLnsSePppStatEntry 19 }

tmnxL2tpLnsSePppStatTxLcpCodeRj OBJECT-TYPE
    SYNTAX      Counter32
    MAX-ACCESS  read-only
    STATUS      obsolete
    DESCRIPTION
        "The value of tmnxL2tpLnsSePppStatTxLcpCodeRj indicates the number of
         LCP code rejects transmitted for this PPP session."
    ::= { tmnxL2tpLnsSePppStatEntry 20 }

tmnxL2tpLnsSePppStatTxLcpEchoRq OBJECT-TYPE
    SYNTAX      Counter32
    MAX-ACCESS  read-only
    STATUS      obsolete
    DESCRIPTION
        "The value of tmnxL2tpLnsSePppStatTxLcpEchoRq indicates the number of
         LCP echo requests transmitted for this PPP session."
    ::= { tmnxL2tpLnsSePppStatEntry 21 }

tmnxL2tpLnsSePppStatTxLcpEchoRep OBJECT-TYPE
    SYNTAX      Counter32
    MAX-ACCESS  read-only
    STATUS      obsolete
    DESCRIPTION
        "The value of tmnxL2tpLnsSePppStatTxLcpEchoRep indicates the number of
         LCP echo replies transmitted for this PPP session."
    ::= { tmnxL2tpLnsSePppStatEntry 22 }

tmnxL2tpLnsSePppStatTxLcpProtRj OBJECT-TYPE
    SYNTAX      Counter32
    MAX-ACCESS  read-only
    STATUS      obsolete
    DESCRIPTION
        "The value of tmnxL2tpLnsSePppStatTxLcpProtRj indicates the number of
         LCP protocol rejects transmitted for this PPP session."
    ::= { tmnxL2tpLnsSePppStatEntry 23 }

tmnxL2tpLnsSePppStatTxLcpDiscRq OBJECT-TYPE
    SYNTAX      Counter32
    MAX-ACCESS  read-only
    STATUS      obsolete
    DESCRIPTION
        "The value of tmnxL2tpLnsSePppStatTxLcpDiscRq indicates the number of
         LCP discard requests transmitted for this PPP session."
    ::= { tmnxL2tpLnsSePppStatEntry 24 }

tmnxL2tpLnsSePppStatRxPapAuthRq OBJECT-TYPE
    SYNTAX      Counter32
    MAX-ACCESS  read-only
    STATUS      obsolete
    DESCRIPTION
        "The value of tmnxL2tpLnsSePppStatRxPapAuthRq indicates the number of
         PAP authentication requests received for this PPP session."
    ::= { tmnxL2tpLnsSePppStatEntry 25 }

tmnxL2tpLnsSePppStatTxPapAuthAk OBJECT-TYPE
    SYNTAX      Counter32
    MAX-ACCESS  read-only
    STATUS      obsolete
    DESCRIPTION
        "The value of tmnxL2tpLnsSePppStatTxPapAuthAk indicates the number of
         PAP authentication acknowledgements transmitted for this PPP
         session."
    ::= { tmnxL2tpLnsSePppStatEntry 26 }

tmnxL2tpLnsSePppStatTxPapAuthNk OBJECT-TYPE
    SYNTAX      Counter32
    MAX-ACCESS  read-only
    STATUS      obsolete
    DESCRIPTION
        "The value of tmnxL2tpLnsSePppStatTxPapAuthNk indicates the number of
         negative PAP authentication acknowledgements transmitted for this
         PPP session."
    ::= { tmnxL2tpLnsSePppStatEntry 27 }

tmnxL2tpLnsSePppStatRxChapResp OBJECT-TYPE
    SYNTAX      Counter32
    MAX-ACCESS  read-only
    STATUS      obsolete
    DESCRIPTION
        "The value of tmnxL2tpLnsSePppStatRxChapResp indicates the number of
         CHAP authentication responses received for this PPP session."
    ::= { tmnxL2tpLnsSePppStatEntry 28 }

tmnxL2tpLnsSePppStatTxChapChall OBJECT-TYPE
    SYNTAX      Counter32
    MAX-ACCESS  read-only
    STATUS      obsolete
    DESCRIPTION
        "The value of tmnxL2tpLnsSePppStatTxChapChall indicates the number of
         CHAP authentication challenges transmitted for this PPP session."
    ::= { tmnxL2tpLnsSePppStatEntry 29 }

tmnxL2tpLnsSePppStatTxChapSucc OBJECT-TYPE
    SYNTAX      Counter32
    MAX-ACCESS  read-only
    STATUS      obsolete
    DESCRIPTION
        "The value of tmnxL2tpLnsSePppStatTxChapSucc indicates the number of
         CHAP authentication acknowledgements transmitted for this PPP
         session."
    ::= { tmnxL2tpLnsSePppStatEntry 30 }

tmnxL2tpLnsSePppStatTxChapFail OBJECT-TYPE
    SYNTAX      Counter32
    MAX-ACCESS  read-only
    STATUS      obsolete
    DESCRIPTION
        "The value of tmnxL2tpLnsSePppStatTxChapFail indicates the number of
         negative CHAP authentication acknowledgements transmitted for this
         PPP session."
    ::= { tmnxL2tpLnsSePppStatEntry 31 }

tmnxL2tpLnsSePppStatRxIpcpConfRq OBJECT-TYPE
    SYNTAX      Counter32
    MAX-ACCESS  read-only
    STATUS      obsolete
    DESCRIPTION
        "The value of tmnxL2tpLnsSePppStatRxIpcpConfRq indicates the number of
         IPCP configure requests received for this PPP session."
    ::= { tmnxL2tpLnsSePppStatEntry 32 }

tmnxL2tpLnsSePppStatRxIpcpConfAk OBJECT-TYPE
    SYNTAX      Counter32
    MAX-ACCESS  read-only
    STATUS      obsolete
    DESCRIPTION
        "The value of tmnxL2tpLnsSePppStatRxIpcpConfAk indicates the number of
         IPCP configure acknowledgements received for this PPP session."
    ::= { tmnxL2tpLnsSePppStatEntry 33 }

tmnxL2tpLnsSePppStatRxIpcpConfNk OBJECT-TYPE
    SYNTAX      Counter32
    MAX-ACCESS  read-only
    STATUS      obsolete
    DESCRIPTION
        "The value of tmnxL2tpLnsSePppStatRxIpcpConfNk indicates the number of
         negative IPCP configure acknowledgements received for this PPP
         session."
    ::= { tmnxL2tpLnsSePppStatEntry 34 }

tmnxL2tpLnsSePppStatRxIpcpConfRj OBJECT-TYPE
    SYNTAX      Counter32
    MAX-ACCESS  read-only
    STATUS      obsolete
    DESCRIPTION
        "The value of tmnxL2tpLnsSePppStatRxIpcpConfRj indicates the number of
         IPCP configure rejects received for this PPP session."
    ::= { tmnxL2tpLnsSePppStatEntry 35 }

tmnxL2tpLnsSePppStatRxIpcpTermRq OBJECT-TYPE
    SYNTAX      Counter32
    MAX-ACCESS  read-only
    STATUS      obsolete
    DESCRIPTION
        "The value of tmnxL2tpLnsSePppStatRxIpcpTermRq indicates the number of
         IPCP terminate requests received for this PPP session."
    ::= { tmnxL2tpLnsSePppStatEntry 36 }

tmnxL2tpLnsSePppStatRxIpcpTermAk OBJECT-TYPE
    SYNTAX      Counter32
    MAX-ACCESS  read-only
    STATUS      obsolete
    DESCRIPTION
        "The value of tmnxL2tpLnsSePppStatRxIpcpTermAk indicates the number of
         IPCP terminate acknowledgements received for this PPP session."
    ::= { tmnxL2tpLnsSePppStatEntry 37 }

tmnxL2tpLnsSePppStatRxIpcpCodeRj OBJECT-TYPE
    SYNTAX      Counter32
    MAX-ACCESS  read-only
    STATUS      obsolete
    DESCRIPTION
        "The value of tmnxL2tpLnsSePppStatRxIpcpCodeRj indicates the number of
         IPCP code rejects received for this PPP session."
    ::= { tmnxL2tpLnsSePppStatEntry 38 }

tmnxL2tpLnsSePppStatTxIpcpConfRq OBJECT-TYPE
    SYNTAX      Counter32
    MAX-ACCESS  read-only
    STATUS      obsolete
    DESCRIPTION
        "The value of tmnxL2tpLnsSePppStatTxIpcpConfRq indicates the number of
         IPCP configure requests transmitted for this PPP session."
    ::= { tmnxL2tpLnsSePppStatEntry 39 }

tmnxL2tpLnsSePppStatTxIpcpConfAk OBJECT-TYPE
    SYNTAX      Counter32
    MAX-ACCESS  read-only
    STATUS      obsolete
    DESCRIPTION
        "The value of tmnxL2tpLnsSePppStatTxIpcpConfAk indicates the number of
         IPCP configure acknowledgements transmitted for this PPP session."
    ::= { tmnxL2tpLnsSePppStatEntry 40 }

tmnxL2tpLnsSePppStatTxIpcpConfNk OBJECT-TYPE
    SYNTAX      Counter32
    MAX-ACCESS  read-only
    STATUS      obsolete
    DESCRIPTION
        "The value of tmnxL2tpLnsSePppStatTxIpcpConfNk indicates the number of
         negative IPCP configure acknowledgements transmitted for this PPP
         session."
    ::= { tmnxL2tpLnsSePppStatEntry 41 }

tmnxL2tpLnsSePppStatTxIpcpConfRj OBJECT-TYPE
    SYNTAX      Counter32
    MAX-ACCESS  read-only
    STATUS      obsolete
    DESCRIPTION
        "The value of tmnxL2tpLnsSePppStatTxIpcpConfRj indicates the number of
         IPCP configure rejects transmitted for this PPP session."
    ::= { tmnxL2tpLnsSePppStatEntry 42 }

tmnxL2tpLnsSePppStatTxIpcpTermRq OBJECT-TYPE
    SYNTAX      Counter32
    MAX-ACCESS  read-only
    STATUS      obsolete
    DESCRIPTION
        "The value of tmnxL2tpLnsSePppStatTxIpcpTermRq indicates the number of
         IPCP terminate requests transmitted for this PPP session."
    ::= { tmnxL2tpLnsSePppStatEntry 43 }

tmnxL2tpLnsSePppStatTxIpcpTermAk OBJECT-TYPE
    SYNTAX      Counter32
    MAX-ACCESS  read-only
    STATUS      obsolete
    DESCRIPTION
        "The value of tmnxL2tpLnsSePppStatTxIpcpTermAk indicates the number of
         IPCP terminate acknowledgements transmitted for this PPP session."
    ::= { tmnxL2tpLnsSePppStatEntry 44 }

tmnxL2tpLnsSePppStatTxIpcpCodeRj OBJECT-TYPE
    SYNTAX      Counter32
    MAX-ACCESS  read-only
    STATUS      obsolete
    DESCRIPTION
        "The value of tmnxL2tpLnsSePppStatTxIpcpCodeRj indicates the number of
         IPCP code rejects transmitted for this PPP session."
    ::= { tmnxL2tpLnsSePppStatEntry 45 }


tmnxL2tpLnsSePppStatRxIpv6cpCfRq OBJECT-TYPE
    SYNTAX      Counter32
    MAX-ACCESS  read-only
    STATUS      obsolete
    DESCRIPTION
        "The value of tmnxL2tpLnsSePppStatRxIpv6cpCfRq indicates the number of
         IPv6 Control Protocol (IPv6CP) configure requests received 
         for this PPP session."
    ::= { tmnxL2tpLnsSePppStatEntry 46 }

tmnxL2tpLnsSePppStatRxIpv6cpCfAk OBJECT-TYPE
    SYNTAX      Counter32
    MAX-ACCESS  read-only
    STATUS      obsolete
    DESCRIPTION
        "The value of tmnxL2tpLnsSePppStatRxIpv6cpCfAk indicates the number of
         IPv6CP configure acknowledgements received for this PPP session."
    ::= { tmnxL2tpLnsSePppStatEntry 47 }

tmnxL2tpLnsSePppStatRxIpv6cpCfNk OBJECT-TYPE
    SYNTAX      Counter32
    MAX-ACCESS  read-only
    STATUS      obsolete
    DESCRIPTION
        "The value of tmnxL2tpLnsSePppStatRxIpv6cpCfNk indicates the number of
         negative IPv6CP configure acknowledgements received for this PPP
         session."
    ::= { tmnxL2tpLnsSePppStatEntry 48 }

tmnxL2tpLnsSePppStatRxIpv6cpCfRj OBJECT-TYPE
    SYNTAX      Counter32
    MAX-ACCESS  read-only
    STATUS      obsolete
    DESCRIPTION
        "The value of tmnxL2tpLnsSePppStatRxIpv6cpCfRj indicates the number of
         IPv6CP configure rejects received for this PPP session."
    ::= { tmnxL2tpLnsSePppStatEntry 49 }

tmnxL2tpLnsSePppStatRxIpv6cpTmRq OBJECT-TYPE
    SYNTAX      Counter32
    MAX-ACCESS  read-only
    STATUS      obsolete
    DESCRIPTION
        "The value of tmnxL2tpLnsSePppStatRxIpv6cpTmRq indicates the number of
         IPv6CP terminate requests received for this PPP session."
    ::= { tmnxL2tpLnsSePppStatEntry 50 }

tmnxL2tpLnsSePppStatRxIpv6cpTmAk OBJECT-TYPE
    SYNTAX      Counter32
    MAX-ACCESS  read-only
    STATUS      obsolete
    DESCRIPTION
        "The value of tmnxL2tpLnsSePppStatRxIpv6cpTmAk indicates the number of
         IPv6CP terminate acknowledgements received for this PPP session."
    ::= { tmnxL2tpLnsSePppStatEntry 51 }

tmnxL2tpLnsSePppStatRxIpv6cpCdRj OBJECT-TYPE
    SYNTAX      Counter32
    MAX-ACCESS  read-only
    STATUS      obsolete
    DESCRIPTION
        "The value of tmnxL2tpLnsSePppStatRxIpv6cpCdRj indicates the number of
         IPv6CP code rejects received for this PPP session."
    ::= { tmnxL2tpLnsSePppStatEntry 52 }

tmnxL2tpLnsSePppStatTxIpv6cpCfRq OBJECT-TYPE
    SYNTAX      Counter32
    MAX-ACCESS  read-only
    STATUS      obsolete
    DESCRIPTION
        "The value of tmnxL2tpLnsSePppStatTxIpv6cpCfRq indicates the number of
         IPv6CP configure requests transmitted for this PPP session."
    ::= { tmnxL2tpLnsSePppStatEntry 53 }

tmnxL2tpLnsSePppStatTxIpv6cpCfAk OBJECT-TYPE
    SYNTAX      Counter32
    MAX-ACCESS  read-only
    STATUS      obsolete
    DESCRIPTION
        "The value of tmnxL2tpLnsSePppStatTxIpv6cpCfAk indicates the number of
         IPv6CP configure acknowledgements transmitted for this PPP session."
    ::= { tmnxL2tpLnsSePppStatEntry 54 }

tmnxL2tpLnsSePppStatTxIpv6cpCfNk OBJECT-TYPE
    SYNTAX      Counter32
    MAX-ACCESS  read-only
    STATUS      obsolete
    DESCRIPTION
        "The value of tmnxL2tpLnsSePppStatTxIpv6cpCfNk indicates the number of
         negative IPv6CP configure acknowledgements transmitted for this PPP
         session."
    ::= { tmnxL2tpLnsSePppStatEntry 55 }

tmnxL2tpLnsSePppStatTxIpv6cpCfRj OBJECT-TYPE
    SYNTAX      Counter32
    MAX-ACCESS  read-only
    STATUS      obsolete
    DESCRIPTION
        "The value of tmnxL2tpLnsSePppStatTxIpv6cpCfRj indicates the number of
         IPv6CP configure rejects transmitted for this PPP session."
    ::= { tmnxL2tpLnsSePppStatEntry 56 }

tmnxL2tpLnsSePppStatTxIpv6cpTmRq OBJECT-TYPE
    SYNTAX      Counter32
    MAX-ACCESS  read-only
    STATUS      obsolete
    DESCRIPTION
        "The value of tmnxL2tpLnsSePppStatTxIpv6cpTmRq indicates the number of
         IPv6CP terminate requests transmitted for this PPP session."
    ::= { tmnxL2tpLnsSePppStatEntry 57 }

tmnxL2tpLnsSePppStatTxIpv6cpTmAk OBJECT-TYPE
    SYNTAX      Counter32
    MAX-ACCESS  read-only
    STATUS      obsolete
    DESCRIPTION
        "The value of tmnxL2tpLnsSePppStatTxIpv6cpTmAk indicates the number of
         IPv6CP terminate acknowledgements transmitted for this PPP session."
    ::= { tmnxL2tpLnsSePppStatEntry 58 }

tmnxL2tpLnsSePppStatTxIpv6cpCdRj OBJECT-TYPE
    SYNTAX      Counter32
    MAX-ACCESS  read-only
    STATUS      obsolete
    DESCRIPTION
        "The value of tmnxL2tpLnsSePppStatTxIpv6cpCdRj indicates the number of
         IPv6CP code rejects transmitted for this PPP session."
    ::= { tmnxL2tpLnsSePppStatEntry 59 }


--
--      The L2TP LNS Session Managed Route Table
--

tmnxL2tpLnsSeMRtTable   OBJECT-TYPE
    SYNTAX      SEQUENCE OF TmnxL2tpLnsSeMRtEntry
    MAX-ACCESS  not-accessible
    STATUS      obsolete
    DESCRIPTION
       "The tmnxL2tpLnsSeMRtTable contains managed routes for 
        Layer Two Tunneling Protocol Sessions for which this system acts as LNS.

        This table is replaced with 
        TIMETRA-SUBSCRIBER-MGMT-MIB::tmnxSubPppMRtTable"
    ::= { tmnxL2tpSeStatObjs 4 }

tmnxL2tpLnsSeMRtEntry   OBJECT-TYPE
    SYNTAX      TmnxL2tpLnsSeMRtEntry
    MAX-ACCESS  not-accessible
    STATUS      obsolete
    DESCRIPTION
       "Each conceptual row represents a managed route of an L2TP session
        for which this system acts as LNS."
    INDEX { vRtrID,
            tmnxL2tpSeStatusId,
            tmnxL2tpLnsSeMRtAddrType,
            tmnxL2tpLnsSeMRtAddr,
            tmnxL2tpLnsSeMRtPrefixLen }
    ::= { tmnxL2tpLnsSeMRtTable 1 }

TmnxL2tpLnsSeMRtEntry ::= 
    SEQUENCE {
        tmnxL2tpLnsSeMRtAddrType          InetAddressType,
        tmnxL2tpLnsSeMRtAddr              InetAddress,
        tmnxL2tpLnsSeMRtPrefixLen         InetAddressPrefixLength,
        tmnxL2tpLnsSeMRtStatus            TmnxManagedRouteStatus
    }
        
tmnxL2tpLnsSeMRtAddrType OBJECT-TYPE
    SYNTAX          InetAddressType
    MAX-ACCESS      not-accessible
    STATUS          obsolete
    DESCRIPTION     "The value of tmnxL2tpLnsSeMRtAddrType indicates
                     the address type of tmnxL2tpLnsSeMRtAddr."
    ::= { tmnxL2tpLnsSeMRtEntry 1 }

tmnxL2tpLnsSeMRtAddr OBJECT-TYPE
    SYNTAX          InetAddress (SIZE(4|16))
    MAX-ACCESS      not-accessible
    STATUS          obsolete
    DESCRIPTION     "The value of tmnxL2tpLnsSeMRtAddr indicates
                     the IP address of the managed route."
    ::= { tmnxL2tpLnsSeMRtEntry 2 }

tmnxL2tpLnsSeMRtPrefixLen OBJECT-TYPE
    SYNTAX          InetAddressPrefixLength
    MAX-ACCESS      not-accessible
    STATUS          obsolete
    DESCRIPTION     "The value of tmnxL2tpLnsSeMRtPrefixLen indicates
                     the prefix length of the subnet associated with
                     tmnxL2tpLnsSeMRtAddr."
    ::= { tmnxL2tpLnsSeMRtEntry 3 }

tmnxL2tpLnsSeMRtStatus OBJECT-TYPE
    SYNTAX          TmnxManagedRouteStatus
    MAX-ACCESS      read-only
    STATUS          obsolete
    DESCRIPTION     "The value of tmnxL2tpLnsSeMRtStatus indicates
                     the state of this managed route."
    ::= { tmnxL2tpLnsSeMRtEntry 4 }


--
--      The L2TP LNS Session Overrides Table
--

tmnxL2tpLnsSeOvrTable   OBJECT-TYPE
    SYNTAX      SEQUENCE OF TmnxL2tpLnsSeOvrEntry
    MAX-ACCESS  not-accessible
    STATUS      obsolete
    DESCRIPTION
       "The tmnxL2tpLnsSeOvrTable contains QoS (Quality of Service) overrides for 
        Layer Two Tunneling Protocol Sessions for which this system acts as LNS.

        This table is replaced with 
        TIMETRA-SUBSCRIBER-MGMT-MIB::tmnxSubPppOvrTable."
    ::= { tmnxL2tpSeStatObjs 6 }

tmnxL2tpLnsSeOvrEntry   OBJECT-TYPE
    SYNTAX      TmnxL2tpLnsSeOvrEntry
    MAX-ACCESS  not-accessible
    STATUS      obsolete
    DESCRIPTION
       "Each conceptual row represents QoS overrides information
        of an L2TP session for which this system acts as LNS."
    INDEX { vRtrID,
            tmnxL2tpSeStatusId,
            tmnxL2tpLnsSeOvrDirection,
            tmnxL2tpLnsSeOvrType,
            tmnxL2tpLnsSeOvrTypeId,
            tmnxL2tpLnsSeOvrTypeName }
    ::= { tmnxL2tpLnsSeOvrTable 1 }

TmnxL2tpLnsSeOvrEntry ::= 
    SEQUENCE {
        tmnxL2tpLnsSeOvrDirection         TDirection,
        tmnxL2tpLnsSeOvrType              TQosOverrideType,
        tmnxL2tpLnsSeOvrTypeId            Integer32,
        tmnxL2tpLnsSeOvrTypeName          TNamedItemOrEmpty,
        tmnxL2tpLnsSeOvrPIR               TPIRRateOverride,
        tmnxL2tpLnsSeOvrCIR               TCIRRateOverride,
        tmnxL2tpLnsSeOvrCBS               TBurstSizeBytesOverride,
        tmnxL2tpLnsSeOvrMBS               TBurstSizeBytesOverride
        
    }
        
tmnxL2tpLnsSeOvrDirection OBJECT-TYPE
    SYNTAX          TDirection ( 1 | 2 )
    MAX-ACCESS      not-accessible
    STATUS          obsolete
    DESCRIPTION     "The value of tmnxL2tpLnsSeOvrDirection indicates if
                     this row specifies ingress or egress qos override 
                     parameters."
    ::= { tmnxL2tpLnsSeOvrEntry 1 }

tmnxL2tpLnsSeOvrType OBJECT-TYPE
    SYNTAX          TQosOverrideType
    MAX-ACCESS      not-accessible
    STATUS          obsolete
    DESCRIPTION     "The value of tmnxL2tpLnsSeOvrType indicates what field
                     has been overridden by this row."
    ::= { tmnxL2tpLnsSeOvrEntry 2 }

tmnxL2tpLnsSeOvrTypeId OBJECT-TYPE
    SYNTAX          Integer32
    MAX-ACCESS      not-accessible
    STATUS          obsolete
    DESCRIPTION     "The value of tmnxL2tpLnsSeOvrTypeId indicates the ID of
                     the queue/policer that has been overridden by this row.
                     
                     If the value of tmnxL2tpLnsSeOvrType is not 'queue (1)'
                     or 'policer (2)', this field must be set to zero (0)."
    ::= { tmnxL2tpLnsSeOvrEntry 3 }

tmnxL2tpLnsSeOvrTypeName OBJECT-TYPE
    SYNTAX          TNamedItemOrEmpty
    MAX-ACCESS      not-accessible
    STATUS          obsolete
    DESCRIPTION     "The value of tmnxL2tpLnsSeOvrTypeName indicates the
                     name of the scheduler/arbiter that has been overridden by
                     this row.
                     
                     If the value of tmnxL2tpLnsSeOvrType is not 
                     'arbiter (4)' or 'scheduler (5)', this field must be set to
                     zero (0)."
    ::= { tmnxL2tpLnsSeOvrEntry 4 }

tmnxL2tpLnsSeOvrPIR OBJECT-TYPE
    SYNTAX          TPIRRateOverride
    MAX-ACCESS      read-only
    STATUS          obsolete
    DESCRIPTION     "The value of tmnxL2tpLnsSeOvrPIR indicates the PIR rate
                     in kbps allowed for the object overridden by this row."
    ::= { tmnxL2tpLnsSeOvrEntry 5 }

tmnxL2tpLnsSeOvrCIR OBJECT-TYPE
    SYNTAX          TCIRRateOverride
    MAX-ACCESS      read-only
    STATUS          obsolete
    DESCRIPTION     "The value of tmnxL2tpLnsSeOvrCIR indicates the CIR rate
                     in kbps allowed for the object overridden by this row."
    ::= { tmnxL2tpLnsSeOvrEntry 6 }

tmnxL2tpLnsSeOvrCBS OBJECT-TYPE
    SYNTAX          TBurstSizeBytesOverride
    MAX-ACCESS      read-only
    STATUS          obsolete
    DESCRIPTION     "The value of tmnxL2tpLnsSeOvrCBS indicates the amount of
                     reserved buffer space (in bytes) for the object
                     overridden by this row."
    ::= { tmnxL2tpLnsSeOvrEntry 7 }

tmnxL2tpLnsSeOvrMBS OBJECT-TYPE
    SYNTAX          TBurstSizeBytesOverride
    MAX-ACCESS      read-only
    STATUS          obsolete
    DESCRIPTION     "The value of tmnxL2tpLnsSeOvrMBS indicates the maximum
                     amount of reserved buffer space (in bytes) for the object
                     overridden by this row."
    ::= { tmnxL2tpLnsSeOvrEntry 8 }

--
--      The L2TP LNS Session Access Loop Encapsulation Table
--

tmnxL2tpLnsSeAleTableLastCh OBJECT-TYPE
    SYNTAX      TimeStamp
    MAX-ACCESS  read-only
    STATUS      obsolete
    DESCRIPTION
        "The value of the object tmnxL2tpLnsSeAleTableLastCh indicates
         the value of sysUpTime at the time of the last update of
         an entry in the tmnxL2tpLnsSeAleTable."
    ::= { tmnxL2tpObjs 21 }

tmnxL2tpLnsSeAleTable   OBJECT-TYPE
    SYNTAX      SEQUENCE OF TmnxL2tpLnsSeAleEntry
    MAX-ACCESS  not-accessible
    STATUS      obsolete
    DESCRIPTION
       "The tmnxL2tpLnsSeAleTable contains Access Loop Encapsulation information
        for Layer Two Tunneling Protocol Sessions for which this system 
        acts as LNS.

        This table is replaced with 
        TIMETRA-SUBSCRIBER-MGMT-MIB::tmnxSubPppAleTable."
    ::= { tmnxL2tpSeStatObjs 7 }

tmnxL2tpLnsSeAleEntry   OBJECT-TYPE
    SYNTAX      TmnxL2tpLnsSeAleEntry
    MAX-ACCESS  not-accessible
    STATUS      obsolete
    DESCRIPTION
       "Each conceptual row represents access loop encapsulation information
        of an L2TP session for which this system acts as LNS."
    INDEX { vRtrID,
            tmnxL2tpSeStatusId }
    ::= { tmnxL2tpLnsSeAleTable 1 }

TmnxL2tpLnsSeAleEntry ::= 
    SEQUENCE {
        tmnxL2tpLnsSeAleDatalink          TmnxAccessLoopEncapDataLink,
        tmnxL2tpLnsSeAleEncaps1           TmnxAccessLoopEncaps1,      
        tmnxL2tpLnsSeAleEncaps2           TmnxAccessLoopEncaps2               
    }
        
tmnxL2tpLnsSeAleDatalink OBJECT-TYPE
    SYNTAX          TmnxAccessLoopEncapDataLink
    MAX-ACCESS      read-only
    STATUS          obsolete
    DESCRIPTION     "The value of tmnxL2tpLnsSeAleDatalink indicates 
                     the data link used by the subscriber host 
                     on the DSL access loop."
    ::= { tmnxL2tpLnsSeAleEntry 1 }

tmnxL2tpLnsSeAleEncaps1 OBJECT-TYPE
    SYNTAX          TmnxAccessLoopEncaps1
    MAX-ACCESS      read-only
    STATUS          obsolete
    DESCRIPTION     "The value of tmnxL2tpLnsSeAleEncaps1 indicates 
                     the encapsulation used by the subscriber host 
                     on the DSL access loop."
    ::= { tmnxL2tpLnsSeAleEntry 2 }

tmnxL2tpLnsSeAleEncaps2 OBJECT-TYPE
    SYNTAX          TmnxAccessLoopEncaps2
    MAX-ACCESS      read-only
    STATUS          obsolete
    DESCRIPTION     "The value of tmnxL2tpLnsSeAleEncaps2 indicates 
                     the encapsulation used by the subscriber host 
                     on the DSL access loop."
    ::= { tmnxL2tpLnsSeAleEntry 3 }

--
--      The L2TP Session Operations Stop Table
--
--  Augmentation of the tmnxL2tpSeStatusTable
--  Use of AUGMENTS clause implies a one-to-one dependent relationship
--  between the base table, tmnxL2tpSeStatusTable, and the augmenting table,
--  tmnxL2tpSeStopTable. This in effect extends the tmnxL2tpSeStatusTable
--  with additional columns. Creation (or deletion) of a row in the
--  tmnxL2tpSeStatusTable results in the same fate for the row in the
--  tmnxL2tpSeStopTable.


tmnxL2tpSeStopTable   OBJECT-TYPE
    SYNTAX      SEQUENCE OF TmnxL2tpSeStopEntry
    MAX-ACCESS  not-accessible
    STATUS      current
    DESCRIPTION
       "The tmnxL2tpSeStopTable has an entry for each 
        active Layer Two Tunneling Protocol Session."
    ::= { tmnxL2tpSeOpObjs 1 }

tmnxL2tpSeStopEntry   OBJECT-TYPE
        SYNTAX          TmnxL2tpSeStopEntry
        MAX-ACCESS      not-accessible
        STATUS          current
        DESCRIPTION
       "Each conceptual row presents an operations interface to stop
        a Layer Two Tunneling Protocol session.

        Entries in this table are created and destroyed by the system."
    AUGMENTS { tmnxL2tpSeStatusEntry }
        ::= { tmnxL2tpSeStopTable 1 }

TmnxL2tpSeStopEntry ::= 
    SEQUENCE {
        tmnxL2tpSeStop                  TmnxActionType
    }

tmnxL2tpSeStop OBJECT-TYPE
    SYNTAX      TmnxActionType
    MAX-ACCESS  read-write
    STATUS      current
    DESCRIPTION
        "Setting this object to 'doAction (1)' triggers 
         an attempt to stop the control connection for this L2TP session.

         Reading this object returns the value 'notApplicable'."
    DEFVAL { notApplicable }
    ::= { tmnxL2tpSeStopEntry 1 }

-- ----------------------------------------------------------------------------
--      The "L2TP LNS ISA" Group
-- ----------------------------------------------------------------------------

tmnxL2tpLnsIsaGrpObjs        OBJECT IDENTIFIER ::= { tmnxL2tpLnsIsaObjs 1 }

--
--      The L2TP LNS ISA Group Table
--

tmnxL2tpIsaGrpTableLastCh OBJECT-TYPE
    SYNTAX      TimeStamp
    MAX-ACCESS  read-only
    STATUS      current
    DESCRIPTION
        "The value of the object tmnxL2tpIsaGrpTableLastCh indicates
         the value of sysUpTime at the time of the last modification of
         an entry in the tmnxL2tpIsaGrpTable."
    ::= { tmnxL2tpObjs 15 }

tmnxL2tpIsaGrpTable   OBJECT-TYPE
    SYNTAX      SEQUENCE OF TmnxL2tpIsaGrpEntry
    MAX-ACCESS  not-accessible
    STATUS      current
    DESCRIPTION
       "The tmnxL2tpIsaGrpTable contains objects to configure 
        L2TP Integrated Service Adaptor (ISA) Groups.
        
        The ISA Groups are used for the L2TP Network Server (LNS) function.
        
        An L2TP ISA group is used to represent multiple hardware 
        adaptors as a single entity, allowing for load balancing between 
        multiple L2TP ISA's."
    ::= { tmnxL2tpLnsIsaGrpObjs 1 }

tmnxL2tpIsaGrpEntry   OBJECT-TYPE
        SYNTAX          TmnxL2tpIsaGrpEntry
        MAX-ACCESS      not-accessible
        STATUS          current
        DESCRIPTION
       "Each conceptual row represents a Layer Two Tunneling Protocol
        Integrated Service Adaptor Group.

        Entries in this table can be created or deleted via SNMP operations."
    INDEX { tmnxL2tpIsaGrpId }
    ::= { tmnxL2tpIsaGrpTable 1 }

TmnxL2tpIsaGrpEntry ::= 
    SEQUENCE {
        tmnxL2tpIsaGrpId                 TmnxL2tpIsaGrpId,
        tmnxL2tpIsaGrpRowStatus          RowStatus,
        tmnxL2tpIsaGrpLastMgmtChange     TimeStamp,
        tmnxL2tpIsaGrpDescription        TItemDescription,
        tmnxL2tpIsaGrpAdminState         TmnxAdminState,
        tmnxL2tpIsaGrpOperState          TmnxOperState,
        tmnxL2tpIsaGrpPortPlcy           TNamedItemOrEmpty
    }
        
tmnxL2tpIsaGrpId OBJECT-TYPE
    SYNTAX      TmnxL2tpIsaGrpId
    MAX-ACCESS  not-accessible
    STATUS      current
    DESCRIPTION
       "The value of the object tmnxL2tpIsaGrpId specifies the identifier of
        the L2TP Integrated Service Adaptor group."
    ::= { tmnxL2tpIsaGrpEntry 1 }

tmnxL2tpIsaGrpRowStatus OBJECT-TYPE
    SYNTAX      RowStatus
    MAX-ACCESS  read-create
    STATUS      current
    DESCRIPTION
       "The value of tmnxL2tpIsaGrpRowStatus specifies the row status of
        this row."
    ::= { tmnxL2tpIsaGrpEntry 2 }

tmnxL2tpIsaGrpLastMgmtChange OBJECT-TYPE
    SYNTAX      TimeStamp
    MAX-ACCESS  read-only
    STATUS      current
    DESCRIPTION
        "The value of tmnxL2tpIsaGrpLastMgmtChange indicates the sysUpTime at
         the time of the most recent management-initiated change to this
         table row."
    ::= { tmnxL2tpIsaGrpEntry 3 }

tmnxL2tpIsaGrpDescription OBJECT-TYPE
    SYNTAX      TItemDescription
    MAX-ACCESS  read-create
    STATUS      current
    DESCRIPTION
       "The value of tmnxL2tpIsaGrpDescription specifies the
        description of this L2TP ISA group."
    DEFVAL { "" }
    ::= { tmnxL2tpIsaGrpEntry 4 }

tmnxL2tpIsaGrpAdminState OBJECT-TYPE
    SYNTAX      TmnxAdminState
    MAX-ACCESS  read-create
    STATUS      current
    DESCRIPTION
       "The value of tmnxL2tpIsaGrpAdminState specifies the
        administrative state of this L2TP ISA group."
    DEFVAL { outOfService }
    ::= { tmnxL2tpIsaGrpEntry 5 }

tmnxL2tpIsaGrpOperState  OBJECT-TYPE
    SYNTAX      TmnxOperState 
    MAX-ACCESS  read-only
    STATUS      current
    DESCRIPTION
        "The value of tmnxL2tpIsaGrpOperState indicates the operational 
         status of this L2TP ISA group."
    ::= { tmnxL2tpIsaGrpEntry 6 }

tmnxL2tpIsaGrpPortPlcy OBJECT-TYPE
    SYNTAX      TNamedItemOrEmpty
    MAX-ACCESS  read-create
    STATUS      current
    DESCRIPTION
       "The value of tmnxL2tpIsaGrpPortPlcy specifies the
        port policy of this L2TP ISA group.
        
        This object refers to a row in 
        the TIMETRA-PORT-MIB::tmnxPortPlcyTable.
        
        If a port policy is associated with an L2TP ISA group,
        ports created for this group can take applicable configuration
        from that port policy."
    DEFVAL { "" }
    ::= { tmnxL2tpIsaGrpEntry 8 }

--
--      The L2TP LNS ISA Group MDA Table
--

tmnxL2tpLnsIsaMdaObjs        OBJECT IDENTIFIER ::= { tmnxL2tpLnsIsaObjs 2 }

tmnxL2tpIsaMdaTableLastCh OBJECT-TYPE
    SYNTAX      TimeStamp
    MAX-ACCESS  read-only
    STATUS      current
    DESCRIPTION
        "The value of the object tmnxL2tpIsaMdaTableLastCh indicates
         the value of sysUpTime at the time of the last modification of
         an entry in the tmnxL2tpIsaMdaTable."
    ::= { tmnxL2tpObjs 16 }

tmnxL2tpIsaMdaTable   OBJECT-TYPE
    SYNTAX      SEQUENCE OF TmnxL2tpIsaMdaEntry
    MAX-ACCESS  not-accessible
    STATUS      current
    DESCRIPTION
       "The tmnxL2tpIsaMdaTable contains objects to configure 
        the L2TP ISA Group Media Dependent Adapters (MDA)."
    ::= { tmnxL2tpLnsIsaMdaObjs 1 }

tmnxL2tpIsaMdaEntry   OBJECT-TYPE
        SYNTAX          TmnxL2tpIsaMdaEntry
        MAX-ACCESS      not-accessible
        STATUS          current
        DESCRIPTION
       "Each conceptual row represents an L2TP 
        ISA Media Dependent Adapter (MDA) of an L2TP ISA Group.

        Entries in this table can be created or deleted via SNMP operations."
    INDEX { tmnxL2tpIsaGrpId ,
            tmnxChassisIndex, 
            tmnxCardSlotNum, 
            tmnxMDASlotNum }
    ::= { tmnxL2tpIsaMdaTable 1 }

TmnxL2tpIsaMdaEntry ::= 
    SEQUENCE {
        tmnxL2tpIsaMdaRowStatus          RowStatus,
        tmnxL2tpIsaMdaLastMgmtChange     TimeStamp,
        tmnxL2tpIsaMdaDrain              TruthValue,
        tmnxL2tpIsaMdaStop               TmnxActionType
    }
        
tmnxL2tpIsaMdaRowStatus OBJECT-TYPE
    SYNTAX      RowStatus
    MAX-ACCESS  read-create
    STATUS      current
    DESCRIPTION
       "The value of tmnxL2tpIsaMdaRowStatus specifies the row status of
        this row."
    ::= { tmnxL2tpIsaMdaEntry 1 }

tmnxL2tpIsaMdaLastMgmtChange OBJECT-TYPE
    SYNTAX      TimeStamp
    MAX-ACCESS  read-only
    STATUS      current
    DESCRIPTION
        "The value of tmnxL2tpIsaMdaLastMgmtChange indicates the sysUpTime at
         the time of the most recent management-initiated change to this
         table row."
    ::= { tmnxL2tpIsaMdaEntry 2 }

tmnxL2tpIsaMdaDrain   OBJECT-TYPE
    SYNTAX      TruthValue
    MAX-ACCESS  read-create
    STATUS      current
    DESCRIPTION
       "The value of tmnxL2tpIsaMdaDrain specifies 
        if this MDA is drained from LNS tunnels."
    ::= { tmnxL2tpIsaMdaEntry 3 }

tmnxL2tpIsaMdaStop   OBJECT-TYPE
    SYNTAX      TmnxActionType
    MAX-ACCESS  read-create
    STATUS      current
    DESCRIPTION
       "Setting the value of tmnxL2tpIsaMdaStop to 'doAction' triggers 
        an attempt to stop all PPP sessions on this L2TP ISA MDA.
        
        Reading the value of tmnxL2tpIsaMdaStop results in 'not-applicable'."
    ::= { tmnxL2tpIsaMdaEntry 4 }

--
--      The L2TP LNS ISA Group MDA Stat Table
--
--  Augmentation of the tmnxL2tpIsaMdaTable
--  Use of AUGMENTS clause implies a one-to-one dependent relationship
--  between the base table, tmnxL2tpIsaMdaTable, and the augmenting table,
--  tmnxL2tpIsaMdaStatTable. This in effect extends the tmnxL2tpIsaMdaTable
--  with additional columns. Creation (or deletion) of a row in the
--  tmnxL2tpIsaMdaTable results in the same fate for the row in the
--  tmnxL2tpIsaMdaStatTable.


tmnxL2tpLnsIsaMdaStatObjs        OBJECT IDENTIFIER ::= { tmnxL2tpLnsIsaObjs 3 }

tmnxL2tpIsaMdaStatTableLastCh OBJECT-TYPE
    SYNTAX      TimeStamp
    MAX-ACCESS  read-only
    STATUS      current
    DESCRIPTION
        "The value of the object tmnxL2tpIsaMdaStatTableLastCh indicates
         the value of sysUpTime at the time of the last modification of
         an entry in the tmnxL2tpIsaGrpTable."
    ::= { tmnxL2tpObjs 17 }

tmnxL2tpIsaMdaStatTable   OBJECT-TYPE
    SYNTAX      SEQUENCE OF TmnxL2tpIsaMdaStatEntry
    MAX-ACCESS  not-accessible
    STATUS      current
    DESCRIPTION
       "The tmnxL2tpIsaMdaStatTable contains status and statistics information 
        about the Media Dependent Adapters (MDA) of an L2TP ISA Group."
    ::= { tmnxL2tpLnsIsaMdaStatObjs 1 }

tmnxL2tpIsaMdaStatEntry   OBJECT-TYPE
        SYNTAX          TmnxL2tpIsaMdaStatEntry
        MAX-ACCESS      not-accessible
        STATUS          current
        DESCRIPTION
       "Each conceptual row contains status and statistics information
        about a Media Dependent Adapter (MDA) of an L2TP ISA Group.

        Entries in this table are created and removed automatically by the 
        system."
    AUGMENTS { tmnxL2tpIsaMdaEntry }
    ::= { tmnxL2tpIsaMdaStatTable 1 }

TmnxL2tpIsaMdaStatEntry ::= 
    SEQUENCE {
        tmnxL2tpIsaMdaStatOperState      TmnxL2tpIsaMdaOperState,
        tmnxL2tpIsaMdaStatSessions       Gauge32
    }
        
tmnxL2tpIsaMdaStatOperState OBJECT-TYPE
    SYNTAX      TmnxL2tpIsaMdaOperState
    MAX-ACCESS  read-only
    STATUS      current
    DESCRIPTION
       "The value of tmnxL2tpIsaMdaStatOperState indicates the
        operational state of this L2TP ISA MDA."
    ::= { tmnxL2tpIsaMdaStatEntry 1 }

tmnxL2tpIsaMdaStatSessions OBJECT-TYPE
    SYNTAX      Gauge32
    MAX-ACCESS  read-only
    STATUS      current
    DESCRIPTION
       "The value of tmnxL2tpIsaMdaStatOperState indicates the
        actual number of PPP sessions on this L2TP ISA MDA."
    ::= { tmnxL2tpIsaMdaStatEntry 2 }

--
--      The L2TP LNS ISA Group MDA Virtual Router Status Table
--

tmnxL2tpIsaMdaVRtrTable   OBJECT-TYPE
    SYNTAX      SEQUENCE OF TmnxL2tpIsaMdaVRtrEntry
    MAX-ACCESS  not-accessible
    STATUS      current
    DESCRIPTION
       "The tmnxL2tpIsaMdaVRtrTable contains status information about 
        the L2TP ISA Group Media Dependent Adapters (MDA) with respect to
        the associated Virtual Routers."
    ::= { tmnxL2tpLnsIsaMdaStatObjs 2 }

tmnxL2tpIsaMdaVRtrEntry   OBJECT-TYPE
        SYNTAX          TmnxL2tpIsaMdaVRtrEntry
        MAX-ACCESS      not-accessible
        STATUS          current
        DESCRIPTION
       "Each conceptual row represents the association of an L2TP 
        ISA Media Dependent Adapter (MDA) and a Virtual Router.

        Entries in this table are created and removed automatically by the 
        system."
    INDEX { tmnxL2tpIsaGrpId ,
            tmnxChassisIndex, 
            tmnxCardSlotNum, 
            tmnxMDASlotNum,
            vRtrID
          }
    ::= { tmnxL2tpIsaMdaVRtrTable 1 }

TmnxL2tpIsaMdaVRtrEntry ::= 
    SEQUENCE {
        tmnxL2tpIsaMdaVRtrOperState      TmnxOperState
    }
        
tmnxL2tpIsaMdaVRtrOperState OBJECT-TYPE
    SYNTAX      TmnxOperState
    MAX-ACCESS  read-only
    STATUS      current
    DESCRIPTION
        "The value of tmnxL2tpIsaMdaVRtrOperState indicates the operational
         state of this L2TP ISA MDA with respect to this Virtual Router."
    ::= { tmnxL2tpIsaMdaVRtrEntry 1 }


--
--      The L2TP LNS ISA Group MDA Statistics Table
--

tmnxL2tpLnsIsaMdaStatisticsObjs        OBJECT IDENTIFIER ::= { tmnxL2tpLnsIsaObjs 4 }

tmnxL2tpIsaMdaStatsTableLastCh OBJECT-TYPE
    SYNTAX      TimeStamp
    MAX-ACCESS  read-only
    STATUS      current
    DESCRIPTION
        "The value of the object tmnxL2tpIsaMdaStatsTableLastCh indicates
         the value of sysUpTime at the time of the last modification of
         an entry in the tmnxL2tpIsaMdaStatisticsTable."
    ::= { tmnxL2tpObjs 23 }

tmnxL2tpIsaMdaStatisticsTable   OBJECT-TYPE
    SYNTAX      SEQUENCE OF TmnxL2tpIsaMdaStatisticsEntry
    MAX-ACCESS  not-accessible
    STATUS      current
    DESCRIPTION
       "The tmnxL2tpIsaMdaStatisticsTable contains statistics information 
        about the Media Dependent Adapters (MDA) of an L2TP ISA Group."
    ::= { tmnxL2tpLnsIsaMdaStatisticsObjs 1 }

tmnxL2tpIsaMdaStatisticsEntry   OBJECT-TYPE
        SYNTAX          TmnxL2tpIsaMdaStatisticsEntry
        MAX-ACCESS      not-accessible
        STATUS          current
        DESCRIPTION
       "Each conceptual row contains statistics information
        about a Media Dependent Adapter (MDA) of an L2TP ISA Group.

        Entries in this table are created and removed automatically by the 
        system.
        
        Rows are only created where the statistics value is nonzero; 
        this allows faster walking through this table; hence, it is recommended
        to perform only get-next-request operations to retrieve information
        from this table."
    INDEX { tmnxL2tpIsaGrpId,
            tmnxChassisIndex, 
            tmnxCardSlotNum, 
            tmnxMDASlotNum,
            tmnxL2tpIsaMdaStatsInstance }
    ::= { tmnxL2tpIsaMdaStatisticsTable 1 }

TmnxL2tpIsaMdaStatisticsEntry ::= 
    SEQUENCE {
        tmnxL2tpIsaMdaStatsInstance      Unsigned32,
        tmnxL2tpIsaMdaStatsName          DisplayString,
        tmnxL2tpIsaMdaStatsVal           Counter32,
        tmnxL2tpIsaMdaStatsValHw         Counter32,
        tmnxL2tpIsaMdaStatsValue         Counter64
    }
    
tmnxL2tpIsaMdaStatsInstance OBJECT-TYPE
    SYNTAX      Unsigned32 (0..70)
    MAX-ACCESS  not-accessible
    STATUS      current
    DESCRIPTION 
       "The value of the object tmnxL2tpIsaMdaStatsInstance indicates
        the instance identifier of the statistics 
        contained in this conceptual row."
    ::= { tmnxL2tpIsaMdaStatisticsEntry 1 }
       
tmnxL2tpIsaMdaStatsName OBJECT-TYPE
    SYNTAX      DisplayString (SIZE (1..64))
    MAX-ACCESS  read-only
    STATUS      current
    DESCRIPTION 
       "The value of the object tmnxL2tpIsaMdaStatsName indicates
        the human-readable identifier of the statistics 
        contained in this conceptual row."
    ::= { tmnxL2tpIsaMdaStatisticsEntry 2 }

tmnxL2tpIsaMdaStatsVal OBJECT-TYPE
    SYNTAX      Counter32
    MAX-ACCESS  read-only
    STATUS      current
    DESCRIPTION 
       "The value of the object tmnxL2tpIsaMdaStatsVal indicates
        the lower 32-bits word of the statistics value 
        contained in this conceptual row."
    ::= { tmnxL2tpIsaMdaStatisticsEntry 3 }

tmnxL2tpIsaMdaStatsValHw OBJECT-TYPE
    SYNTAX      Counter32
    MAX-ACCESS  read-only
    STATUS      current
    DESCRIPTION 
       "The value of the object tmnxL2tpIsaMdaStatsValHw indicates
        the higher 32-bits word of the statistics value 
        contained in this conceptual row."
    ::= { tmnxL2tpIsaMdaStatisticsEntry 4 }

tmnxL2tpIsaMdaStatsValue OBJECT-TYPE
    SYNTAX      Counter64
    MAX-ACCESS  read-only
    STATUS      current
    DESCRIPTION 
       "The value of the object tmnxL2tpIsaMdaStatsValue indicates
        the value of the statistics contained in this conceptual row."
    ::= { tmnxL2tpIsaMdaStatisticsEntry 5 }        

-- ----------------------------------------------------------------------------
--      The "L2TP LNS Service" Group
-- ----------------------------------------------------------------------------

tmnxL2tpLnsIfObjs        OBJECT IDENTIFIER ::= { tmnxL2tpLnsSvcObjs 1 }

--
--      The L2TP LNS Interface Table
--
--      Sparse augment of the TIMETRA-SERV-MIB::iesIfTable

tmnxL2tpLnsIfTable   OBJECT-TYPE
    SYNTAX      SEQUENCE OF TmnxL2tpLnsIfEntry
    MAX-ACCESS  not-accessible
    STATUS      current
    DESCRIPTION
       "This table is supported for backwards compatibility; the
        recommended way to configure L2TP LNS Group-Interfaces is
        by means of the TIMETRA-SERV-MIB::svcIfSapCfgTable.
        
        The tmnxL2tpLnsIfTable contains objects to configure 
        L2TP LNS Group-Interfaces.
        
        Entries in this table are created and destroyed by the system.
        
        The system automatically creates an entry in this table for each
        entry in the TIMETRA-SERV-MIB::iesIfTable where the value of iesIfType
        is equal to 'group' and the value of 
        iesIfGroupInterfaceType is equal to 'lns'. 
        
        Deletion of such a row in the iesIfTable results in the same fate
        for the corresponding row in this table."
    ::= { tmnxL2tpLnsIfObjs 1 }

tmnxL2tpLnsIfEntry OBJECT-TYPE
    SYNTAX      TmnxL2tpLnsIfEntry
    MAX-ACCESS  not-accessible
    STATUS      current
    DESCRIPTION
        "L2TP LNS specific information about a specific group interface.
        
         Unlike regular subscriber traffic, that enters the system through
         Service Access Points (SAP) on a group-interface, 
         traffic for PPP subscriber sessions terminated by the LNS function, 
         enters the system through a plain layer 3 interface; 
         this traffic is relayed for processing to an L2TP ISA MDA; 
         it re-enters through an internal LNS group interface;
         this entry allows to configure subscriber management parameters for
         PPP subscriber sessions."
    INDEX { svcId, iesIfIndex }
    ::= { tmnxL2tpLnsIfTable 1 }

TmnxL2tpLnsIfEntry ::=
    SEQUENCE {
        tmnxL2tpLnsIfLastMgmtChange      TimeStamp,
        tmnxL2tpLnsIfDescription         TItemDescription,
        tmnxL2tpLnsIfDefSubProfile       TNamedItemOrEmpty,
        tmnxL2tpLnsIfDefSlaProfile       TNamedItemOrEmpty,
        tmnxL2tpLnsIfDefAppProfile       TNamedItemOrEmpty,
        tmnxL2tpLnsIfSubIdentPolicy      TNamedItemOrEmpty,
        tmnxL2tpLnsIfDefSubIdent         TmnxDefSubIdSource,
        tmnxL2tpLnsIfDefSubIdentString   DisplayString,
        tmnxL2tpLnsIfDefFilterProfile    TNamedItemOrEmpty
    }

tmnxL2tpLnsIfLastMgmtChange OBJECT-TYPE
    SYNTAX      TimeStamp
    MAX-ACCESS  read-only
    STATUS      current
    DESCRIPTION
        "The value of tmnxL2tpLnsIfLastMgmtChange indicates the sysUpTime at
         the time of the most recent management-initiated change to this
         table row."
    ::= { tmnxL2tpLnsIfEntry 1 }

tmnxL2tpLnsIfDescription OBJECT-TYPE
    SYNTAX      TItemDescription
    MAX-ACCESS  read-create
    STATUS      current
    DESCRIPTION
       "The value of tmnxL2tpLnsIfDescription specifies the
        description of this L2TP LNS interface."
    DEFVAL { "" }
    ::= { tmnxL2tpLnsIfEntry 2 }

tmnxL2tpLnsIfDefSubProfile OBJECT-TYPE
    SYNTAX      TNamedItemOrEmpty
    MAX-ACCESS  read-create
    STATUS      current
    DESCRIPTION
       "The value of tmnxL2tpLnsIfDefSubProfile specifies the
        default subscriber profile 
        of the subscribers of this LNS interface."
    DEFVAL { "" }
    ::= { tmnxL2tpLnsIfEntry 3 }

tmnxL2tpLnsIfDefSlaProfile OBJECT-TYPE
    SYNTAX      TNamedItemOrEmpty
    MAX-ACCESS  read-create
    STATUS      current
    DESCRIPTION
       "The value of tmnxL2tpLnsIfDefSlaProfile specifies the
        default SLA profile 
        of the subscribers of this LNS interface."
    DEFVAL { "" }
    ::= { tmnxL2tpLnsIfEntry 4 }

tmnxL2tpLnsIfDefAppProfile OBJECT-TYPE
    SYNTAX      TNamedItemOrEmpty
    MAX-ACCESS  read-create
    STATUS      current
    DESCRIPTION
       "The value of tmnxL2tpLnsIfDefSlaProfile specifies the
        default application profile 
        of the subscribers of this LNS interface."
    DEFVAL { "" }
    ::= { tmnxL2tpLnsIfEntry 5 }

tmnxL2tpLnsIfSubIdentPolicy OBJECT-TYPE
    SYNTAX      TNamedItemOrEmpty
    MAX-ACCESS  read-create
    STATUS      current
    DESCRIPTION
       "The value of tmnxL2tpLnsIfSubIdentPolicy specifies the
        subscriber identification policy 
        of the subscribers of this LNS interface."
    DEFVAL { "" }
    ::= { tmnxL2tpLnsIfEntry 6 }

tmnxL2tpLnsIfDefSubIdent OBJECT-TYPE
    SYNTAX      TmnxDefSubIdSource
    MAX-ACCESS  read-create
    STATUS      current
    DESCRIPTION
       "The value of tmnxL2tpLnsIfDefSubIdent specifies the
        default subscriber identification 
        of the subscribers of this LNS interface.
        This value is used in case no other source (like Radius) provides a 
        subscriber identification string.

        If the value of this object is set to 'useSapId', the SAP-id will
        be used as the default subscriber identification string; in this case,
        tmnxL2tpLnsIfDefSubIdentString must contain the empty string, so any
        non-empty string in tmnxL2tpLnsIfDefSubIdentString will be set to an 
        empty string.

        If the value of this object is set to 'useAutoId',
        the auto-generated subscriber identification string, as defined in
        tmnxSubMgmtAutoSubIdObjs, is used as the default subscriber
        identification string. In this case, tmnxL2tpLnsIfDefSubIdentString
        must contain the empty string, so any non-empty string in
        tmnxL2tpLnsIfDefSubIdentString will be set to an empty string.

        If the value of this object is set to 'useString', the value of
        tmnxL2tpLnsIfDefSubIdentString will be used as the default subscriber 
        identification string; in this case, an empty 
        tmnxL2tpLnsIfDefSubIdentString means that there is no default subscriber 
        identification configured."
    DEFVAL { useString }
    ::= { tmnxL2tpLnsIfEntry 7 }

tmnxL2tpLnsIfDefSubIdentString OBJECT-TYPE
    SYNTAX      DisplayString (SIZE (0..32))
    MAX-ACCESS  read-create
    STATUS      current
    DESCRIPTION
       "The value of tmnxL2tpLnsIfDefSubIdentString specifies the
        default subscriber identification string 
        applicable on the subscribers of this LNS interface."
    DEFVAL { "" }
    ::= { tmnxL2tpLnsIfEntry 8 }

tmnxL2tpLnsIfDefFilterProfile OBJECT-TYPE
    SYNTAX      TNamedItemOrEmpty
    MAX-ACCESS  read-create
    STATUS      current
    DESCRIPTION 
       "The value of the object tmnxL2tpLnsIfDefFilterProfile specifies the
        default filter profile for this LNS interface. The specified filter
        profile needs to exists in the
        TIMETRA-SUBSCRIBER-MGMT-MIB::tmnxSubFilterProfileTable."
    DEFVAL { "" }
    ::= { tmnxL2tpLnsIfEntry 9 }

-- ----------------------------------------------------------------------------
--      The "L2TP MLPPP" Group
-- ----------------------------------------------------------------------------

--
--      The L2TP LAC MLPPP Bundle Table
--

tmnxL2tpLacMlpppBundleTable   OBJECT-TYPE
    SYNTAX      SEQUENCE OF TmnxL2tpLacMlpppBundleEntry
    MAX-ACCESS  not-accessible
    STATUS      current
    DESCRIPTION
       "The tmnxL2tpLacMlpppBundleTable allows monitoring of 
        MLPPP (Multi Link PPP) bundles of PPP sessions where this system
        acts as a LAC."
    ::= { tmnxL2tpMlpppObjs 1 }

tmnxL2tpLacMlpppBundleEntry   OBJECT-TYPE
    SYNTAX      TmnxL2tpLacMlpppBundleEntry
    MAX-ACCESS  not-accessible
    STATUS      current
    DESCRIPTION
       "Each conceptual row represents an MLPPP Bundle associated with
        PPP sessions for which this system acts as a LAC.

        Entries in this table are created and destroyed by the system."
    INDEX { vRtrID,
            tmnxL2tpLacMlpppBundleIndex }
    ::= { tmnxL2tpLacMlpppBundleTable 1 }

TmnxL2tpLacMlpppBundleEntry ::= 
    SEQUENCE {
        tmnxL2tpLacMlpppBundleIndex      Unsigned32,
        tmnxL2tpLacMlpppBundleSvcId      TmnxServId,
        tmnxL2tpLacMlpppBundleFwdTuId    TmnxL2tpTunnelId,
        tmnxL2tpLacMlpppBundleUserName   TmnxPppoeUserNameOrEmpty,
        tmnxL2tpLacMlpppBundleLocEpClass TmnxMlpppEpClass,
        tmnxL2tpLacMlpppBundleLocEpAddr  OCTET STRING,
        tmnxL2tpLacMlpppBundleRemEpClass TmnxMlpppEpClass,
        tmnxL2tpLacMlpppBundleRemEpAddr  OCTET STRING
    }
        
tmnxL2tpLacMlpppBundleIndex OBJECT-TYPE
    SYNTAX      Unsigned32
    MAX-ACCESS  not-accessible
    STATUS      current
    DESCRIPTION
       "The value of the object tmnxL2tpLacMlpppBundleIndex indicates the local  
        identifier of this MLPPP Bundle."
    ::= { tmnxL2tpLacMlpppBundleEntry 1 }

tmnxL2tpLacMlpppBundleSvcId OBJECT-TYPE
    SYNTAX      TmnxServId
    MAX-ACCESS  read-only
    STATUS      current
    DESCRIPTION
        "The value of tmnxL2tpLacMlpppBundleSvcId indicates the service ID of
         the IES/VPRN service to which this MLPPP bundle belongs."
    ::= { tmnxL2tpLacMlpppBundleEntry 2 }

tmnxL2tpLacMlpppBundleFwdTuId OBJECT-TYPE
    SYNTAX      TmnxL2tpTunnelId
    MAX-ACCESS  read-only
    STATUS      current
    DESCRIPTION
       "The value of tmnxL2tpLacMlpppBundleFwdTuId indicates the
        LTS (L2TP Tunnel Stitching) tunnel ID if this bundle is associated
        with PPP sessions that are stitched to another L2TP tunnel.
        
        Otherwise, the value of tmnxL2tpLacMlpppBundleFwdTuId is equal to zero."
    ::= { tmnxL2tpLacMlpppBundleEntry 3 }

tmnxL2tpLacMlpppBundleUserName OBJECT-TYPE
    SYNTAX      TmnxPppoeUserNameOrEmpty
    MAX-ACCESS  read-only
    STATUS      current
    DESCRIPTION
        "The value of tmnxL2tpLacMlpppBundleUserName indicates the user name
         of the subscriber associated with this MLPPP bundle, or another string
         used to identify that subscriber."
    ::= { tmnxL2tpLacMlpppBundleEntry 4 }

tmnxL2tpLacMlpppBundleLocEpClass OBJECT-TYPE
    SYNTAX      TmnxMlpppEpClass
    MAX-ACCESS  read-only
    STATUS      current
    DESCRIPTION
       "The value of tmnxL2tpLacMlpppBundleLocEpClass indicates the
        address class of the local endpoint.
        
        If the value of tmnxL2tpLacMlpppBundleLocEpClass is equal to 'null',
        the address class of the MLPPP Endpoint Discriminator option was not
        present in a received Configure-Request."
    REFERENCE
       "RFC 1990 The PPP Multilink Protocol (MP), 
        section 5.1.3 Endpoint Discriminator Option."
    ::= { tmnxL2tpLacMlpppBundleEntry 5 }

tmnxL2tpLacMlpppBundleLocEpAddr OBJECT-TYPE
    SYNTAX      OCTET STRING(SIZE(0..20))
    MAX-ACCESS  read-only
    STATUS      current
    DESCRIPTION
       "The value of tmnxL2tpLacMlpppBundleLocEpAddr indicates the
        address of the local MLPPP Endpoint.
        
        Its interpretation depends on the value of tmnxL2tpLacMlpppBundleLocEpClass."
    REFERENCE
       "RFC 1990 The PPP Multilink Protocol (MP), 
        section 5.1.3 Endpoint Discriminator Option."
    ::= { tmnxL2tpLacMlpppBundleEntry 6 }

tmnxL2tpLacMlpppBundleRemEpClass OBJECT-TYPE
    SYNTAX      TmnxMlpppEpClass
    MAX-ACCESS  read-only
    STATUS      current
    DESCRIPTION
       "The value of tmnxL2tpLacMlpppBundleRemEpClass indicates the
        address class of the local endpoint.
        
        If the value of tmnxL2tpLacMlpppBundleRemEpClass is equal to 'null',
        the address class of the MLPPP Endpoint Discriminator option was not
        present in a received Configure-Request."
    REFERENCE
       "RFC 1990 The PPP Multilink Protocol (MP), 
        section 5.1.3 Endpoint Discriminator Option."
    ::= { tmnxL2tpLacMlpppBundleEntry 7 }

tmnxL2tpLacMlpppBundleRemEpAddr OBJECT-TYPE
    SYNTAX      OCTET STRING(SIZE(0..20))
    MAX-ACCESS  read-only
    STATUS      current
    DESCRIPTION
       "The value of tmnxL2tpLacMlpppBundleRemEpAddr indicates the
        address of the local MLPPP Endpoint.
        
        Its interpretation depends on the value of tmnxL2tpLacMlpppBundleRemEpClass."
    REFERENCE
       "RFC 1990 The PPP Multilink Protocol (MP), 
        section 5.1.3 Endpoint Discriminator Option."
    ::= { tmnxL2tpLacMlpppBundleEntry 8 }
    
--
--      The L2TP LAC MLPPP Link Table
--

tmnxL2tpLacMlpppLinkTable   OBJECT-TYPE
    SYNTAX      SEQUENCE OF TmnxL2tpLacMlpppLinkEntry
    MAX-ACCESS  not-accessible
    STATUS      current
    DESCRIPTION
       "The tmnxL2tpLacMlpppLinkTable contains
        the subscriber MLPPP (Multi Link PPP) links where this system
        acts as a LAC, ordered per bundle."
    REFERENCE "RFC 1990 The PPP Multilink Protocol"
    ::= { tmnxL2tpMlpppObjs 2 }

tmnxL2tpLacMlpppLinkEntry   OBJECT-TYPE
    SYNTAX      TmnxL2tpLacMlpppLinkEntry
    MAX-ACCESS  not-accessible
    STATUS      current
    DESCRIPTION
       "Each conceptual row represents an MLPPP Link associated with
        a PPP session for which this system acts as a LAC.

        Entries in this table are created and destroyed by the system."
    INDEX { vRtrID,
            tmnxL2tpLacMlpppBundleIndex,
            tmnxL2tpSeStatusId
          }
        
    ::= { tmnxL2tpLacMlpppLinkTable 1 }

TmnxL2tpLacMlpppLinkEntry ::= 
    SEQUENCE {
        tmnxL2tpLacMlpppLinkState        TmnxL2tpSeOperState
    }
        
tmnxL2tpLacMlpppLinkState OBJECT-TYPE
    SYNTAX      TmnxL2tpSeOperState
    MAX-ACCESS  read-only
    STATUS      current
    DESCRIPTION
        "The value of tmnxL2tpLacMlpppLinkState indicates 
         the operational state of the session associated with this MLPPP link."
    ::= { tmnxL2tpLacMlpppLinkEntry 1 }

-- ----------------------------------------------------------------------------
--      The L2TP Accounting Group
-- ----------------------------------------------------------------------------
--
-- The L2TP Accounting Policy table
-- --------------------------------------------------------

tmnxL2tpApTable OBJECT-TYPE
    SYNTAX      SEQUENCE OF TmnxL2tpApEntry
    MAX-ACCESS  not-accessible
    STATUS      current
    DESCRIPTION
        "The tmnxL2tpApTable allows configuration of RADIUS based
         accounting policies for L2TP (Layer Two Tunneling Protocol)
         tunnel accounting."
    ::= { tmnxL2tpAccountingObjs 1 }

tmnxL2tpApEntry OBJECT-TYPE
    SYNTAX      TmnxL2tpApEntry
    MAX-ACCESS  not-accessible
    STATUS      current
    DESCRIPTION
        "Each entry represents the configuration for 
         an L2TP RADIUS Accounting Policy.
         
         Entries in this table can be created and deleted via SNMP SET
         operations to tmnxL2tpApRowStatus."
    INDEX { tmnxL2tpApName }
    ::= { tmnxL2tpApTable 1 }

TmnxL2tpApEntry ::=
    SEQUENCE {
        tmnxL2tpApName                TNamedItem,
        tmnxL2tpApRowStatus           RowStatus,
        tmnxL2tpApLastMgmtChange      TimeStamp,
        tmnxL2tpApDescription         TItemDescription,
        tmnxL2tpApType                BITS,
        tmnxL2tpApServerVRtrID        TmnxVRtrIDOrZero,
        tmnxL2tpApServerAlgorithm     TmnxSubRadServAlgorithm,
        tmnxL2tpApServerRetry         Unsigned32,
        tmnxL2tpApServerSrcAddrType   InetAddressType,
        tmnxL2tpApServerSrcAddr       InetAddress,
        tmnxL2tpApServerTimeout       Unsigned32,
        tmnxL2tpApIncludeAttributes   BITS,
        tmnxL2tpApRequestScriptPlcy   TNamedItemOrEmpty,
        tmnxL2tpApNasPortIdPfixType   TmnxSubNasPortPrefixType,
        tmnxL2tpApNasPortIdPfixString DisplayString,
        tmnxL2tpApNasPortIdSfixType   TmnxSubNasPortSuffixType,
        tmnxL2tpApNasPortTypeType     TmnxSubNasPortTypeType,
        tmnxL2tpApNasPortTypeValue    Unsigned32,
        tmnxL2tpApNasPortBitspec      TmnxBinarySpecification,
        tmnxL2tpApRadServPlcy         TNamedItemOrEmpty
    }
    
tmnxL2tpApName OBJECT-TYPE
    SYNTAX      TNamedItem
    MAX-ACCESS  not-accessible
    STATUS      current
    DESCRIPTION
        "The value of tmnxL2tpApName specifies the name of an
         L2TP RADIUS Accounting Policy."
    ::= { tmnxL2tpApEntry 1 }

tmnxL2tpApRowStatus OBJECT-TYPE
    SYNTAX      RowStatus
    MAX-ACCESS  read-create
    STATUS      current
    DESCRIPTION
        "The value of tmnxL2tpApRowStatus controls the creation and
         deletion of rows in the table. 
         
         An attempt to delete a row that is
         referred to will fail with an inconsistentValue error."
    ::= { tmnxL2tpApEntry 2 }

tmnxL2tpApLastMgmtChange OBJECT-TYPE
    SYNTAX      TimeStamp
    MAX-ACCESS  read-only
    STATUS      current
    DESCRIPTION
        "The value of tmnxL2tpApLastMgmtChange indicates the sysUpTime at
         the time of the most recent management-initiated change to this
         policy."
    ::= { tmnxL2tpApEntry 3 }

tmnxL2tpApDescription OBJECT-TYPE
    SYNTAX      TItemDescription
    MAX-ACCESS  read-create
    STATUS      current
    DESCRIPTION
        "The value of tmnxL2tpApDescription specifies the user provided
         description of this policy."
    DEFVAL { "" }
    ::= { tmnxL2tpApEntry 4 }

tmnxL2tpApType OBJECT-TYPE
    SYNTAX      BITS { 
        session (0),
        tunnel  (1)
    }
    MAX-ACCESS  read-create
    STATUS      current
    DESCRIPTION
        "The value of tmnxL2tpApType specifies the type of accounting
         for the L2TP tunnels associated with this policy."
    DEFVAL { { session, tunnel } }
    ::= { tmnxL2tpApEntry 5 }

tmnxL2tpApServerVRtrID OBJECT-TYPE
    SYNTAX      TmnxVRtrIDOrZero
    MAX-ACCESS  read-create
    STATUS      current
    DESCRIPTION
        "The value of tmnxL2tpApServerVRtrID specifies the virtual router
         instance applicable for the set of configured RADIUS servers
         (tmnxL2tpApRadServTable). 
         
         The value of this object cannot be changed once a RADIUS server is 
         configured for this policy.
         
         When the value is '0', both base and management router instances are
         available."
    DEFVAL { 0 }
    ::= { tmnxL2tpApEntry 6 }

tmnxL2tpApServerAlgorithm OBJECT-TYPE
    SYNTAX      TmnxSubRadServAlgorithm {
                    direct     (1),
                    roundRobin (2)
                }
    MAX-ACCESS  read-create
    STATUS      current
    DESCRIPTION
        "The value of tmnxL2tpApServerAlgorithm specifies the algorithm
         used to select a RADIUS server from the list of configured servers
         (tmnxL2tpApRadServTable)."
    DEFVAL { direct }
    ::= { tmnxL2tpApEntry 7 }

tmnxL2tpApServerRetry OBJECT-TYPE
    SYNTAX      Unsigned32 (1..10)
    MAX-ACCESS  read-create
    STATUS      current
    DESCRIPTION
        "The value of tmnxL2tpApServerRetry specifies the number of RADIUS
         requests towards the same RADIUS server."
    DEFVAL { 3 }
    ::= { tmnxL2tpApEntry 8 }

tmnxL2tpApServerSrcAddrType OBJECT-TYPE
    SYNTAX      InetAddressType
    MAX-ACCESS  read-create
    STATUS      current
    DESCRIPTION
        "The value of tmnxL2tpApServerSrcAddrType specifies the type of
         address stored in tmnxL2tpApServerSrcAddr."
    DEFVAL { unknown }
    ::= { tmnxL2tpApEntry 9 }

tmnxL2tpApServerSrcAddr OBJECT-TYPE
    SYNTAX      InetAddress (SIZE(0|4|16))
    MAX-ACCESS  read-create
    STATUS      current
    DESCRIPTION
        "The value of tmnxL2tpApServerSrcAddr specifies the source address
         of a RADIUS packet for L2TP accounting; it must be a valid
         unicast address (otherwise a wrongValue error is returned).

         If this object is configured with the address of a router interface
         (ref TIMETRA-VRTR-MIB::vRiaIpAddress) the RADIUS client uses it while
         making a request to the server.

         If the address is not configured or is not the address of one of the
         interfaces, the source address is based on the address of the RADIUS
         server; if the server address is in-band, the client uses the system
         IP address; if it is out-of-band, the source address is the address of
         the management interface (the addresses can be found in
         TIMETRA-VRTR-MIB::vRiaIpAddress)."
    DEFVAL { ''H }  
    ::= { tmnxL2tpApEntry 10 }

tmnxL2tpApServerTimeout OBJECT-TYPE
    SYNTAX      Unsigned32 (1..90)
    UNITS       "seconds"
    MAX-ACCESS  read-create
    STATUS      current
    DESCRIPTION
        "The value of tmnxL2tpApServerTimeout specifies the
         timeout between retries towards the same RADIUS server."
    DEFVAL { 5 }
    ::= { tmnxL2tpApEntry 11 }

tmnxL2tpApIncludeAttributes OBJECT-TYPE
    SYNTAX      BITS {
                    nasIdentifier                    (0),
                    nasPort                          (1),
                    nasPortId                        (2),
                    nasPortType                      (3)
                }
    MAX-ACCESS  read-create
    STATUS      current
    DESCRIPTION
        "The value of tmnxL2tpApIncludeAttributes specifies what RADIUS
         attributes the system should include into RADIUS accounting messages."
    DEFVAL { '0'H }
    ::= { tmnxL2tpApEntry 12 }

tmnxL2tpApRequestScriptPlcy OBJECT-TYPE
    SYNTAX      TNamedItemOrEmpty
    MAX-ACCESS  read-create
    STATUS      current
    DESCRIPTION
       "The value of tmnxL2tpApRequestScriptPlcy specifies
        the RADIUS script policy used to change the RADIUS attributes of the
        outgoing Accounting-Request messages."
    DEFVAL    { "" }
    ::= { tmnxL2tpApEntry 13 }

tmnxL2tpApNasPortIdPfixType OBJECT-TYPE
    SYNTAX      TmnxSubNasPortPrefixType
    MAX-ACCESS  read-create
    STATUS      current
    DESCRIPTION
        "The value of tmnxL2tpApNasPortIdPfixType specifies what type of
         prefix will be added to the NAS-Port-Id attribute if included in RADIUS
         accounting-request messages.
         
         This field is only applicable if the 'nasPortId' bit is set in
         tmnxL2tpApIncludeAttributes."
    DEFVAL { none }
    ::= { tmnxL2tpApEntry 14 }

tmnxL2tpApNasPortIdPfixString OBJECT-TYPE
    SYNTAX      DisplayString (SIZE (0..8))
    MAX-ACCESS  read-create
    STATUS      current
    DESCRIPTION
        "The value of tmnxL2tpApNasPortIdPfixString specifies
         the user configurable string to be added as prefix to 
         the NAS-Port-Id attribute 
         if included in RADIUS accounting-request messages.
         
         This field is only applicable if the 'nasPortId' bit is set in
         tmnxL2tpApIncludeAttributes and tmnxL2tpApNasPortIdPfixType
         is set to 'userString'."
    DEFVAL { "" }
    ::= { tmnxL2tpApEntry 15 }

tmnxL2tpApNasPortIdSfixType OBJECT-TYPE
    SYNTAX      TmnxSubNasPortSuffixType
    MAX-ACCESS  read-create
    STATUS      current
    DESCRIPTION
        "The value of tmnxL2tpApNasPortIdSfixType specifies what type of
         suffix will be added to the NAS-Port-Id attribute if included in RADIUS
         accounting-request messages.
         
         This field is only applicable if the 'nasPortId' bit is set in
         tmnxL2tpApIncludeAttributes."
    DEFVAL { none }
    ::= { tmnxL2tpApEntry 16 }

tmnxL2tpApNasPortTypeType OBJECT-TYPE
    SYNTAX      TmnxSubNasPortTypeType
    MAX-ACCESS  read-create
    STATUS      current
    DESCRIPTION
        "The value of tmnxL2tpApNasPortTypeType specifies 
         what kind of value will be put in the RADIUS NAS-Port-Type attribute 
         if included in RADIUS accounting-request messages.

         This field is only applicable if the 'nasPortType'
         bit is set in tmnxL2tpApIncludeAttributes."
    DEFVAL { standard }
    ::= { tmnxL2tpApEntry 17 }

tmnxL2tpApNasPortTypeValue OBJECT-TYPE
    SYNTAX      Unsigned32 (0..255)
    MAX-ACCESS  read-create
    STATUS      current
    DESCRIPTION
        "The value of tmnxL2tpApNasPortTypeValue specifies
         what value will be put in the RADIUS NAS-Port-Type attribute 
         if included in RADIUS accounting-request messages.

         This field is only applicable if the 'nasPortType' 
         bit is set in tmnxL2tpApIncludeAttributes and the value of the object 
         tmnxL2tpApNasPortTypeType is equal to 'config'."
    DEFVAL { 0 }
    ::= { tmnxL2tpApEntry 18 }

tmnxL2tpApNasPortBitspec OBJECT-TYPE
    SYNTAX      TmnxBinarySpecification
    MAX-ACCESS  read-create
    STATUS      current
    DESCRIPTION
        "The value of tmnxL2tpApNasPortBitspec specifies
         what number will be put in the RADIUS NAS-Port 
         attribute if included in RADIUS accounting-request messages.

         This field is only applicable if the 'nasPort' bit is set in
         tmnxL2tpApIncludeAttributes.
         
         <origin>               ::= 'o' | 'i' | 's' | 'm' | 'p' | 'v' | 'c'

         'c' - ATM VCI (Virtual Channel Identifier)
         'i' - inner VLAN ID
         'm' - MDA number
         'o' - outer VLAN ID
         'p' - port number
         's' - slot number
         'v' - ATM VPI (Virtual Path Identifier)

         Maximum 32 bits can be specified.
         
         If less than 32 bits are specified, the least significant bits are
         used and the omitted higher bits are set to zero.
         
         Example:  *12o*12i*2s01 means 'the 12 least significant bits of the
         outer VLAN ID, followed by the 12 least significant bits of the inner
         VLAN ID, followed by the two least significant bits of the slot number,
         followed by a zero and a one-bit', stored in network order in the least
         significant bits: 0000ooooooooooooiiiiiiiiiiiiss01."
    DEFVAL { "" }
    ::= { tmnxL2tpApEntry 19 }

tmnxL2tpApRadServPlcy OBJECT-TYPE
   SYNTAX      TNamedItemOrEmpty
   MAX-ACCESS  read-create
   STATUS      current
   DESCRIPTION
       "The value of tmnxL2tpApRadServPlcy specifies the RADIUS server policy 
        defined in TIMETRA-RADIUS-MIB::tmnxRadSrvPlcyTable."
   DEFVAL { "" }
   ::= { tmnxL2tpApEntry 20 }
   
-- --------------------------------------------------------
-- The L2TP Accounting Server table
-- --------------------------------------------------------
tmnxL2tpApServTable OBJECT-TYPE
    SYNTAX      SEQUENCE OF TmnxL2tpApServEntry
    MAX-ACCESS  not-accessible
    STATUS      current
    DESCRIPTION
        "The tmnxL2tpApServTable allows the configuration of objects
         related to a particular RADIUS server associated with a particular
         L2TP RADIUS Accounting Policy."
    ::= { tmnxL2tpAccountingObjs 2 }

tmnxL2tpApServEntry OBJECT-TYPE
    SYNTAX      TmnxL2tpApServEntry
    MAX-ACCESS  not-accessible
    STATUS      current
    DESCRIPTION
        "Each entry represents the configuration for a particular RADIUS server. 
        
         Entries in this table can be created and deleted
         via SNMP SET operations to tmnxL2tpApServRowStatus."
    INDEX { tmnxL2tpApName,
            tmnxL2tpApServIndex }
    ::= { tmnxL2tpApServTable 1 }

TmnxL2tpApServEntry ::=
    SEQUENCE {
        tmnxL2tpApServIndex           Unsigned32,
        tmnxL2tpApServRowStatus       RowStatus,
        tmnxL2tpApServLastMgmtChange  TimeStamp,
        tmnxL2tpApServAddrType        InetAddressType,
        tmnxL2tpApServAddr            InetAddress,
        tmnxL2tpApServSecret          DisplayString,
        tmnxL2tpApServAcctPort        Unsigned32,
        tmnxL2tpApServOperState       TmnxOperState
    }

tmnxL2tpApServIndex OBJECT-TYPE
    SYNTAX      Unsigned32 (1..5)
    MAX-ACCESS  not-accessible
    STATUS      current
    DESCRIPTION
        "The value of tmnxL2tpApServIndex specifies the index
         of this RADIUS server in the set of servers associated with this
         L2TP accounting policy."
   ::= { tmnxL2tpApServEntry 1 }

tmnxL2tpApServRowStatus OBJECT-TYPE
    SYNTAX      RowStatus
    MAX-ACCESS  read-create
    STATUS      current
    DESCRIPTION
        "The value of tmnxL2tpApServRowStatus controls the creation and
         deletion of rows in the table."
    ::= { tmnxL2tpApServEntry 2 }

tmnxL2tpApServLastMgmtChange OBJECT-TYPE
    SYNTAX      TimeStamp
    MAX-ACCESS  read-only
    STATUS      current
    DESCRIPTION
        "The value tmnxL2tpApServLastMgmtChange indicates the sysUpTime at
         the time of the most recent management-initiated change to this
         conceptual row."
    ::= { tmnxL2tpApServEntry 3 }

tmnxL2tpApServAddrType OBJECT-TYPE
    SYNTAX      InetAddressType
    MAX-ACCESS  read-create
    STATUS      current
    DESCRIPTION
        "The value of tmnxL2tpApServAddrType specifies the type of
         address stored in tmnxL2tpApServAddr."
    ::= { tmnxL2tpApServEntry 5 }

tmnxL2tpApServAddr OBJECT-TYPE
    SYNTAX      InetAddress (SIZE(4|16))
    MAX-ACCESS  read-create
    STATUS      current
    DESCRIPTION
        "The value of tmnxL2tpApServAddr specifies the IP address of
         the RADIUS server. 
         
         A valid unicast IP address must be specified at row creation time."
    ::= { tmnxL2tpApServEntry 6 }

tmnxL2tpApServSecret OBJECT-TYPE
    SYNTAX      DisplayString (SIZE (0|1..20))
    MAX-ACCESS  read-create
    STATUS      current
    DESCRIPTION
        "The value of tmnxL2tpApServSecret specifies the secret key
         associated with the RADIUS server. 
         
         A non-empty value must be specified at row creation time. 
         
         An SNMP get request on this object always returns an empty string."
    ::= { tmnxL2tpApServEntry 7 }

tmnxL2tpApServAcctPort OBJECT-TYPE
    SYNTAX      Unsigned32 (1..65535)
    MAX-ACCESS  read-create
    STATUS      current
    DESCRIPTION
        "The value of tmnxL2tpApServAcctPort specifies the UDP port
         number on which to contact the RADIUS server for accounting."
    DEFVAL { 1813 }
    ::= { tmnxL2tpApServEntry 8 }

tmnxL2tpApServOperState OBJECT-TYPE
    SYNTAX      TmnxOperState
    MAX-ACCESS  read-only
    STATUS      current
    DESCRIPTION
        "The value of tmnxL2tpApServOperState indicates the operational
         state of the RADIUS server."
    ::= { tmnxL2tpApServEntry 9 }

-- --------------------------------------------------------
-- The L2TP Accounting Server Statistics table
-- --------------------------------------------------------

tmnxL2tpApServStatsTable OBJECT-TYPE
    SYNTAX      SEQUENCE OF TmnxL2tpApServStatsEntry
    MAX-ACCESS  not-accessible
    STATUS      current
    DESCRIPTION
        "The tmnxL2tpApServStatsTable presents statistics of
         l2tp-accounting-policies' RADIUS servers."
    ::= { tmnxL2tpAccountingObjs 3 }

tmnxL2tpApServStatsEntry OBJECT-TYPE
    SYNTAX      TmnxL2tpApServStatsEntry
    MAX-ACCESS  not-accessible
    STATUS      current
    DESCRIPTION
        "Each row represents statistics about a specific server
         of a specify L2TP accounting policy. 
         
         Rows in this table are created automatically by the system."
    AUGMENTS { tmnxL2tpApServEntry }
    ::= { tmnxL2tpApServStatsTable 1 }

TmnxL2tpApServStatsEntry ::=
    SEQUENCE {
        tmnxL2tpApServStatsTxRequests    Counter32,
        tmnxL2tpApServStatsRxResponses   Counter32,
        tmnxL2tpApServStatsReqTimeout    Counter32,
        tmnxL2tpApServStatsReqSendFail   Counter32,
        tmnxL2tpApServStatsReqPending    Counter32,
        tmnxL2tpApServStatsRespInvAuth   Counter32,
        tmnxL2tpApServStatsSendRetries   Counter32
     }

tmnxL2tpApServStatsTxRequests OBJECT-TYPE
    SYNTAX      Counter32
    MAX-ACCESS  read-only
    STATUS      current
    DESCRIPTION
        "The value of tmnxL2tpApServStatsTxRequests indicates the number of
         RADIUS request packets transmitted for this server."
    ::= { tmnxL2tpApServStatsEntry 1 }

tmnxL2tpApServStatsRxResponses OBJECT-TYPE
    SYNTAX      Counter32
    MAX-ACCESS  read-only
    STATUS      current
    DESCRIPTION
        "The value of tmnxL2tpApServStatsRxResponses indicates the number of
         RADIUS response packets received from this server."
    ::= { tmnxL2tpApServStatsEntry 2 }

tmnxL2tpApServStatsReqTimeout OBJECT-TYPE
    SYNTAX      Counter32
    MAX-ACCESS  read-only
    STATUS      current
    DESCRIPTION
        "The value of tmnxL2tpApServStatsReqTimeout indicates the number of
         RADIUS requests that have timed out for this server."
    ::= { tmnxL2tpApServStatsEntry 3 }

tmnxL2tpApServStatsReqSendFail OBJECT-TYPE
    SYNTAX      Counter32
    MAX-ACCESS  read-only
    STATUS      current
    DESCRIPTION
        "The value of tmnxL2tpApServStatsReqSendFail indicates the number of
         RADIUS request packets that could not be transmitted for this
         server."
    ::= { tmnxL2tpApServStatsEntry 4 }

tmnxL2tpApServStatsReqPending OBJECT-TYPE
    SYNTAX      Counter32
    MAX-ACCESS  read-only
    STATUS      current
    DESCRIPTION
        "The value of tmnxL2tpApServStatsReqPending indicates the number of
         RADIUS requests that are currently pending for this server."
    ::= { tmnxL2tpApServStatsEntry 5 }

tmnxL2tpApServStatsRespInvAuth OBJECT-TYPE
    SYNTAX      Counter32
    MAX-ACCESS  read-only
    STATUS      current
    DESCRIPTION
        "The value of tmnxL2tpApServStatsRespInvAuth indicates the number of
         RADIUS response packets with an invalid Authenticator received
         from this server."
    ::= { tmnxL2tpApServStatsEntry 6 }

tmnxL2tpApServStatsSendRetries OBJECT-TYPE
    SYNTAX      Counter32
    MAX-ACCESS  read-only
    STATUS      current
    DESCRIPTION
        "The value of tmnxL2tpApServStatsSendRetries indicates the number of
         retries to a different server for a single accounting request 
         for this connection with this RADIUS server."
    ::= { tmnxL2tpApServStatsEntry 7 } 
    
-- --------------------------------------------------------
-- L2TP accounting scalar objects
-- --------------------------------------------------------

tmnxL2tpApTableLastCh OBJECT-TYPE
    SYNTAX      TimeStamp
    MAX-ACCESS  read-only
    STATUS      current
    DESCRIPTION
        "The value of the object tmnxL2tpApTableLastCh indicates
         the value of sysUpTime at the time of the last modification of
         an entry in the tmnxL2tpApTable."
    ::= { tmnxL2tpAccountingObjs 100 }

tmnxL2tpApServTableLastCh OBJECT-TYPE
    SYNTAX      TimeStamp
    MAX-ACCESS  read-only
    STATUS      current
    DESCRIPTION
        "The value of the object tmnxL2tpApServTableLastCh indicates
         the value of sysUpTime at the time of the last modification of
         an entry in the tmnxL2tpApServTable."
    ::= { tmnxL2tpAccountingObjs 101 }

-- ----------------------------------------------------------------------------
--  Notification objects
-- ----------------------------------------------------------------------------

tmnxL2tpNotifyDescription  OBJECT-TYPE
SYNTAX       DisplayString
MAX-ACCESS   accessible-for-notify
STATUS       current
DESCRIPTION
    "The object tmnxL2tpNotifyDescription is a printable character 
     string."
::= { tmnxL2tpNotificationObjs 1 }

tmnxL2tpPppNcpFailureProtocol OBJECT-TYPE
SYNTAX      TmnxPppNcpProtocol
MAX-ACCESS  accessible-for-notify
STATUS      current
DESCRIPTION
    "The value of tmnxL2tpPppNcpFailureProtocol indicates the
     failing NCP protocol."
::= { tmnxL2tpNotificationObjs 20 }

-- ----------------------------------------------------------------------------
--  Notifications
-- ----------------------------------------------------------------------------

tmnxL2tpPeerUnreachable NOTIFICATION-TYPE
    OBJECTS {
        tmnxL2tpPeerStatUnreachable,
        tmnxL2tpNotifyDescription
    }
    STATUS current
    DESCRIPTION
        "The tmnxL2tpPeerUnreachable notification is sent when 
         an L2TP peer becomes unreachable and when it becomes reachable again."
    ::= { tmnxL2tpNotifications 1 }

tmnxL2tpIsaMdaVRtrStateChange NOTIFICATION-TYPE
    OBJECTS {
        tmnxL2tpIsaMdaVRtrOperState,
        tmnxL2tpNotifyDescription
    }
    STATUS current
    DESCRIPTION
        "The tmnxL2tpIsaMdaVRtrStateChange notification is sent when 
         the operational state of an L2TP ISA MDA with respect 
         to a Virtual Router changes."
    ::= { tmnxL2tpNotifications 2 }

tmnxL2tpLnsSePppSessionFailure NOTIFICATION-TYPE
    OBJECTS {
        tmnxL2tpLnsSePppPppUserName,
        tmnxL2tpLnsSePppSvcId,
        tmnxL2tpLnsSePppGrpIf,
        tmnxL2tpNotifyDescription
    }
    STATUS current
    DESCRIPTION
        "The tmnxL2tpLnsSePppSessionFailure notification is sent when 
         the system could not create a new session in the tmnxL2tpLnsSePppTable."
    ::= { tmnxL2tpNotifications 3 }

tmnxL2tpLnsPppNcpFailure NOTIFICATION-TYPE
    OBJECTS {
        tmnxL2tpLnsSePppPppUserName,
        tmnxL2tpLnsSePppSvcId,
        tmnxL2tpLnsSePppGrpIf,
        tmnxL2tpPppNcpFailureProtocol,
        tmnxL2tpNotifyDescription
    }
    STATUS current
    DESCRIPTION
        "The tmnxL2tpLnsPppNcpFailure notification indicates that
         there is a NCP phase setup problem."
    ::= { tmnxL2tpNotifications 10}

tmnxL2tpApFailure NOTIFICATION-TYPE
    OBJECTS {
        tmnxL2tpApDescription,
        tmnxL2tpNotifyDescription
    }
    STATUS current
    DESCRIPTION
        "The tmnxL2tpApFailure notification is generated when a RADIUS
         accounting request was not sent out successfully to any of the RADIUS
         servers in the indicated accounting policy."
    ::= { tmnxL2tpNotifications 11 }

tmnxL2tpTunnelBlacklisted NOTIFICATION-TYPE
    OBJECTS {
        tmnxL2tpTuStatusSelBlacklstState,
        tmnxL2tpNotifyDescription
    }
    STATUS current
    DESCRIPTION
        "The tmnxL2tpTunnelBlacklisted notification is sent when
         a L2TP tunnel is added to or removed from the
         tunnel-selection-blacklist."
    ::= { tmnxL2tpNotifications 12 }

tmnxL2tpTunnelSelBlacklistFull NOTIFICATION-TYPE
    OBJECTS {
        tmnxL2tpStatCurrSelBlacklstLen,
        tmnxL2tpXtTuSelBlacklistLength,
        tmnxL2tpNotifyDescription
    }
    STATUS current
    DESCRIPTION
        "The tmnxL2tpTunnelSelBlacklistFull notification is sent when the number
         of tunnels and peers in the tunnel-selection-blacklist reaches the 
         limit configured in tmnxL2tpXtTuSelBlacklistLength, or when the limit
         is no longer reached."
    ::= { tmnxL2tpNotifications 13 }

-- ----------------------------------------------------------------------------
--  Conformance Groups
-- ----------------------------------------------------------------------------
tmnxL2tpCfgGroup OBJECT-GROUP
    OBJECTS {
        tmnxL2tpTableLastCh,
        tmnxL2tpLastMgmtChange,
        tmnxL2tpAdminState,
        tmnxL2tpSessionLimit,
        tmnxL2tpReceiveWindowSize
    }
    STATUS      obsolete
    DESCRIPTION
        "The group of objects providing management of L2TP instances
         on Alcatel-Lucent SROS series systems."
    ::= { tmnxL2tpGroups 1 }

tmnxL2tpTgCfgGroup OBJECT-GROUP
    OBJECTS {
        tmnxL2tpTgCfgTableLastCh,
        tmnxL2tpTgCfgRowStatus,
        tmnxL2tpTgCfgLastMgmtChange,
        tmnxL2tpTgCfgDescription,
        tmnxL2tpTgCfgAdminState,
        tmnxL2tpTgCfgSecret,
        tmnxL2tpTgCfgHelloInterval,
        tmnxL2tpTgCfgIdleTO,
        tmnxL2tpTgCfgDestructTO,
        tmnxL2tpTgCfgMaxRetxEstab,
        tmnxL2tpTgCfgMaxRetxNotEstab,
        tmnxL2tpTgCfgSessionLimit,
        tmnxL2tpTgCfgAvpHiding,
        tmnxL2tpTgCfgSessionAssignMethod,
        tmnxL2tpTgCfgLocalName,
        tmnxL2tpTgCfgDoChallenge,
        tmnxL2tpTgCfgReceiveWindowSize
    }
    STATUS      current
    DESCRIPTION
        "The group of objects providing management of L2TP tunnel groups
         on Alcatel-Lucent SROS series systems."
    ::= { tmnxL2tpGroups 2 }

tmnxL2tpTuCfgGroup OBJECT-GROUP
    OBJECTS {
        tmnxL2tpTuCfgTableLastCh,
        tmnxL2tpTuCfgRowStatus,
        tmnxL2tpTuCfgLastMgmtChange,
        tmnxL2tpTuCfgDescription,
        tmnxL2tpTuCfgAdminState,
        tmnxL2tpTuCfgPreference,
        tmnxL2tpTuCfgPeerAddrType,
        tmnxL2tpTuCfgPeerAddr,
        tmnxL2tpTuCfgAddrType,
        tmnxL2tpTuCfgAddr,
        tmnxL2tpTuCfgLocalName,
        tmnxL2tpTuCfgRemoteName,
        tmnxL2tpTuCfgSecret,
        tmnxL2tpTuCfgHelloInterval,
        tmnxL2tpTuCfgIdleTO,
        tmnxL2tpTuCfgDestructTO,
        tmnxL2tpTuCfgMaxRetxEstab,
        tmnxL2tpTuCfgMaxRetxNotEstab,
        tmnxL2tpTuCfgSessionLimit,
        tmnxL2tpTuCfgAvpHiding,
        tmnxL2tpTuCfgAutoEstab,
        tmnxL2tpTuCfgDoChallenge,
        tmnxL2tpTuCfgReceiveWindowSize
    }
    STATUS      current
    DESCRIPTION
        "The group of objects providing management of L2TP tunnels
         on Alcatel-Lucent SROS series systems."
    ::= { tmnxL2tpGroups 3 }

tmnxL2tpStatGroup OBJECT-GROUP
    OBJECTS {
        tmnxL2tpStatCleared,
        tmnxL2tpStatTotalTunnels,
        tmnxL2tpStatFailedTunnels,
        tmnxL2tpStatFailedTuAuth,
        tmnxL2tpStatActiveTunnels,
        tmnxL2tpStatTotalSessions,
        tmnxL2tpStatFailedSessions,
        tmnxL2tpStatActiveSessions
    }
    STATUS      obsolete
    DESCRIPTION
        "The group of objects providing monitoring of L2TP
         on Alcatel-Lucent SROS series systems."
    ::= { tmnxL2tpGroups 4 }

tmnxL2tpStatV8v0Group OBJECT-GROUP
    OBJECTS {
        tmnxL2tpStatCleared,
        tmnxL2tpStatTotalTunnels,
        tmnxL2tpStatFailedTunnels,
        tmnxL2tpStatFailedTuAuth,
        tmnxL2tpStatActiveTunnels,
        tmnxL2tpStatTotalSessions,
        tmnxL2tpStatFailedSessions,
        tmnxL2tpStatActiveSessions,
        tmnxL2tpStatCurrentTunnels,
        tmnxL2tpStatCurrentSessions
    }
    STATUS      obsolete
    DESCRIPTION
        "The group of objects providing monitoring of L2TP
         on Alcatel-Lucent SROS series systems release 8.0."
    ::= { tmnxL2tpGroups 21 }

tmnxL2tpStatV11v0Group OBJECT-GROUP
    OBJECTS {
        tmnxL2tpStatCleared,
        tmnxL2tpStatTotalTunnels,
        tmnxL2tpStatFailedTunnels,
        tmnxL2tpStatFailedTuAuth,
        tmnxL2tpStatActiveTunnels,
        tmnxL2tpStatTotalSessions,
        tmnxL2tpStatFailedSessions,
        tmnxL2tpStatActiveSessions,
        tmnxL2tpStatCurrentTunnels,
        tmnxL2tpStatCurrentSessions,
        tmnxL2tpStatCurrSelBlacklstLen,
        tmnxL2tpStatUnavailTunnelIds
    }
    STATUS      current
    DESCRIPTION
        "The group of objects providing monitoring of L2TP
         on Alcatel-Lucent SROS series systems release 11.0."
    ::= { tmnxL2tpGroups 23 }

tmnxL2tpTgStatGroup OBJECT-GROUP
    OBJECTS {
        tmnxL2tpTgStatState,
        tmnxL2tpTgStatCleared,
        tmnxL2tpTgStatTotalTunnels,
        tmnxL2tpTgStatFailedTunnels,
        tmnxL2tpTgStatFailedTuAuth,
        tmnxL2tpTgStatActiveTunnels,
        tmnxL2tpTgStatTunnels,
        tmnxL2tpTgStatTotalSessions,
        tmnxL2tpTgStatFailedSessions,
        tmnxL2tpTgStatActiveSessions,
        tmnxL2tpTgStatSessions,
        tmnxL2tpTgStatControlRxOctets,
        tmnxL2tpTgStatControlRxOctetsLw,
        tmnxL2tpTgStatControlRxOctetsHw,
        tmnxL2tpTgStatControlRxPkts,
        tmnxL2tpTgStatControlTxOctets,
        tmnxL2tpTgStatControlTxOctetsLw,
        tmnxL2tpTgStatControlTxOctetsHw,
        tmnxL2tpTgStatControlTxPkts,
        tmnxL2tpTgStatErrorTxPkts,
        tmnxL2tpTgStatErrorRxPkts,
        tmnxL2tpTgStatSessionLimit,
        tmnxL2tpTgStatSeAssignMethod,
        tmnxL2tpTgTuId
    }
    STATUS      current
    DESCRIPTION
        "The group of objects providing monitoring of L2TP tunnel groups
         on Alcatel-Lucent SROS series systems."
    ::= { tmnxL2tpGroups 5 }

tmnxL2tpTuStatGroup OBJECT-GROUP
    OBJECTS {
        tmnxL2tpTuStatusTableLastCh,
        tmnxL2tpTuStatusState,
        tmnxL2tpTuStatusTunnelId,
        tmnxL2tpTuStatusPreference,
        tmnxL2tpTuStatusPeerAddrType,
        tmnxL2tpTuStatusPeerAddr,
        tmnxL2tpTuStatusAddrType,
        tmnxL2tpTuStatusAddr,
        tmnxL2tpTuStatusLocalName,
        tmnxL2tpTuStatusRemoteName,
        tmnxL2tpTuStatusAssignmentId,
        tmnxL2tpTuStatusHelloInterval,
        tmnxL2tpTuStatusIdleTO,
        tmnxL2tpTuStatusDestructTO,
        tmnxL2tpTuStatusMaxRetxEstab,
        tmnxL2tpTuStatusMaxRetxNotEstab,
        tmnxL2tpTuStatusSessionLimit,
        tmnxL2tpTuStatusAvpHiding,
        tmnxL2tpTuStatusGroupName,
        tmnxL2tpTuStatusRemoteTunnelId,
        tmnxL2tpTuStatusRemoteConnId,
        tmnxL2tpTuStatusTransportType,
        tmnxL2tpTuStatusUdpPort,
        tmnxL2tpTuStatusRemoteUdpPort,
        tmnxL2tpTuStatusStartTime,
        tmnxL2tpTuStatusEstabTime,
        tmnxL2tpTuStatusIdleTime,
        tmnxL2tpTuStatusClosedTime,
        tmnxL2tpTuStatusStopCcnResult,
        tmnxL2tpTuStatusGeneralError,
        tmnxL2tpTuStatusErrorMessage,
        tmnxL2tpTuStatusDoChallenge,
        tmnxL2tpTuStatusRws,
        tmnxL2tpTuStatusTxDestAddrType,
        tmnxL2tpTuStatusTxDestAddr,
        tmnxL2tpTuStatusRxSrcAddrType,
        tmnxL2tpTuStatusRxSrcAddr,
        tmnxL2tpTuStatsLastCleared,
        tmnxL2tpTuStatsTotalSessions,
        tmnxL2tpTuStatsFailedSessions,
        tmnxL2tpTuStatsActiveSessions,
        tmnxL2tpTuStatsSessions,
        tmnxL2tpTuStatsControlRxOctets,
        tmnxL2tpTuStatsControlRxOctetsLw,
        tmnxL2tpTuStatsControlRxOctetsHw,
        tmnxL2tpTuStatsControlRxPkts,
        tmnxL2tpTuStatsControlTxOctets,
        tmnxL2tpTuStatsControlTxOctetsLw,
        tmnxL2tpTuStatsControlTxOctetsHw,
        tmnxL2tpTuStatsControlTxPkts,
        tmnxL2tpTuStatsErrorTxPkts,
        tmnxL2tpTuStatsErrorRxPkts,
        tmnxL2tpTuStatsFsmMsgAccepted,   
        tmnxL2tpTuStatsFsmMsgDuplicateRx,
        tmnxL2tpTuStatsFsmMsgOutOfWndwRx,
        tmnxL2tpTuStatsQLengthUnsentMax, 
        tmnxL2tpTuStatsQLengthUnsentCur, 
        tmnxL2tpTuStatsQLengthAckMax,    
        tmnxL2tpTuStatsQLengthAckCur,    
        tmnxL2tpTuStatsWindowSizeCur,    
        tmnxL2tpTuProtStatsName,
        tmnxL2tpTuProtStatsVal
    }
    STATUS      current
    DESCRIPTION
        "The group of objects providing monitoring of L2TP tunnels
         on Alcatel-Lucent SROS series systems."
    ::= { tmnxL2tpGroups 18 }

tmnxL2tpPeerStatGroup OBJECT-GROUP
    OBJECTS {
        tmnxL2tpPeerStatRole,
        tmnxL2tpPeerStatActiveTunnels,
        tmnxL2tpPeerStatTunnels,
        tmnxL2tpPeerStatActiveSessions,
        tmnxL2tpPeerStatSessions,
        tmnxL2tpPeerStatDraining,
        tmnxL2tpPeerStatUnreachable,
        tmnxL2tpPeerStatUnreachableTime,
        tmnxL2tpPeerStatControlRxOct,  
        tmnxL2tpPeerStatControlRxOctLw,
        tmnxL2tpPeerStatControlRxOctHw,
        tmnxL2tpPeerStatControlRxPkts, 
        tmnxL2tpPeerStatControlTxOct,  
        tmnxL2tpPeerStatControlTxOctLw,
        tmnxL2tpPeerStatControlTxOctHw,
        tmnxL2tpPeerStatControlTxPkts, 
        tmnxL2tpPeerStatErrorTxPkts,   
        tmnxL2tpPeerStatErrorRxPkts,   
        tmnxL2tpPeerStatMsgAccepted,   
        tmnxL2tpPeerStatMsgDuplicateRx,
        tmnxL2tpPeerStatMsgOutOfWndwRx,
        tmnxL2tpPeerStatLastCleared,
        tmnxL2tpPeerTuId,
        tmnxL2tpPeerProtStatsName,    
        tmnxL2tpPeerProtStatsVal     
    }
    STATUS      obsolete
    DESCRIPTION
        "The group of objects providing monitoring of L2TP peers
         on Alcatel-Lucent SROS series systems."
    ::= { tmnxL2tpGroups 7 }

tmnxL2tpPeerStatV8v0Group OBJECT-GROUP
    OBJECTS {
        tmnxL2tpPeerStatActiveTunnels,
        tmnxL2tpPeerStatTunnels,
        tmnxL2tpPeerStatActiveSessions,
        tmnxL2tpPeerStatSessions,
        tmnxL2tpPeerStatDraining,
        tmnxL2tpPeerStatUnreachable,
        tmnxL2tpPeerStatUnreachableTime,
        tmnxL2tpPeerStatControlRxOct,  
        tmnxL2tpPeerStatControlRxOctLw,
        tmnxL2tpPeerStatControlRxOctHw,
        tmnxL2tpPeerStatControlRxPkts, 
        tmnxL2tpPeerStatControlTxOct,  
        tmnxL2tpPeerStatControlTxOctLw,
        tmnxL2tpPeerStatControlTxOctHw,
        tmnxL2tpPeerStatControlTxPkts, 
        tmnxL2tpPeerStatErrorTxPkts,   
        tmnxL2tpPeerStatErrorRxPkts,   
        tmnxL2tpPeerStatMsgAccepted,   
        tmnxL2tpPeerStatMsgDuplicateRx,
        tmnxL2tpPeerStatMsgOutOfWndwRx,
        tmnxL2tpPeerStatRolesCapability,
        tmnxL2tpPeerStatRoles,
        tmnxL2tpPeerStatLastCleared,
        tmnxL2tpPeerTuId,
        tmnxL2tpPeerProtStatsName,    
        tmnxL2tpPeerProtStatsVal,
        tmnxL2tpPeerStatUnreachTimeRem   
    }
    STATUS      current
    DESCRIPTION
        "The group of objects providing monitoring of L2TP peers
         on Alcatel-Lucent SROS series systems."
    ::= { tmnxL2tpGroups 19 }

tmnxL2tpSeStatGroup OBJECT-GROUP
    OBJECTS {
        tmnxL2tpSeStatusTableLastCh,
        tmnxL2tpSeStatusState,
        tmnxL2tpSeStatusTunnelId,
        tmnxL2tpSeStatusTunnelConnId,
        tmnxL2tpSeStatusSessionId,
        tmnxL2tpSeStatusRemoteTunnelId,
        tmnxL2tpSeStatusRemoteSessionId,
        tmnxL2tpSeStatusRemoteConnId,
        tmnxL2tpSeStatusStartTime,
        tmnxL2tpSeStatusEstabTime,
        tmnxL2tpTuStatusRemoteName,
        tmnxL2tpSeStatusClosedTime,
        tmnxL2tpSeStatusCdnResult,
        tmnxL2tpSeStatusGeneralError,
        tmnxL2tpSeStatusErrorMessage
    }
    STATUS      current
    DESCRIPTION
        "The group of objects providing monitoring of L2TP sessions
         on Alcatel-Lucent SROS series systems."
    ::= { tmnxL2tpGroups 8 }

tmnxL2tpPeerOpGroup OBJECT-GROUP
    OBJECTS {
        tmnxL2tpPeerDrain
    }
    STATUS      current
    DESCRIPTION
        "The group of objects providing monitoring of L2TP peers
         on Alcatel-Lucent SROS series systems."
    ::= { tmnxL2tpGroups 9 }

tmnxL2tpTgOpGroup OBJECT-GROUP
    OBJECTS {
        tmnxL2tpTgDrain
    }
    STATUS      current
    DESCRIPTION
        "The group of objects providing operations on L2TP tunnel groups
         on Alcatel-Lucent SROS series systems."
    ::= { tmnxL2tpGroups 10 }

tmnxL2tpTuOpGroup OBJECT-GROUP
    OBJECTS {
        tmnxL2tpTuStart,
        tmnxL2tpTuStop,
        tmnxL2tpTuDrain
    }
    STATUS      current
    DESCRIPTION
        "The group of objects providing operations on L2TP tunnels
         on Alcatel-Lucent SROS series systems."
    ::= { tmnxL2tpGroups 11 }

tmnxL2tpLnsIsaGroup OBJECT-GROUP
    OBJECTS {
        tmnxL2tpIsaGrpTableLastCh,
        tmnxL2tpIsaGrpRowStatus,
        tmnxL2tpIsaGrpLastMgmtChange,
        tmnxL2tpIsaGrpDescription,
        tmnxL2tpIsaGrpAdminState,
        tmnxL2tpIsaGrpOperState,
        tmnxL2tpIsaMdaTableLastCh,
        tmnxL2tpIsaMdaRowStatus,
        tmnxL2tpIsaMdaLastMgmtChange,
        tmnxL2tpIsaMdaDrain,
        tmnxL2tpIsaMdaStop
    }
    STATUS      current
    DESCRIPTION
        "The group of objects providing configuration of L2TP 
         Integrated Service Adaptors (ISA) 
         on Alcatel-Lucent SROS series systems."
    ::= { tmnxL2tpGroups 12 }

tmnxL2tpLnsIsaStatGroup OBJECT-GROUP
    OBJECTS {
        tmnxL2tpIsaMdaStatTableLastCh,
        tmnxL2tpIsaMdaStatOperState,
        tmnxL2tpIsaMdaStatSessions,
        tmnxL2tpIsaMdaVRtrOperState
    }
    STATUS      current
    DESCRIPTION
        "The group of objects providing monitoring of L2TP 
         Integrated Service Adaptors (ISA) 
         on Alcatel-Lucent SROS series systems."
    ::= { tmnxL2tpGroups 13 }

tmnxL2tpLnsTgGroup OBJECT-GROUP
    OBJECTS {
        tmnxL2tpTuCfgDoChallenge,
        tmnxL2tpTgCfgIsaGrpId,
        tmnxL2tpTgCfgAddrType,
        tmnxL2tpTgCfgAddr,
        tmnxL2tpLnsTgPppTableLastCh,
        tmnxL2tpLnsTgPppLastMgmtChange,
        tmnxL2tpLnsTgPppAuthPlcy,
        tmnxL2tpLnsTgPppAuthProtocol,      
        tmnxL2tpLnsTgPppUserDb,
        tmnxL2tpLnsTgPppDefaultService,
        tmnxL2tpLnsTgPppDefaultGroupIf,
        tmnxL2tpLnsTgPppProxyLcp,
        tmnxL2tpLnsTgPppProxyAuth,
        tmnxL2tpLnsTgPppMtu,
        tmnxL2tpLnsTgPppLcpKaInterval,
        tmnxL2tpLnsTgPppLcpKaHoldUp
    }
    STATUS      current
    DESCRIPTION
        "The group of objects providing management of L2TP LNS tunnel groups
         on Alcatel-Lucent SROS series systems."
    ::= { tmnxL2tpGroups 14 }

tmnxL2tpLnsTuGroup OBJECT-GROUP
    OBJECTS {
        tmnxL2tpTuCfgIsaGrpId,
        tmnxL2tpLnsTuPppTableLastCh,
        tmnxL2tpLnsTuPppLastMgmtChange,
        tmnxL2tpLnsTuPppAuthPlcy,
        tmnxL2tpLnsTuPppAuthProtocol,
        tmnxL2tpLnsTuPppUserDb,      
        tmnxL2tpLnsTuPppDefaultService,
        tmnxL2tpLnsTuPppDefaultGroupIf,
        tmnxL2tpLnsTuPppProxyLcp,
        tmnxL2tpLnsTuPppProxyAuth,
        tmnxL2tpLnsTuPppMtu,          
        tmnxL2tpLnsTuPppLcpKaInterval,
        tmnxL2tpLnsTuPppLcpKaHoldUp
    }
    STATUS      current
    DESCRIPTION
        "The group of objects providing management of L2TP LNS tunnels
         on Alcatel-Lucent SROS series systems."
    ::= { tmnxL2tpGroups 15 }

tmnxL2tpLnsSeGroup OBJECT-GROUP
    OBJECTS {
        tmnxL2tpLnsSePppTableLastCh,
        tmnxL2tpLnsSePppUpTime,
        tmnxL2tpLnsSePppLcpState,
        tmnxL2tpLnsSePppIpcpState,
        tmnxL2tpLnsSePppPppMtu,
        tmnxL2tpLnsSePppPppAuthProtocol,
        tmnxL2tpLnsSePppPppUserName,
        tmnxL2tpLnsSePppSubIdent,
        tmnxL2tpLnsSePppOriginSubIdent,
        tmnxL2tpLnsSePppSubProfString,
        tmnxL2tpLnsSePppSlaProfString,
        tmnxL2tpLnsSePppAncpString,
        tmnxL2tpLnsSePppInterDestId,
        tmnxL2tpLnsSePppAppProfString,
        tmnxL2tpLnsSePppOriginStrings,
        tmnxL2tpLnsSePppSessionTimeout,
        tmnxL2tpLnsSePppIpAddrType,
        tmnxL2tpLnsSePppIpAddr,
        tmnxL2tpLnsSePppPrimaryDnsType,
        tmnxL2tpLnsSePppPrimaryDns,
        tmnxL2tpLnsSePppSecondaryDnsType,
        tmnxL2tpLnsSePppSecondaryDns,
        tmnxL2tpLnsSePppPrimaryNbnsType,
        tmnxL2tpLnsSePppPrimaryNbns,
        tmnxL2tpLnsSePppSecondNbnsType,
        tmnxL2tpLnsSePppSecondNbns,
        tmnxL2tpLnsSePppOriginIpcpInfo,
        tmnxL2tpLnsSePppCircuitId,
        tmnxL2tpLnsSePppRemoteId,
        tmnxL2tpLnsSePppAddressPool,
        tmnxL2tpLnsSePppType,
        tmnxL2tpLnsSePppSvcId,
        tmnxL2tpLnsSePppGrpIf,
        tmnxL2tpLnsSePppL2tpVrtrId,
        tmnxL2tpLnsSePppL2tpConnectionId,
        tmnxL2tpLnsSePppCategoryMapName,
        tmnxL2tpLnsSePppRadiusClassAttr,
        tmnxL2tpLnsSePppRadiusUserName,
        tmnxL2tpLnsSePppIpv6cpState,
        tmnxL2tpLnsSePppInterfaceId,
        tmnxL2tpLnsSePppOriginIpv6cpInfo,
        tmnxL2tpLnsSePppIpv6DnsType,
        tmnxL2tpLnsSePppIpv6Dns1,
        tmnxL2tpLnsSePppIpv6Dns2,
        tmnxL2tpLnsSePppIpv6DelPfxType,
        tmnxL2tpLnsSePppIpv6DelPfxLen,
        tmnxL2tpLnsSePppIpv6DelPfx,
        tmnxL2tpLnsSePppIpv6PrefixType,
        tmnxL2tpLnsSePppIpv6PrefixLen,
        tmnxL2tpLnsSePppIpv6Prefix,
        tmnxL2tpLnsSePppStatRxUnkwnProto,
        tmnxL2tpLnsSePppStatRxLcpConfRq,  
        tmnxL2tpLnsSePppStatRxLcpConfAk,  
        tmnxL2tpLnsSePppStatRxLcpConfNk,  
        tmnxL2tpLnsSePppStatRxLcpConfRj,  
        tmnxL2tpLnsSePppStatRxLcpTermRq,  
        tmnxL2tpLnsSePppStatRxLcpTermAk,  
        tmnxL2tpLnsSePppStatRxLcpCodeRj,  
        tmnxL2tpLnsSePppStatRxLcpEchoRq,  
        tmnxL2tpLnsSePppStatRxLcpEchoRep, 
        tmnxL2tpLnsSePppStatRxLcpProtRj,  
        tmnxL2tpLnsSePppStatRxLcpDiscRq,  
        tmnxL2tpLnsSePppStatTxLcpConfRq,  
        tmnxL2tpLnsSePppStatTxLcpConfAk,  
        tmnxL2tpLnsSePppStatTxLcpConfNk,  
        tmnxL2tpLnsSePppStatTxLcpConfRj,  
        tmnxL2tpLnsSePppStatTxLcpTermRq,  
        tmnxL2tpLnsSePppStatTxLcpTermAk,  
        tmnxL2tpLnsSePppStatTxLcpCodeRj,  
        tmnxL2tpLnsSePppStatTxLcpEchoRq,  
        tmnxL2tpLnsSePppStatTxLcpEchoRep, 
        tmnxL2tpLnsSePppStatTxLcpProtRj,  
        tmnxL2tpLnsSePppStatTxLcpDiscRq,  
        tmnxL2tpLnsSePppStatRxPapAuthRq,  
        tmnxL2tpLnsSePppStatTxPapAuthAk,  
        tmnxL2tpLnsSePppStatTxPapAuthNk,  
        tmnxL2tpLnsSePppStatRxChapResp,   
        tmnxL2tpLnsSePppStatTxChapChall,  
        tmnxL2tpLnsSePppStatTxChapSucc,   
        tmnxL2tpLnsSePppStatTxChapFail,   
        tmnxL2tpLnsSePppStatRxIpcpConfRq, 
        tmnxL2tpLnsSePppStatRxIpcpConfAk, 
        tmnxL2tpLnsSePppStatRxIpcpConfNk, 
        tmnxL2tpLnsSePppStatRxIpcpConfRj, 
        tmnxL2tpLnsSePppStatRxIpcpTermRq, 
        tmnxL2tpLnsSePppStatRxIpcpTermAk, 
        tmnxL2tpLnsSePppStatRxIpcpCodeRj, 
        tmnxL2tpLnsSePppStatTxIpcpConfRq, 
        tmnxL2tpLnsSePppStatTxIpcpConfAk, 
        tmnxL2tpLnsSePppStatTxIpcpConfNk, 
        tmnxL2tpLnsSePppStatTxIpcpConfRj, 
        tmnxL2tpLnsSePppStatTxIpcpTermRq, 
        tmnxL2tpLnsSePppStatTxIpcpTermAk, 
        tmnxL2tpLnsSePppStatTxIpcpCodeRj,
        tmnxL2tpLnsSeMRtStatus,
        tmnxL2tpLnsSeOvrPIR,
        tmnxL2tpLnsSeOvrCIR,
        tmnxL2tpLnsSeOvrCBS,
        tmnxL2tpLnsSeOvrMBS,
        tmnxL2tpLnsSeAleTableLastCh,
        tmnxL2tpLnsSeAleDatalink,
        tmnxL2tpLnsSeAleEncaps1, 
        tmnxL2tpLnsSeAleEncaps2, 
        tmnxL2tpLnsSePppStatRxIpv6cpCfRq ,
        tmnxL2tpLnsSePppStatRxIpv6cpCfAk ,
        tmnxL2tpLnsSePppStatRxIpv6cpCfNk ,
        tmnxL2tpLnsSePppStatRxIpv6cpCfRj ,
        tmnxL2tpLnsSePppStatRxIpv6cpTmRq ,
        tmnxL2tpLnsSePppStatRxIpv6cpTmAk ,
        tmnxL2tpLnsSePppStatRxIpv6cpCdRj ,
        tmnxL2tpLnsSePppStatTxIpv6cpCfRq ,
        tmnxL2tpLnsSePppStatTxIpv6cpCfAk ,
        tmnxL2tpLnsSePppStatTxIpv6cpCfNk ,
        tmnxL2tpLnsSePppStatTxIpv6cpCfRj ,
        tmnxL2tpLnsSePppStatTxIpv6cpTmRq ,
        tmnxL2tpLnsSePppStatTxIpv6cpTmAk ,
        tmnxL2tpLnsSePppStatTxIpv6cpCdRj 
    }
    STATUS      obsolete
    DESCRIPTION
        "The group of objects providing monitoring of L2TP LNS PPP sessions
         on Alcatel-Lucent SROS series systems."
    ::= { tmnxL2tpGroups 16 }

tmnxL2tpCfgV8v0Group OBJECT-GROUP
    OBJECTS {
        tmnxL2tpTableLastCh,
        tmnxL2tpLastMgmtChange,
        tmnxL2tpAdminState,
        tmnxL2tpSessionLimit,
        tmnxL2tpReceiveWindowSize,
        tmnxL2tpRowStatus,
        tmnxL2tpPeerAddrChangePlcy,
        tmnxL2tpAvpExclude,
        tmnxL2tpAvpCallingNumberSpec
    }
    STATUS      current
    DESCRIPTION
        "The group of objects providing management of L2TP instances
         on Alcatel-Lucent SROS series systems release 8.0."
    ::= { tmnxL2tpGroups 17 }

tmnxL2tpLnsIfGroup OBJECT-GROUP
    OBJECTS {
        tmnxL2tpLnsIfLastMgmtChange,
        tmnxL2tpLnsIfDescription,
        tmnxL2tpLnsIfDefSubProfile,
        tmnxL2tpLnsIfDefSlaProfile,
        tmnxL2tpLnsIfDefAppProfile,
        tmnxL2tpLnsIfSubIdentPolicy,
        tmnxL2tpLnsIfDefSubIdent,
        tmnxL2tpLnsIfDefSubIdentString
    }
    STATUS      obsolete
    DESCRIPTION
        "The group of objects providing configuration of L2TP 
         LNS group interfaces on Alcatel-Lucent SROS series systems."
    ::= { tmnxL2tpGroups 20 }

tmnxL2tpSeOpGroup OBJECT-GROUP
    OBJECTS {
        tmnxL2tpSeStop
    }
    STATUS      current
    DESCRIPTION
        "The group of objects providing operations on L2TP sessions
         on Alcatel-Lucent SROS series systems."
    ::= { tmnxL2tpGroups 22 }

tmnxL2tpLnsTgV9v0Group OBJECT-GROUP
    OBJECTS {
        tmnxL2tpLnsTgPppIpcpSubnetNeg
    }
    STATUS      current
    DESCRIPTION
        "The group of objects providing management of L2TP LNS tunnel groups
         on Alcatel-Lucent SROS series systems that were added in release 9.0."
    ::= { tmnxL2tpGroups 30 }

tmnxL2tpLnsTuV9v0Group OBJECT-GROUP
    OBJECTS {
        tmnxL2tpLnsTuPppIpcpSubnetNeg
    }
    STATUS      current
    DESCRIPTION
        "The group of objects providing management of L2TP LNS tunnels
         on Alcatel-Lucent SROS series systems that were added in release 9.0."
    ::= { tmnxL2tpGroups 31 }

tmnxL2tpLnsIfV9v0Group OBJECT-GROUP
    OBJECTS {
        tmnxL2tpLnsIfLastMgmtChange,
        tmnxL2tpLnsIfDescription,
        tmnxL2tpLnsIfDefSubProfile,
        tmnxL2tpLnsIfDefSlaProfile,
        tmnxL2tpLnsIfDefAppProfile,
        tmnxL2tpLnsIfSubIdentPolicy,
        tmnxL2tpLnsIfDefSubIdent,
        tmnxL2tpLnsIfDefSubIdentString
    }
    STATUS      current
    DESCRIPTION
        "The group of objects providing configuration of L2TP 
         LNS group interfaces on Alcatel-Lucent SROS series systems."
    ::= { tmnxL2tpGroups 32 }

tmnxL2tpMlpppGroup OBJECT-GROUP
    OBJECTS {
        tmnxL2tpTgCfgLoadBalanceMethod,
        tmnxL2tpTuCfgLoadBalanceMethod,
        tmnxL2tpTgMlpppLastMgmtChange,
        tmnxL2tpTgMlpppAdminState,    
        tmnxL2tpTgMlpppMaxLinks,      
        tmnxL2tpTgMlpppInterleave,    
        tmnxL2tpTgMlpppMaxFragDelay,  
        tmnxL2tpTgMlpppReassemblyTo,
        tmnxL2tpTgMlpppShortSeqNumberRx,
        tmnxL2tpTgMlpppEpClass,
        tmnxL2tpTgMlpppEpIpv4Address, 
        tmnxL2tpTgMlpppEpMacAddress,  
        tmnxL2tpTuMlpppLastMgmtChange,
        tmnxL2tpTuMlpppAdminState,    
        tmnxL2tpTuMlpppMaxLinks,      
        tmnxL2tpTuMlpppInterleave,    
        tmnxL2tpTuMlpppMaxFragDelay,  
        tmnxL2tpTuMlpppReassemblyTo,
        tmnxL2tpTuMlpppShortSeqNumberRx,
        tmnxL2tpTuMlpppEpClass,
        tmnxL2tpTuMlpppEpIpv4Address, 
        tmnxL2tpTuMlpppEpMacAddress,  
        tmnxL2tpLacMlpppBundleSvcId,
        tmnxL2tpLacMlpppBundleFwdTuId,
        tmnxL2tpLacMlpppBundleUserName,      
        tmnxL2tpLacMlpppBundleLocEpClass,  
        tmnxL2tpLacMlpppBundleLocEpAddr,
        tmnxL2tpLacMlpppBundleRemEpClass,  
        tmnxL2tpLacMlpppBundleRemEpAddr,
        tmnxL2tpLacMlpppLinkState,
        tmnxL2tpSeStatusMlpppBundleIndex
    }
    STATUS      current
    DESCRIPTION
        "The group of objects providing management of MLPPP for L2TP tunnels
         on Alcatel-Lucent SROS series systems."
    ::= { tmnxL2tpGroups 40 }

tmnxL2tpLnsSeV9v0Group OBJECT-GROUP
    OBJECTS {
       tmnxL2tpLnsSePppTableLastCh,
       tmnxL2tpLnsSePppSubPppIndex
   }
    STATUS      current
    DESCRIPTION
        "The group of objects providing monitoring of L2TP LNS PPP sessions
         in release 9.0 of Alcatel-Lucent SROS series systems."
    ::= { tmnxL2tpGroups 41 }

tmnxL2tpFilterProfileV9v0Group OBJECT-GROUP
    OBJECTS {
            tmnxL2tpLnsIfDefFilterProfile
    }
    STATUS      current
    DESCRIPTION
        "The group of objects providing configuration of Filter Profiles 
         on Alcatel-Lucent SROS series systems."
    ::= { tmnxL2tpGroups 42 }
        
tmnxL2tpTgV10v0Group OBJECT-GROUP
    OBJECTS {
        tmnxL2tpTgCfgLoadBalanceMethod
    }
    STATUS      current
    DESCRIPTION
        "The group of objects providing management of L2TP LNS tunnel groups
         on Alcatel-Lucent SROS series systems that were added in release 10.0."
    ::= { tmnxL2tpGroups 43 }

tmnxL2tpTuV10v0Group OBJECT-GROUP
    OBJECTS {
        tmnxL2tpTuCfgLoadBalanceMethod
    }
    STATUS      current
    DESCRIPTION
        "The group of objects providing management of L2TP LNS tunnels
         on Alcatel-Lucent SROS series systems that were added in release 10.0."
    ::= { tmnxL2tpGroups 44 }

tmnxL2tpAccountingGroup OBJECT-GROUP
    OBJECTS {
        tmnxL2tpApRowStatus,
        tmnxL2tpApLastMgmtChange,
        tmnxL2tpApDescription,
        tmnxL2tpApType,
        tmnxL2tpApServerVRtrID,     
        tmnxL2tpApServerAlgorithm,  
        tmnxL2tpApServerRetry,      
        tmnxL2tpApServerSrcAddrType,
        tmnxL2tpApServerSrcAddr,
        tmnxL2tpApServerTimeout,    
        tmnxL2tpApServRowStatus,     
        tmnxL2tpApServLastMgmtChange,
        tmnxL2tpApServAddrType,
        tmnxL2tpApServAddr,
        tmnxL2tpApServSecret,      
        tmnxL2tpApServAcctPort,
        tmnxL2tpApServOperState,
        tmnxL2tpApServStatsTxRequests,
        tmnxL2tpApServStatsRxResponses,
        tmnxL2tpApServStatsReqTimeout,
        tmnxL2tpApServStatsReqSendFail,
        tmnxL2tpApServStatsReqPending,
        tmnxL2tpApServStatsRespInvAuth,
        tmnxL2tpApServStatsSendRetries,
        tmnxL2tpApServTableLastCh,
        tmnxL2tpApTableLastCh,
        tmnxL2tpAccountingPolicy,
        tmnxL2tpTgCfgAccountingPolicy,
        tmnxL2tpTuCfgAccountingPolicy,
        tmnxL2tpApIncludeAttributes,
        tmnxL2tpApRequestScriptPlcy,
        tmnxL2tpApNasPortIdPfixType,
        tmnxL2tpApNasPortIdPfixString,
        tmnxL2tpApNasPortIdSfixType,
        tmnxL2tpApNasPortTypeType,
        tmnxL2tpApNasPortTypeValue,
        tmnxL2tpApNasPortBitspec,
        tmnxL2tpTuStatusAccountingPolicy,
        tmnxL2tpTuStatusSelBlacklstState,
        tmnxL2tpTuStatusSelBlacklstTime,
        tmnxL2tpTuStatSelBlacklstTimeRem
    }
    STATUS      current
    DESCRIPTION
        "The group of objects providing management of RADIUS accounting
         for L2TP tunnels on Alcatel-Lucent SROS series systems."
    ::= { tmnxL2tpGroups 45 }

tmnxL2tpLnsIsaV10v0Group OBJECT-GROUP
    OBJECTS {
        tmnxL2tpIsaGrpPortPlcy
    }
    STATUS      current
    DESCRIPTION
        "The group of objects providing configuration of L2TP 
         Integrated Service Adaptors (ISA) added in release 10.0 
         of Alcatel-Lucent SROS series systems."
    ::= { tmnxL2tpGroups 46 }

tmnxL2tpV11v0Group OBJECT-GROUP
    OBJECTS {
        tmnxL2tpHelloInterval,
        tmnxL2tpIdleTO,
        tmnxL2tpDestructTO,
        tmnxL2tpMaxRetxEstab,
        tmnxL2tpMaxRetxNotEstab,
        tmnxL2tpTunnelSessionLimit,
        tmnxL2tpGroupSessionLimit,
        tmnxL2tpAvpHiding,
        tmnxL2tpDoChallenge,
        tmnxL2tpSecret,
        tmnxL2tpSessionAssignMethod,
        tmnxL2tpLocalName,
        tmnxL2tpAddrType,
        tmnxL2tpAddr,
        tmnxL2tpXtTableLastCh,
        tmnxL2tpXtLastMgmtChange,
        tmnxL2tpXtNextAttempt,
        tmnxL2tpXtTuSelBlacklistReason,
        tmnxL2tpXtTuSelBlacklistMaxTime,
        tmnxL2tpXtTuSelBlacklistLength,
        tmnxL2tpXtTuSelBlacklistToAction,
        tmnxL2tpXtReplaceResultCodes, 
        tmnxL2tpXtAvpCiscoNasPortEth,
        tmnxL2tpXtAvpCiscoNasPortAtm
    }
    STATUS      current
    DESCRIPTION
        "The group of objects providing configuration of L2TP 
         added in release 11.0 
         of Alcatel-Lucent SROS series systems."
    ::= { tmnxL2tpGroups 47 }
    
tmnxL2tpLnsTgV11v0Group OBJECT-GROUP
    OBJECTS {
        tmnxL2tpLnsTgPppLcpIgnoreMagic,
        tmnxL2tpLnsTgPppMinChapChall,
        tmnxL2tpLnsTgPppMaxChapChall
    }
    STATUS      current
    DESCRIPTION
        "The group of objects providing management of L2TP LNS tunnel groups
         on Alcatel-Lucent SROS series systems that were added in release 11.0."
    ::= { tmnxL2tpGroups 48 }

tmnxL2tpLnsTuV11v0Group OBJECT-GROUP
    OBJECTS {
        tmnxL2tpLnsTuPppLcpIgnoreMagic,
        tmnxL2tpLnsTuPppMinChapChall,
        tmnxL2tpLnsTuPppMaxChapChall
    }
    STATUS      current
    DESCRIPTION
        "The group of objects providing management of L2TP LNS tunnels
         on Alcatel-Lucent SROS series systems that were added in release 11.0."
    ::= { tmnxL2tpGroups 49 }

tmnxL2tpTuStatV11v0Group OBJECT-GROUP
    OBJECTS {
        tmnxL2tpTuStatusTxDestUdpPort,
        tmnxL2tpTuStatusRxSrcUdpPort
    }
    STATUS      current
    DESCRIPTION
        "The group of objects providing monitoring of L2TP tunnels
         on Alcatel-Lucent SROS series systems, added in release 12.0."
    ::= { tmnxL2tpGroups 50 }

tmnxL2tpAccountingV12v0Group OBJECT-GROUP
    OBJECTS {
        tmnxL2tpApRadServPlcy
    }
    STATUS      current
    DESCRIPTION
        "The group of objects providing management of RADIUS accounting
         for L2TP tunnels on Alcatel-Lucent SROS series systems that were added in release 12.0."
    ::= { tmnxL2tpGroups 55 }
  
tmnxL2tpLnsIsaStatV12v0Group OBJECT-GROUP
    OBJECTS {
        tmnxL2tpIsaMdaStatsTableLastCh,
        tmnxL2tpIsaMdaStatsName,
        tmnxL2tpIsaMdaStatsVal,
        tmnxL2tpIsaMdaStatsValHw,
        tmnxL2tpIsaMdaStatsValue
    }
    STATUS      current
    DESCRIPTION
        "The group of objects providing monitoring of L2TP 
         Integrated Service Adaptors (ISA) on Alcatel-Lucent SROS series systems
         that were added in release 12.0."
    ::= { tmnxL2tpGroups 56 }
    
tmnxL2tpDontFragmentBitLacGroup OBJECT-GROUP
    OBJECTS {
        tmnxL2tpXtDfBitLac,
        tmnxL2tpTgXtTableLastCh,
        tmnxL2tpTgXtLastMgmtChange,
        tmnxL2tpTgXtDfBitLac,
        tmnxL2tpTuXtTableLastCh,
        tmnxL2tpTuXtLastMgmtChange,
        tmnxL2tpTuXtDfBitLac,
        tmnxL2tpTuStatusDfBitLac
    }
    STATUS      current
    DESCRIPTION
        "The group of objects providing configuration
         of the DF bit in data traffic transmitted by a system
         performing the LAC role."
    ::= { tmnxL2tpGroups 57 }
    
tmnxL2tpObsoletedObjsV9v0Group     OBJECT-GROUP
    OBJECTS {   
        tmnxL2tpLnsSePppUpTime,
        tmnxL2tpLnsSePppLcpState,
        tmnxL2tpLnsSePppIpcpState,
        tmnxL2tpLnsSePppPppMtu,
        tmnxL2tpLnsSePppPppAuthProtocol,
        tmnxL2tpLnsSePppPppUserName,
        tmnxL2tpLnsSePppSubIdent,
        tmnxL2tpLnsSePppOriginSubIdent,
        tmnxL2tpLnsSePppSubProfString,
        tmnxL2tpLnsSePppSlaProfString,
        tmnxL2tpLnsSePppAncpString,
        tmnxL2tpLnsSePppInterDestId,
        tmnxL2tpLnsSePppAppProfString,
        tmnxL2tpLnsSePppOriginStrings,
        tmnxL2tpLnsSePppSessionTimeout,
        tmnxL2tpLnsSePppIpAddrType,
        tmnxL2tpLnsSePppIpAddr,
        tmnxL2tpLnsSePppPrimaryDnsType,
        tmnxL2tpLnsSePppPrimaryDns,
        tmnxL2tpLnsSePppSecondaryDnsType,
        tmnxL2tpLnsSePppSecondaryDns,
        tmnxL2tpLnsSePppPrimaryNbnsType,
        tmnxL2tpLnsSePppPrimaryNbns,
        tmnxL2tpLnsSePppSecondNbnsType,
        tmnxL2tpLnsSePppSecondNbns,
        tmnxL2tpLnsSePppOriginIpcpInfo,
        tmnxL2tpLnsSePppCircuitId,
        tmnxL2tpLnsSePppRemoteId,
        tmnxL2tpLnsSePppAddressPool,
        tmnxL2tpLnsSePppType,
        tmnxL2tpLnsSePppSvcId,
        tmnxL2tpLnsSePppGrpIf,
        tmnxL2tpLnsSePppL2tpVrtrId,
        tmnxL2tpLnsSePppL2tpConnectionId,
        tmnxL2tpLnsSePppCategoryMapName,
        tmnxL2tpLnsSePppRadiusClassAttr,
        tmnxL2tpLnsSePppRadiusUserName,
        tmnxL2tpLnsSePppIpv6cpState,
        tmnxL2tpLnsSePppInterfaceId,
        tmnxL2tpLnsSePppOriginIpv6cpInfo,
        tmnxL2tpLnsSePppIpv6DnsType,
        tmnxL2tpLnsSePppIpv6Dns1,
        tmnxL2tpLnsSePppIpv6Dns2,
        tmnxL2tpLnsSePppIpv6DelPfxType,
        tmnxL2tpLnsSePppIpv6DelPfxLen,
        tmnxL2tpLnsSePppIpv6DelPfx,
        tmnxL2tpLnsSePppIpv6PrefixType,
        tmnxL2tpLnsSePppIpv6PrefixLen,
        tmnxL2tpLnsSePppIpv6Prefix,
        tmnxL2tpLnsSePppStatRxUnkwnProto,
        tmnxL2tpLnsSePppStatRxLcpConfRq,  
        tmnxL2tpLnsSePppStatRxLcpConfAk,  
        tmnxL2tpLnsSePppStatRxLcpConfNk,  
        tmnxL2tpLnsSePppStatRxLcpConfRj,  
        tmnxL2tpLnsSePppStatRxLcpTermRq,  
        tmnxL2tpLnsSePppStatRxLcpTermAk,  
        tmnxL2tpLnsSePppStatRxLcpCodeRj,  
        tmnxL2tpLnsSePppStatRxLcpEchoRq,  
        tmnxL2tpLnsSePppStatRxLcpEchoRep, 
        tmnxL2tpLnsSePppStatRxLcpProtRj,  
        tmnxL2tpLnsSePppStatRxLcpDiscRq,  
        tmnxL2tpLnsSePppStatTxLcpConfRq,  
        tmnxL2tpLnsSePppStatTxLcpConfAk,  
        tmnxL2tpLnsSePppStatTxLcpConfNk,  
        tmnxL2tpLnsSePppStatTxLcpConfRj,  
        tmnxL2tpLnsSePppStatTxLcpTermRq,  
        tmnxL2tpLnsSePppStatTxLcpTermAk,  
        tmnxL2tpLnsSePppStatTxLcpCodeRj,  
        tmnxL2tpLnsSePppStatTxLcpEchoRq,  
        tmnxL2tpLnsSePppStatTxLcpEchoRep, 
        tmnxL2tpLnsSePppStatTxLcpProtRj,  
        tmnxL2tpLnsSePppStatTxLcpDiscRq,  
        tmnxL2tpLnsSePppStatRxPapAuthRq,  
        tmnxL2tpLnsSePppStatTxPapAuthAk,  
        tmnxL2tpLnsSePppStatTxPapAuthNk,  
        tmnxL2tpLnsSePppStatRxChapResp,   
        tmnxL2tpLnsSePppStatTxChapChall,  
        tmnxL2tpLnsSePppStatTxChapSucc,   
        tmnxL2tpLnsSePppStatTxChapFail,   
        tmnxL2tpLnsSePppStatRxIpcpConfRq, 
        tmnxL2tpLnsSePppStatRxIpcpConfAk, 
        tmnxL2tpLnsSePppStatRxIpcpConfNk, 
        tmnxL2tpLnsSePppStatRxIpcpConfRj, 
        tmnxL2tpLnsSePppStatRxIpcpTermRq, 
        tmnxL2tpLnsSePppStatRxIpcpTermAk, 
        tmnxL2tpLnsSePppStatRxIpcpCodeRj, 
        tmnxL2tpLnsSePppStatTxIpcpConfRq, 
        tmnxL2tpLnsSePppStatTxIpcpConfAk, 
        tmnxL2tpLnsSePppStatTxIpcpConfNk, 
        tmnxL2tpLnsSePppStatTxIpcpConfRj, 
        tmnxL2tpLnsSePppStatTxIpcpTermRq, 
        tmnxL2tpLnsSePppStatTxIpcpTermAk, 
        tmnxL2tpLnsSePppStatTxIpcpCodeRj,
        tmnxL2tpLnsSePppStatRxIpv6cpCdRj,
        tmnxL2tpLnsSePppStatRxIpv6cpCfAk,
        tmnxL2tpLnsSePppStatRxIpv6cpCfNk,
        tmnxL2tpLnsSePppStatRxIpv6cpCfRj,
        tmnxL2tpLnsSePppStatRxIpv6cpCfRq,
        tmnxL2tpLnsSePppStatRxIpv6cpTmAk,
        tmnxL2tpLnsSePppStatRxIpv6cpTmRq,
        tmnxL2tpLnsSePppStatTxIpv6cpCdRj,
        tmnxL2tpLnsSePppStatTxIpv6cpCfAk,
        tmnxL2tpLnsSePppStatTxIpv6cpCfNk,
        tmnxL2tpLnsSePppStatTxIpv6cpCfRj,
        tmnxL2tpLnsSePppStatTxIpv6cpCfRq,
        tmnxL2tpLnsSePppStatTxIpv6cpTmAk,
        tmnxL2tpLnsSePppStatTxIpv6cpTmRq,
        tmnxL2tpLnsSeMRtStatus,
        tmnxL2tpLnsSeOvrPIR,
        tmnxL2tpLnsSeOvrCIR,
        tmnxL2tpLnsSeOvrCBS,
        tmnxL2tpLnsSeOvrMBS,
        tmnxL2tpLnsSeAleTableLastCh,
        tmnxL2tpLnsSeAleDatalink,
        tmnxL2tpLnsSeAleEncaps1, 
        tmnxL2tpLnsSeAleEncaps2 
    }
    STATUS        current
    DESCRIPTION
        "The group of objects that were obsoleted in release 9.0
         of Alcatel-Lucent SROS series systems."
    ::= { tmnxL2tpGroups 97 }

tmnxL2tpObsoletedObjsV8v0Group     OBJECT-GROUP
    OBJECTS {   
        tmnxL2tpPeerStatRole
    }
    STATUS        current
    DESCRIPTION
        "The group of objects that were obsoleted in release 8.0
         of Alcatel-Lucent SROS series systems."
    ::= { tmnxL2tpGroups 98 }

tmnxL2tpNotifyObjsGroup     OBJECT-GROUP
    OBJECTS {   
        tmnxL2tpNotifyDescription
    }
    STATUS        current
    DESCRIPTION
        "The group of notification objects supporting L2TP notifications
         on Alcatel-Lucent SROS series systems."
    ::= { tmnxL2tpGroups 99 }

tmnxL2tpNotifyObjsV9v0Group     OBJECT-GROUP
    OBJECTS {   
        tmnxL2tpPppNcpFailureProtocol
    }
    STATUS        current
    DESCRIPTION
        "The group of notification objects supporting L2TP notifications
         on Alcatel-Lucent SROS series systems added in release 9.0."
    ::= { tmnxL2tpGroups 102 }

-- ----------------------
-- NOTIFICATION-GROUPS
-- ----------------------

tmnxL2tpNotifyGroup NOTIFICATION-GROUP
    NOTIFICATIONS {
        tmnxL2tpPeerUnreachable,
        tmnxL2tpIsaMdaVRtrStateChange,
        tmnxL2tpLnsSePppSessionFailure
    }
    STATUS      current
    DESCRIPTION
        "The group of notifications supporting L2TP
         on Alcatel-Lucent SROS series systems."
    ::= { tmnxL2tpGroups 100 }

tmnxL2tpNotifyV9v0Group NOTIFICATION-GROUP
    NOTIFICATIONS {
        tmnxL2tpLnsPppNcpFailure
    }
    STATUS      current
    DESCRIPTION
        "The group of notifications supporting L2TP
         on Alcatel-Lucent SROS series systems added in release 9.0."
    ::= { tmnxL2tpGroups 101 }

tmnxL2tpNotifyV10v0Group NOTIFICATION-GROUP
    NOTIFICATIONS {
        tmnxL2tpApFailure
    }
    STATUS      current
    DESCRIPTION
        "The group of notifications supporting L2TP
         on Alcatel-Lucent SROS series systems added in release 10.0."
    ::= { tmnxL2tpGroups 103 }

tmnxL2tpNotifyV11v0Group NOTIFICATION-GROUP
    NOTIFICATIONS {
        tmnxL2tpTunnelBlacklisted,
        tmnxL2tpTunnelSelBlacklistFull
    }
    STATUS      current
    DESCRIPTION
        "The group of notifications supporting L2TP
         on Alcatel-Lucent SROS series systems added in release 11.0."
    ::= { tmnxL2tpGroups 104 }

-- ----------------------------------------------------------------------------
--  Conformance information
-- ----------------------------------------------------------------------------
tmnxL2tpCompliance MODULE-COMPLIANCE
    STATUS  obsolete
    DESCRIPTION
        "The compliance statement for management of L2TP
         on Alcatel-Lucent SROS series systems."
    MODULE  -- this module
        MANDATORY-GROUPS {
            tmnxL2tpCfgGroup,
            tmnxL2tpTgCfgGroup,
            tmnxL2tpTuCfgGroup
        }
    ::= { tmnxL2tpCompliances 1 }

tmnxL2tpStatCompliance MODULE-COMPLIANCE
    STATUS  obsolete
    DESCRIPTION
        "The compliance statement for monitoring of L2TP
         on Alcatel-Lucent SROS series systems."
    MODULE  -- this module
        MANDATORY-GROUPS {
            tmnxL2tpStatGroup,
            tmnxL2tpTgStatGroup,
            tmnxL2tpTuStatGroup,
            tmnxL2tpPeerStatGroup,
            tmnxL2tpSeStatGroup
        }
    ::= { tmnxL2tpCompliances 2 }

tmnxL2tpOpCompliance MODULE-COMPLIANCE
    STATUS  current
    DESCRIPTION
        "The compliance statement for L2TP operations
         on Alcatel-Lucent SROS series systems."
    MODULE  -- this module
        MANDATORY-GROUPS {
            tmnxL2tpTgOpGroup,
            tmnxL2tpTuOpGroup,
            tmnxL2tpPeerOpGroup,
            tmnxL2tpSeOpGroup
        }
    ::= { tmnxL2tpCompliances 3 }

tmnxL2tpLnsCompliance MODULE-COMPLIANCE
    STATUS  obsolete
    DESCRIPTION
        "The compliance statement for management of L2TP LNS
         on Alcatel-Lucent SROS series systems."
    MODULE  -- this module
        MANDATORY-GROUPS {
            tmnxL2tpLnsIsaGroup,
            tmnxL2tpLnsIsaStatGroup,
            tmnxL2tpLnsTgGroup,
            tmnxL2tpLnsTuGroup,
            tmnxL2tpLnsSeGroup,
            tmnxL2tpLnsIfGroup
        }
    ::= { tmnxL2tpCompliances 4 }

tmnxL2tpNotifyCompliance MODULE-COMPLIANCE
    STATUS  obsolete
    DESCRIPTION
        "The compliance statement for L2TP notifications
         on Alcatel-Lucent SROS series systems."
    MODULE  -- this module
        MANDATORY-GROUPS {
            tmnxL2tpNotifyGroup
        }
    ::= { tmnxL2tpCompliances 5 }

tmnxL2tpV8v0Compliance MODULE-COMPLIANCE
    STATUS  current
    DESCRIPTION
        "The compliance statement for management of L2TP
         on Alcatel-Lucent SROS series systems."
    MODULE  -- this module
        MANDATORY-GROUPS {
            tmnxL2tpCfgV8v0Group,
            tmnxL2tpTgCfgGroup,
            tmnxL2tpTuCfgGroup
        }
    ::= { tmnxL2tpCompliances 6 }

tmnxL2tpStatV8v0Compliance MODULE-COMPLIANCE
    STATUS  obsolete
    DESCRIPTION
        "The compliance statement for monitoring of L2TP
         on Alcatel-Lucent SROS series systems."
    MODULE  -- this module
        MANDATORY-GROUPS {
            tmnxL2tpStatV8v0Group,
            tmnxL2tpTgStatGroup,
            tmnxL2tpTuStatGroup,
            tmnxL2tpPeerStatV8v0Group,
            tmnxL2tpSeStatGroup
        }
    ::= { tmnxL2tpCompliances 7 }

tmnxL2tpLnsV9v0Compliance MODULE-COMPLIANCE
    STATUS  obsolete
    DESCRIPTION
        "The compliance statement for management of L2TP LNS
         on Alcatel-Lucent SROS series systems."
    MODULE  -- this module
        MANDATORY-GROUPS {
            tmnxL2tpLnsIsaGroup,
            tmnxL2tpLnsIsaStatGroup,
            tmnxL2tpLnsTgGroup,
            tmnxL2tpLnsTgV9v0Group,
            tmnxL2tpLnsTuGroup,
            tmnxL2tpLnsTuV9v0Group,
            tmnxL2tpLnsSeV9v0Group,
            tmnxL2tpLnsIfV9v0Group,
            tmnxL2tpFilterProfileV9v0Group
        }
    ::= { tmnxL2tpCompliances 10 }

tmnxL2tpNotifyV9v0Compliance MODULE-COMPLIANCE
    STATUS  obsolete
    DESCRIPTION
        "The compliance statement for L2TP notifications
         on Alcatel-Lucent SROS series systems."
    MODULE  -- this module
        MANDATORY-GROUPS {
            tmnxL2tpNotifyGroup,
            tmnxL2tpNotifyV9v0Group
}
    ::= { tmnxL2tpCompliances 11 }

tmnxL2tpMlpppCompliance MODULE-COMPLIANCE
    STATUS  current
    DESCRIPTION
        "The compliance statement for management of 
         MLPPP (Multi Link Point to Point Protocol) for L2TP
         on Alcatel-Lucent SROS series systems."
    MODULE  -- this module
        MANDATORY-GROUPS {
            tmnxL2tpMlpppGroup
        }
    ::= { tmnxL2tpCompliances 12 }
    
tmnxL2tpV10v0Compliance MODULE-COMPLIANCE
    STATUS  obsolete
    DESCRIPTION
        "The compliance statement for management of L2TP
         on Alcatel-Lucent SROS series systems."
    MODULE  -- this module
        MANDATORY-GROUPS {
            tmnxL2tpCfgV8v0Group,
            tmnxL2tpTgCfgGroup,
            tmnxL2tpTuCfgGroup,
            tmnxL2tpTgV10v0Group,
            tmnxL2tpTuV10v0Group,
            tmnxL2tpAccountingGroup
        }
    ::= { tmnxL2tpCompliances 13 }

tmnxL2tpNotifyV10v0Compliance MODULE-COMPLIANCE
    STATUS  obsolete
    DESCRIPTION
        "The compliance statement for L2TP notifications
         on Alcatel-Lucent SROS series systems."
    MODULE  -- this module
        MANDATORY-GROUPS {
            tmnxL2tpNotifyGroup,
            tmnxL2tpNotifyV9v0Group,
            tmnxL2tpNotifyV10v0Group
        }
    ::= { tmnxL2tpCompliances 14 }

tmnxL2tpLnsV10v0Compliance MODULE-COMPLIANCE
    STATUS  obsolete
    DESCRIPTION
        "The compliance statement for management of L2TP LNS
         on Alcatel-Lucent SROS series systems."
    MODULE  -- this module
        MANDATORY-GROUPS {
            tmnxL2tpLnsIsaGroup,
            tmnxL2tpLnsIsaV10v0Group,
            tmnxL2tpLnsIsaStatGroup,
            tmnxL2tpLnsTgGroup,
            tmnxL2tpLnsTgV9v0Group,
            tmnxL2tpLnsTuGroup,
            tmnxL2tpLnsTuV9v0Group,
            tmnxL2tpLnsSeV9v0Group,
            tmnxL2tpLnsIfV9v0Group,
            tmnxL2tpFilterProfileV9v0Group
        }
    ::= { tmnxL2tpCompliances 15 }

tmnxL2tpV11v0Compliance MODULE-COMPLIANCE
    STATUS  obsolete
    DESCRIPTION
        "The compliance statement for management of L2TP
         on Alcatel-Lucent SROS series systems."
    MODULE  -- this module
        MANDATORY-GROUPS {
            tmnxL2tpCfgV8v0Group,
            tmnxL2tpTgCfgGroup,
            tmnxL2tpTuCfgGroup,
            tmnxL2tpTgV10v0Group,
            tmnxL2tpTuV10v0Group,
            tmnxL2tpAccountingGroup,
            tmnxL2tpV11v0Group
        }
    ::= { tmnxL2tpCompliances 16 }

tmnxL2tpLnsV11v0Compliance MODULE-COMPLIANCE
    STATUS  obsolete
    DESCRIPTION
        "The compliance statement for management of L2TP LNS
         on Alcatel-Lucent SROS series systems."
    MODULE  -- this module
        MANDATORY-GROUPS {
            tmnxL2tpLnsIsaGroup,
            tmnxL2tpLnsIsaV10v0Group,
            tmnxL2tpLnsIsaStatGroup,
            tmnxL2tpLnsTgGroup,
            tmnxL2tpLnsTgV9v0Group,
            tmnxL2tpLnsTgV11v0Group,
            tmnxL2tpLnsTuGroup,
            tmnxL2tpLnsTuV9v0Group,
            tmnxL2tpLnsTuV11v0Group,
            tmnxL2tpLnsSeV9v0Group,
            tmnxL2tpLnsIfV9v0Group,
            tmnxL2tpFilterProfileV9v0Group
        }
    ::= { tmnxL2tpCompliances 17 }

tmnxL2tpStatV11v0Compliance MODULE-COMPLIANCE
    STATUS  obsolete
    DESCRIPTION
        "The compliance statement for monitoring of L2TP
         on Alcatel-Lucent SROS series systems."
    MODULE  -- this module
        MANDATORY-GROUPS {
            tmnxL2tpStatV11v0Group,
            tmnxL2tpTgStatGroup,
            tmnxL2tpTuStatGroup,
            tmnxL2tpTuStatV11v0Group,
            tmnxL2tpPeerStatV8v0Group,
            tmnxL2tpSeStatGroup
        }
    ::= { tmnxL2tpCompliances 18 }

tmnxL2tpNotifyV11v0Compliance MODULE-COMPLIANCE
    STATUS  obsolete
    DESCRIPTION
        "The compliance statement for L2TP notifications
         on Alcatel-Lucent SROS series systems."
    MODULE  -- this module
        MANDATORY-GROUPS {
            tmnxL2tpNotifyGroup,
            tmnxL2tpNotifyV9v0Group,
            tmnxL2tpNotifyV10v0Group,
            tmnxL2tpNotifyV11v0Group
        }
    ::= { tmnxL2tpCompliances 19 }

tmnxL2tpV12v0Compliance MODULE-COMPLIANCE
    STATUS  current
    DESCRIPTION
        "The compliance statement for management of L2TP
         on Alcatel-Lucent SROS series systems."
    MODULE  -- this module
        MANDATORY-GROUPS {
            tmnxL2tpCfgV8v0Group,
            tmnxL2tpTgCfgGroup,
            tmnxL2tpTuCfgGroup,
            tmnxL2tpTgV10v0Group,
            tmnxL2tpTuV10v0Group,
            tmnxL2tpAccountingGroup,
            tmnxL2tpAccountingV12v0Group,
            tmnxL2tpV11v0Group,
            tmnxL2tpDontFragmentBitLacGroup
        }
    ::= { tmnxL2tpCompliances 20 }
    
tmnxL2tpLnsV12v0Compliance MODULE-COMPLIANCE
    STATUS  current
    DESCRIPTION
        "The compliance statement for management of L2TP LNS
         on Alcatel-Lucent SROS series systems."
    MODULE  -- this module
        MANDATORY-GROUPS {
            tmnxL2tpLnsIsaGroup,
            tmnxL2tpLnsIsaV10v0Group,
            tmnxL2tpLnsIsaStatGroup,
            tmnxL2tpLnsIsaStatV12v0Group,
            tmnxL2tpLnsTgGroup,
            tmnxL2tpLnsTgV9v0Group,
            tmnxL2tpLnsTgV11v0Group,
            tmnxL2tpLnsTuGroup,
            tmnxL2tpLnsTuV9v0Group,
            tmnxL2tpLnsTuV11v0Group,
            tmnxL2tpLnsSeV9v0Group,
            tmnxL2tpLnsIfV9v0Group,
            tmnxL2tpFilterProfileV9v0Group
        }
    ::= { tmnxL2tpCompliances 21 }

tmnxL2tpStatV12v0Compliance MODULE-COMPLIANCE
    STATUS  current
    DESCRIPTION
        "The compliance statement for monitoring of L2TP
         on Alcatel-Lucent SROS series systems."
    MODULE  -- this module
        MANDATORY-GROUPS {
            tmnxL2tpStatV11v0Group,
            tmnxL2tpTgStatGroup,
            tmnxL2tpTuStatGroup,
            tmnxL2tpTuStatV11v0Group,
            tmnxL2tpPeerStatV8v0Group,
            tmnxL2tpSeStatGroup
        }
    ::= { tmnxL2tpCompliances 22 }

tmnxL2tpNotifyV12v0Compliance MODULE-COMPLIANCE
    STATUS  current
    DESCRIPTION
        "The compliance statement for L2TP notifications
         on Alcatel-Lucent SROS series systems."
    MODULE  -- this module
        MANDATORY-GROUPS {
            tmnxL2tpNotifyGroup,
            tmnxL2tpNotifyV9v0Group,
            tmnxL2tpNotifyV10v0Group,
            tmnxL2tpNotifyV11v0Group
        }
    ::= { tmnxL2tpCompliances 23 }

END
