TIMETRA-LDP-NG-MIB DEFINITIONS ::= BEGIN


IMPORTS
        MODULE-IDENTITY, OBJECT-TYPE, NOTIFICATION-TYPE,
        Unsigned32, Counter32, Gauge32, Counter64,
        IpAddress
            FROM SNMPv2-SMI

        MODULE-COMPLIANCE, OBJECT-GROUP, NOTIFICATION-GROUP
            FROM SNMPv2-CONF

        RowStatus, TruthValue, TestAndIncr,
        TimeStamp, TimeInterval, DisplayString, TEXTUAL-CONVENTION
            FROM SNMPv2-TC

        InterfaceIndexOrZero
            FROM IF-MIB

        InetAddress, InetAddressType, InetAddressPrefixLength
            FROM INET-ADDRESS-MIB

        timetraSRMIBModules, tmnxSRObjs, tmnxSRNotifyPrefix,
        tmnxSRConfs
            FROM TIMETRA-GLOBAL-MIB

        vRtrID, vRtrLdpStatus
            FROM TIMETRA-VRTR-MIB

        TmnxAdminState, TmnxOperState, TPolicyStatementNameOrEmpty,
        TmnxServId, TmnxVcType, TmnxVcId, TmnxEnabledDisabled
            FROM TIMETRA-TC-MIB

        ServType, SdpId, TdmOptionsSigPkts, TdmOptionsCasTrunkFraming
            FROM TIMETRA-SERV-MIB

        TFilterLogId, TFilterID
            FROM TIMETRA-FILTER-MIB

        TNamedItemOrEmpty, TmnxVRtrMplsLspID, TmnxLdpFECType, TNamedItem,
        TmnxMplsLdpNgIdType, TmnxMplsLdpNgIdentifier, TmnxMplsLsrNgIdentifier
            FROM TIMETRA-TC-MIB

        TmnxLdpKeepAliveFactor, TmnxLdpNewKeepAliveTimeout, TmnxLdpHelloFactor,
        TmnxLdpNewHelloTimeout, TmnxLdpBackoffTime, TmnxLdpAdjacencyType, 
        TmnxLdpIntTargOperDownReasonCode, TmnxLdpLabelDistMethod,
        TmnxLdpHelloTimeout, TmnxLdpFECFlags, TmnxLabelStatus, TmnxVpnId,
        TmnxLabelSigStatus, TmnxLdpInLblWdrawalReasonCode, TmnxLdpFec129Tlv,
        vRtrLdpSessOverloadState, vRtrLdpSessOverloadDirection, 
        vRtrLdpSessOverloadFecType, TmnxLdpGenOperDownReasonCode, 
        TmnxLdpFECPolicy
            FROM TIMETRA-LDP-MIB

        MplsLsrIdentifier
            FROM MPLS-LDP-MIB
        ;

timetraLdpNgMIBModule MODULE-IDENTITY
        LAST-UPDATED "201402010000Z"
        ORGANIZATION "Alcatel-Lucent"
        CONTACT-INFO
            "Alcatel-Lucent SROS Support
             Web: http://support.alcatel-lucent.com"
        DESCRIPTION
        "The MIB module to manage and provision the Alcatel-Lucent SROS LDP
        NG protocol features.

        Copyright 2013-2014 Alcatel-Lucent. All rights reserved.
        Reproduction of this document is authorized on the condition that
        the foregoing copyright notice is included.

        This SNMP MIB module (Specification) embodies Alcatel-Lucent's
        proprietary intellectual property.  Alcatel-Lucent retains
        all title and ownership in the Specification, including any
        revisions.

        Alcatel-Lucent grants all interested parties a non-exclusive
        license to use and distribute an unmodified copy of this
        Specification in connection with management of Alcatel-Lucent
        products, and without fee, provided this copyright notice and
        license appear on all copies.

        This Specification is supplied 'as is', and Alcatel-Lucent
        makes no warranty, either express or implied, as to the use,
        operation, condition, or performance of the Specification."

--
--  Revision History
--
        REVISION        "201402010000Z"
        DESCRIPTION     "Rev 0.1            1 Feb 2014 00:00
                         Initial version of the TIMETRA-LDP-NG-MIB."

        ::= { timetraSRMIBModules 91 }



-- ----------------------------------------------------------------------------
--  Alcatel-Lucent SROS series LDP NG MIB structure
-- ----------------------------------------------------------------------------

tmnxLdpNgObjs             OBJECT IDENTIFIER ::= { tmnxSRObjs 91 }
tmnxLdpNgConformance      OBJECT IDENTIFIER ::= { tmnxSRConfs 91 }
tmnxLdpNgCompliances      OBJECT IDENTIFIER ::= { tmnxLdpNgConformance 1 }
tmnxLdpNgGroups           OBJECT IDENTIFIER ::= { tmnxLdpNgConformance 2 }
tmnxLdpNgNotifyPrefix     OBJECT IDENTIFIER ::= { tmnxSRNotifyPrefix 91 }
    tmnxLdpNgNotifications    OBJECT IDENTIFIER ::= { tmnxLdpNgNotifyPrefix 0 }

--
--  The Virtual Router Label Distribution Protocol (LDP) Interface Table
--

vRtrLdpNgIfTableLstChanged OBJECT-TYPE
    SYNTAX     TimeStamp
    MAX-ACCESS read-only
    STATUS     current
    DESCRIPTION
        "The value of vRtrLdpNgIfTableLstChanged indicates the last
         timestamp when an entry in the vRtrLdpNgIfTable was last changed."
    ::= { tmnxLdpNgObjs 1 }

vRtrLdpNgIfTable    OBJECT-TYPE
    SYNTAX      SEQUENCE OF VRtrLdpNgIfEntry
    MAX-ACCESS  not-accessible
    STATUS      current
    DESCRIPTION
        "The vRtrLdpNgIfTable provides an entry for each virtual router interface
         configured to be used with the Label Distribution Protocol (LDP)."
    ::= { tmnxLdpNgObjs 2 }

vRtrLdpNgIfEntry    OBJECT-TYPE
    SYNTAX      VRtrLdpNgIfEntry
    MAX-ACCESS  not-accessible
    STATUS      current
    DESCRIPTION
        "Each row entry represents an interface on this virtual router
         that participates in the LDP protocol.

         Row entries can be created or deleted via SNMP SET requests.
         A row with default attribute values is created by setting
         vRtrLdpNgIfRowStatus to 'createAndGo'. A row entry can be
         destroyed by setting vRtrLdpNgIfRowStatus to 'destroy'."
   INDEX  { vRtrID,
            vRtrLdpNgIfIndex
          }
   ::= { vRtrLdpNgIfTable 1 }

VRtrLdpNgIfEntry ::= SEQUENCE {
    vRtrLdpNgIfIndex                  InterfaceIndexOrZero,
    vRtrLdpNgIfRowStatus              RowStatus,
    vRtrLdpNgIfLastChange             TimeStamp,
    vRtrLdpNgIfAdminState             TmnxAdminState,
    vRtrLdpNgIfOperState              TmnxOperState,
    vRtrLdpNgIfOperDownReason         TmnxLdpIntTargOperDownReasonCode,
    vRtrLdpNgIfBfdEnabled             BITS
}

vRtrLdpNgIfIndex    OBJECT-TYPE
    SYNTAX      InterfaceIndexOrZero
    MAX-ACCESS  not-accessible
    STATUS      current
    DESCRIPTION
        "The value of vRtrLdpNgIfIndex specifies the interface index."
    ::= { vRtrLdpNgIfEntry 1 }

vRtrLdpNgIfRowStatus    OBJECT-TYPE
    SYNTAX      RowStatus
    MAX-ACCESS  read-create
    STATUS      current
    DESCRIPTION
        "vRtrLdpNgIfRowStatus is used to control the creation and deletion
         of rows in the vRtrLdpNgIfTable.

         A row can be created by setting vRtrLdpNgIfRowStatus to 'createAndGo'.
         The agent should assign the default attribute values and change
         the row status to 'active'.

         A row entry can be destroyed by setting vRtrLdpNgIfRowStatus to
         'destroy'."
    ::= { vRtrLdpNgIfEntry 2 }

vRtrLdpNgIfLastChange    OBJECT-TYPE
    SYNTAX      TimeStamp
    MAX-ACCESS  read-only
    STATUS      current
    DESCRIPTION
        "The value of vRtrLdpNgIfLastChange indicates the sysUpTime when this
         row was last modified."
    ::= { vRtrLdpNgIfEntry 3 }

vRtrLdpNgIfAdminState    OBJECT-TYPE
    SYNTAX      TmnxAdminState
    MAX-ACCESS  read-create
    STATUS      current
    DESCRIPTION
        "The value of vRtrLdpNgIfAdminState indicates the desired administrative
         state for LDP on this interface."
    DEFVAL { inService }
    ::= { vRtrLdpNgIfEntry 4 }

vRtrLdpNgIfOperState    OBJECT-TYPE
    SYNTAX      TmnxOperState
    MAX-ACCESS  read-only
    STATUS      current
    DESCRIPTION
        "The value of vRtrLdpNgIfOperState indicates the current operational
         state of LDP of this interface"
    ::= { vRtrLdpNgIfEntry 5 }

vRtrLdpNgIfOperDownReason    OBJECT-TYPE
    SYNTAX      TmnxLdpIntTargOperDownReasonCode
    MAX-ACCESS  read-only
    STATUS      current
    DESCRIPTION
        "The value of vRtrLdpNgIfOperDownReason indicates the reason
         that the LDP interface is operationally down."
    ::= { vRtrLdpNgIfEntry 6 }

vRtrLdpNgIfBfdEnabled  OBJECT-TYPE
     SYNTAX     BITS {
                    ipv4    (0),
                    ipv6    (1)
                }
     MAX-ACCESS  read-create
     STATUS      current
     DESCRIPTION
         "The value of vRtrLdpNgIfBfdEnabled specifies whether BFD tracking 
         is enabled to hello adjacency source address of the peer. When multiple 
         links exist to the same LDP peer, a Hello adjacency is established over 
         each link and a separate BFD session is enabled on each LDP interface. 
         If there are any FEC resolved over this interface, LDP will enable BFD 
         tracking to each next hop.
         
         When this object has a value of 'ipv4', BFD tracking is enabled to each 
         resolved ipv4 FEC next hop and or ipv4 hello adjacency over this interface. 
         When this object has a value of 'ipv6', BFD tracking is enabled to each 
         resolved ipv6 FEC next hop and or ipv6 hello adjacency over this 
         interface. In case FEC next hop and hello adjacency source address of 
         the peer is same, only one BFD session is used to track both. When this 
         object has value of 0, BFD tracking is disabled."
     DEFVAL { {} }
     ::= { vRtrLdpNgIfEntry 7 }

--
-- LDP Hello Adjacency Table
--

vRtrLdpNgHelloAdjTable    OBJECT-TYPE
    SYNTAX      SEQUENCE OF VRtrLdpNgHelloAdjEntry
    MAX-ACCESS  not-accessible
    STATUS      current
    DESCRIPTION
        "The vRtrLdpNgHelloAdjTable is a read-only table which has information 
        about Hello Adjacencies for Sessions. A hello adjacency can be 
        associated with an LDP interface or with a targeted peer."
    ::= { tmnxLdpNgObjs 3}

vRtrLdpNgHelloAdjEntry    OBJECT-TYPE
    SYNTAX      VRtrLdpNgHelloAdjEntry
    MAX-ACCESS  not-accessible
    STATUS      current
    DESCRIPTION
        "Each row represents a single LDP Hello Adjacency. An LDP Session 
         can have one or more Hello adjacencies."
    INDEX  { vRtrID,
             vRtrLdpNgPeerLdpIdType,
             vRtrLdpNgPeerLdpId,
             vRtrLdpNgIfIndex,
             vRtrLdpNgPeerAddressType,
             vRtrLdpNgPeerAddress }
    ::= { vRtrLdpNgHelloAdjTable 1 }

VRtrLdpNgHelloAdjEntry ::= SEQUENCE {
    vRtrLdpNgPeerLdpIdType                      TmnxMplsLdpNgIdType,
    vRtrLdpNgPeerLdpId                          TmnxMplsLdpNgIdentifier,
    vRtrLdpNgHelloAdjLclLdpIdType               TmnxMplsLdpNgIdType,
    vRtrLdpNgHelloAdjLclLdpId                   TmnxMplsLdpNgIdentifier,
    vRtrLdpNgHelloAdjEntityIndex                Unsigned32,
    vRtrLdpNgHelloAdjIndex                      Unsigned32,
    vRtrLdpNgHelloAdjHoldTimeRem                Unsigned32,
    vRtrLdpNgHelloAdjType                       TmnxLdpAdjacencyType,
    vRtrLdpNgHelloAdjRemConfSeqNum              Unsigned32,
    vRtrLdpNgHelloAdjRemIpAddrType              InetAddressType,
    vRtrLdpNgHelloAdjRemIpAddress               InetAddress,
    vRtrLdpNgHelloAdjUpTime                     TimeInterval,
    vRtrLdpNgHelloAdjLclConfSeqNum              Unsigned32,
    vRtrLdpNgHelloAdjLclIpAddrType              InetAddressType,
    vRtrLdpNgHelloAdjLclIpAddress               InetAddress,
    vRtrLdpNgHelloAdjInHelloMsgCnt              Counter32,
    vRtrLdpNgHelloAdjOutHelloMsgCnt             Counter32,
    vRtrLdpNgHelloAdjLclTimeout                 TmnxLdpHelloTimeout,
    vRtrLdpNgHelloAdjRemTimeout                 TmnxLdpHelloTimeout,
    vRtrLdpNgHelloAdjBfdStatus                  INTEGER
}

vRtrLdpNgPeerLdpIdType    OBJECT-TYPE
    SYNTAX      TmnxMplsLdpNgIdType
    MAX-ACCESS  not-accessible
    STATUS      current
    DESCRIPTION
        "The object vRtrLdpNgPeerLdpIdType is an index for the row entry. 
        It indicates the LDP identifier type of the peer indicated by 
        vRtrLdpNgPeerLdpId."
    ::= { vRtrLdpNgHelloAdjEntry 1 }

vRtrLdpNgPeerLdpId    OBJECT-TYPE
    SYNTAX      TmnxMplsLdpNgIdentifier (SIZE (6|18))
    MAX-ACCESS  not-accessible
    STATUS      current
    DESCRIPTION
        "The object vRtrLdpNgPeerLdpId is an index for the row entry. It indicates 
        the LDP identifier of the peer."
    ::= { vRtrLdpNgHelloAdjEntry 2 }

vRtrLdpNgHelloAdjLclLdpIdType    OBJECT-TYPE
    SYNTAX      TmnxMplsLdpNgIdType
    MAX-ACCESS  read-only
    STATUS      current
    DESCRIPTION
        "The value of vRtrLdpNgHelloAdjLclLdpId indicates the local LDP 
         identifier type for this specific adjacency indicated by 
         vRtrLdpNgHelloAdjLclLdpId ."
    ::= { vRtrLdpNgHelloAdjEntry 3 }
    
vRtrLdpNgHelloAdjLclLdpId    OBJECT-TYPE
    SYNTAX      TmnxMplsLdpNgIdentifier (SIZE (6|18))
    MAX-ACCESS  read-only
    STATUS      current
    DESCRIPTION
        "The value of vRtrLdpNgHelloAdjLclLdpId indicates the local LDP 
         identifier for this specific adjacency."
    ::= { vRtrLdpNgHelloAdjEntry 4 }

vRtrLdpNgHelloAdjEntityIndex    OBJECT-TYPE
    SYNTAX      Unsigned32 (1..4294967295)
    MAX-ACCESS  read-only
    STATUS      current
    DESCRIPTION
        "The value of vRtrLdpNgHelloAdjEntityIndex indicates the Entity index
         which is an index for MPLS-LDP-MIB::mplsLdpHelloAdjacencyEntry."
    ::= { vRtrLdpNgHelloAdjEntry 5 }

vRtrLdpNgHelloAdjIndex    OBJECT-TYPE
    SYNTAX      Unsigned32 (1..4294967295)
    MAX-ACCESS  read-only
    STATUS      current
    DESCRIPTION
        "The value of vRtrLdpNgHelloAdjIndex indicates the Hello adjacency index 
         which is an index for MPLS-LDP-MIB::mplsLdpHelloAdjacencyEntry."
    ::= { vRtrLdpNgHelloAdjEntry 6 }

vRtrLdpNgHelloAdjHoldTimeRem    OBJECT-TYPE
    SYNTAX      Unsigned32
    UNITS       "seconds"
    MAX-ACCESS  read-only
    STATUS      current
    DESCRIPTION
        "The value of vRtrLdpNgHelloAdjHoldTimeRem indicates the hold 
         time remaining for this Hello Adjacency. This interval will change 
         when the next Hello message which corresponds to this Hello 
         Adjacency is received."
    ::= { vRtrLdpNgHelloAdjEntry 7 }

vRtrLdpNgHelloAdjType    OBJECT-TYPE
    SYNTAX      TmnxLdpAdjacencyType
    MAX-ACCESS  read-only
    STATUS      current
    DESCRIPTION
        "The value of vRtrLdpNgHelloAdjType indicates the type of this Hello
         Adjacency. If this value is 'link' then this adjacency is a result
         of a Link Hello. If this value is 'hello', then the adjacency is a
         result of a Targeted Hello."
    ::= { vRtrLdpNgHelloAdjEntry 8 }

vRtrLdpNgHelloAdjRemConfSeqNum    OBJECT-TYPE
    SYNTAX      Unsigned32
    MAX-ACCESS  read-only
    STATUS      current
    DESCRIPTION
        "The value of vRtrLdpNgHelloAdjRemConfSeqNum indicates the 
         Configuration sequence number that was in the Hello received when 
         this adjacency started up. This configuration sequence number 
         changes when there is a change of configuration."
    ::= { vRtrLdpNgHelloAdjEntry 9 }

vRtrLdpNgHelloAdjRemIpAddrType    OBJECT-TYPE
    SYNTAX      InetAddressType
    MAX-ACCESS  read-only
    STATUS      current
    DESCRIPTION
        "The value of vRtrLdpNgHelloAdjRemIpAddrType indicates the type of
         address indicated by vRtrLdpNgHelloAdjRemIpAddress."
    ::= { vRtrLdpNgHelloAdjEntry 10 }

vRtrLdpNgHelloAdjRemIpAddress    OBJECT-TYPE
    SYNTAX      InetAddress (SIZE (0|4|16))
    MAX-ACCESS  read-only
    STATUS      current
    DESCRIPTION
        "The value of vRtrLdpNgHelloAdjRemIpAddress indicates the peer 
         IP address of the interface/targeted session that sent hellos 
         for this specific adjacency."
    ::= { vRtrLdpNgHelloAdjEntry 11 }

vRtrLdpNgHelloAdjUpTime    OBJECT-TYPE
    SYNTAX      TimeInterval
    UNITS       "hundreds of seconds"
    MAX-ACCESS  read-only
    STATUS      current
    DESCRIPTION
        "The value of vRtrLdpNgHelloAdjUpTime indicates the time that this 
        adjacency has been up."
    ::= { vRtrLdpNgHelloAdjEntry 12 }

vRtrLdpNgHelloAdjLclConfSeqNum    OBJECT-TYPE
    SYNTAX      Unsigned32
    MAX-ACCESS  read-only
    STATUS      current
    DESCRIPTION
        "The value of vRtrLdpNgHelloAdjLclConfSeqNum indicates the 
         Configuration sequence number that was used in the Hello sent 
         when this adjacency started up. This configuration sequence 
         number changes when there is a change of configuration."
    ::= { vRtrLdpNgHelloAdjEntry 13 }

vRtrLdpNgHelloAdjLclIpAddrType    OBJECT-TYPE
    SYNTAX      InetAddressType
    MAX-ACCESS  read-only
    STATUS      current
    DESCRIPTION
        "The value of vRtrLdpNgHelloAdjLclIpAddrType indicates the type of
         address indicated by vRtrLdpNgHelloAdjLclIpAddress."
    ::= { vRtrLdpNgHelloAdjEntry 14 }

vRtrLdpNgHelloAdjLclIpAddress    OBJECT-TYPE
    SYNTAX      InetAddress (SIZE (0|4|16))
    MAX-ACCESS  read-only
    STATUS      current
    DESCRIPTION
        "The value of vRtrLdpNgHelloAdjLclIpAddress indicates the local 
         IP address of the interface/targeted session used in Hellos sent
         for this specific adjacency."
    ::= { vRtrLdpNgHelloAdjEntry 15 }

vRtrLdpNgHelloAdjInHelloMsgCnt    OBJECT-TYPE
    SYNTAX      Counter32
    MAX-ACCESS  read-only
    STATUS      current
    DESCRIPTION
        "The value of vRtrLdpNgHelloAdjInHelloMsgCnt indicates the number 
         of Hello messages that have been received for this adjacency."
    ::= { vRtrLdpNgHelloAdjEntry 16 }

vRtrLdpNgHelloAdjOutHelloMsgCnt    OBJECT-TYPE
    SYNTAX      Counter32
    MAX-ACCESS  read-only
    STATUS      current
    DESCRIPTION
        "The value of vRtrLdpNgHelloAdjOutHelloMsgCnt indicates the number 
         of Hello messages that have been sent for this adjacency."
    ::= { vRtrLdpNgHelloAdjEntry 17 }

vRtrLdpNgHelloAdjLclTimeout    OBJECT-TYPE
    SYNTAX      TmnxLdpHelloTimeout
    MAX-ACCESS  read-only
    STATUS      current
    DESCRIPTION
        "The value of vRtrLdpNgHelloAdjLclTimeout indicates the hello 
         timeout used in the Hellos sent for this specific adjacency."
    ::= { vRtrLdpNgHelloAdjEntry 18 }

vRtrLdpNgHelloAdjRemTimeout    OBJECT-TYPE
    SYNTAX      TmnxLdpHelloTimeout
    MAX-ACCESS  read-only
    STATUS      current
    DESCRIPTION
        "The value of vRtrLdpNgHelloAdjRemTimeout indicates the hello 
         timeout used by the remote end that sent Hellos for this specific 
         adjacency."
    ::= { vRtrLdpNgHelloAdjEntry 19 }

vRtrLdpNgHelloAdjBfdStatus  OBJECT-TYPE
    SYNTAX      INTEGER {
                   noService (1),
                   inService (2),
                   outOfService (3)
                }
    MAX-ACCESS  read-only
    STATUS      current
    DESCRIPTION
        "The value of vRtrLdpNgHelloAdjBfdStatus indicates the BFD operational
         status for LDP hello adjacency.

         If the value of vRtrLdpNgHelloAdjBfdStatus is 'noService', BFD is 
         not enabled for LDP hello adjacency. If the value of the object is
         'outOfService', BFD is enabled but it is down and not running.
         If the value of object is 'inService', BFD is enabled and it is
         running."
    ::= { vRtrLdpNgHelloAdjEntry 20 }

--
-- LDP Session Table
--

vRtrLdpNgSessionTable    OBJECT-TYPE
    SYNTAX      SEQUENCE OF VRtrLdpNgSessionEntry
    MAX-ACCESS  not-accessible
    STATUS      current
    DESCRIPTION
        "The vRtrLdpNgSessionTable is a read-only table which parallels the
         mplsLdpSessionTable in the MPLS-LDP-MIB. The purpose of this 
         table is to keep information about a single session between
         an LDP entity and an LDP Peer."
    ::= { tmnxLdpNgObjs 4 }

vRtrLdpNgSessionEntry OBJECT-TYPE
    SYNTAX      VRtrLdpNgSessionEntry
    MAX-ACCESS  not-accessible
    STATUS      current
    DESCRIPTION
        "A row in this table represents information about a single 
         session between an LDP entity and an LDP Peer."
    INDEX  { vRtrID,
             vRtrLdpNgPeerLdpIdType, 
             vRtrLdpNgPeerLdpId }
    ::= { vRtrLdpNgSessionTable 1 }

VRtrLdpNgSessionEntry ::= SEQUENCE {
    vRtrLdpNgSessLocalLdpIdType                TmnxMplsLdpNgIdType,
    vRtrLdpNgSessLocalLdpId                    TmnxMplsLdpNgIdentifier,
    vRtrLdpNgSessEntityIndex                   Unsigned32,
    vRtrLdpNgSessLabelDistMethod               TmnxLdpLabelDistMethod,
    vRtrLdpNgSessLoopDetectForPV               INTEGER,
    vRtrLdpNgSessPathVectorLimit               Unsigned32,
    vRtrLdpNgSessState                         INTEGER,
    vRtrLdpNgSessAdjacencyType                 TmnxLdpAdjacencyType,
    vRtrLdpNgSessProtocolVersion               Unsigned32,
    vRtrLdpNgSessLocalUdpPort                  Unsigned32,
    vRtrLdpNgSessPeerUdpPort                   Unsigned32,
    vRtrLdpNgSessLocalTcpPort                  Unsigned32,
    vRtrLdpNgSessPeerTcpPort                   Unsigned32,
    vRtrLdpNgSessLocalAddrType                 InetAddressType,
    vRtrLdpNgSessLocalAddress                  InetAddress,
    vRtrLdpNgSessPeerAddrType                  InetAddressType,
    vRtrLdpNgSessPeerAddress                   InetAddress,
    vRtrLdpNgSessKAHoldTimeRemaining           TimeInterval,
    vRtrLdpNgSessMaxPduLength                  Unsigned32,
    vRtrLdpNgSessUpTime                        TimeInterval,
    vRtrLdpNgSessLocalKATimeout                TmnxLdpNewKeepAliveTimeout,
    vRtrLdpNgSessPeerKATimeout                 TmnxLdpNewKeepAliveTimeout,
    vRtrLdpNgSessAdvertise                     INTEGER,
    vRtrLdpNgSessLclGRHelperState              TruthValue,
    vRtrLdpNgSessPeerGRState                   TruthValue,
    vRtrLdpNgSessPeerNumRestart                Counter32,   
    vRtrLdpNgSessLastRestartTime               TimeStamp,
    vRtrLdpNgSessLocalFtReconTime              Unsigned32,
    vRtrLdpNgSessPeerFtReconTime               Unsigned32,
    vRtrLdpNgSessLocalFtRecovTime              Unsigned32,
    vRtrLdpNgSessPeerFtRecovTime               Unsigned32,
    vRtrLdpNgSessFtReconTimeRem                Unsigned32,
    vRtrLdpNgSessFtRecovTimeRem                Unsigned32,
    vRtrLdpNgSessBfdStatus                     INTEGER,
    vRtrLdpNgSessLocalP2MPCap                  TruthValue,
    vRtrLdpNgSessPeerP2MPCap                   TruthValue,
    vRtrLdpNgSessLocalMPMBBCap                 TruthValue,
    vRtrLdpNgSessPeerMPMBBCap                  TruthValue,
    vRtrLdpNgSessLocalDynCap                   TruthValue,
    vRtrLdpNgSessPeerDynCap                    TruthValue,
    vRtrLdpNgSessLocalOLoadCap                 TruthValue,
    vRtrLdpNgSessPeerOLoadCap                  TruthValue,
    vRtrLdpNgSessIPv4PfxFecOLoadSent           TruthValue,
    vRtrLdpNgSessIPv6PfxFecOLoadSent           TruthValue,
    vRtrLdpNgSessIPv4PfxFecOLoadRecv           TruthValue,
    vRtrLdpNgSessIPv6PfxFecOLoadRecv           TruthValue,
    vRtrLdpNgSessIPv4P2MPFecOLSent             TruthValue,
    vRtrLdpNgSessIPv6P2MPFecOLSent             TruthValue,
    vRtrLdpNgSessIPv4P2MPFecOLRecv             TruthValue,
    vRtrLdpNgSessIPv6P2MPFecOLRecv             TruthValue,
    vRtrLdpNgSessSvcFec128OLoadSent            TruthValue,
    vRtrLdpNgSessSvcFec128OLoadRecv            TruthValue,
    vRtrLdpNgSessSvcFec129OLoadSent            TruthValue,
    vRtrLdpNgSessSvcFec129OLoadRecv            TruthValue,
    vRtrLdpNgSessLocalIPv4PfxFecCap            TruthValue,
    vRtrLdpNgSessPeerIPv4PfxFecCap             TruthValue,
    vRtrLdpNgSessLocalIPv6PfxFecCap            TruthValue,
    vRtrLdpNgSessPeerIPv6PfxFecCap             TruthValue,
    vRtrLdpNgSessLocalSvcFec128Cap             TruthValue,
    vRtrLdpNgSessPeerSvcFec128Cap              TruthValue,
    vRtrLdpNgSessLocalSvcFec129Cap             TruthValue,
    vRtrLdpNgSessPeerSvcFec129Cap              TruthValue,
    vRtrLdpNgSessOperMaxFecThreshold           Unsigned32  
}

vRtrLdpNgSessLocalLdpIdType    OBJECT-TYPE
    SYNTAX      TmnxMplsLdpNgIdType
    MAX-ACCESS  read-only
    STATUS      current
    DESCRIPTION
        "The value of vRtrLdpNgSessLocalLdpIdType indicates the local LDP
         identifier type for the LDP session indicated by 
         vRtrLdpNgSessLocalLdpId."
    ::= { vRtrLdpNgSessionEntry 1 }
    
vRtrLdpNgSessLocalLdpId    OBJECT-TYPE
    SYNTAX      TmnxMplsLdpNgIdentifier (SIZE (6|18))
    MAX-ACCESS  read-only
    STATUS      current
    DESCRIPTION
        "The value of vRtrLdpNgSessLocalLdpId indicates the local LDP
         identifier for this LDP session."
    ::= { vRtrLdpNgSessionEntry 2 }

vRtrLdpNgSessEntityIndex    OBJECT-TYPE
    SYNTAX      Unsigned32 (1..4294967295)
    MAX-ACCESS  read-only
    STATUS      current
    DESCRIPTION
        "The value of vRtrLdpNgSessEntityIndex indicates the Entity index
         for the LDP entity represented in this session."
    ::= { vRtrLdpNgSessionEntry 3 }

vRtrLdpNgSessLabelDistMethod    OBJECT-TYPE
    SYNTAX      TmnxLdpLabelDistMethod
    MAX-ACCESS  read-only
    STATUS      current
    DESCRIPTION
        "The value of vRtrLdpNgSessLabelDistMethod indicates the label 
         distribution method used for this LDP session."
    ::= { vRtrLdpNgSessionEntry 4 }

vRtrLdpNgSessLoopDetectForPV    OBJECT-TYPE
    SYNTAX      INTEGER {
                    disabled(0),
                    enabled(1)
                }
    MAX-ACCESS  read-only
    STATUS      current
    DESCRIPTION
        "The value of vRtrLdpNgSessLoopDetectForPV indicates whether
         loop detection based on path vectors is disabled or enabled 
         for this LDP session.

         If this object has a value of disabled(0), then loop detection
         is disabled.  Otherwise, if this object has a value of enabled(1), 
         then loop detection based on path vectors is enabled."
    ::= { vRtrLdpNgSessionEntry 5 }

vRtrLdpNgSessPathVectorLimit    OBJECT-TYPE
    SYNTAX      Unsigned32 (0..255)
    MAX-ACCESS  read-only
    STATUS      current
    DESCRIPTION
        "If the value of vRtrLdpNgSessLoopDetectForPV for this entry 
         is 'enabled', then the value of vRtrLdpNgSessPathVectorLimit
         represents the Path Vector Limit for this LDP Session.

         If the value of vRtrLdpNgSessLoopDetectForPV for this entry 
         is 'disabled', then the value of vRtrLdpNgSessPathVectorLimit
         be 0 (zero)."
    ::= { vRtrLdpNgSessionEntry 6 }

vRtrLdpNgSessState    OBJECT-TYPE
    SYNTAX      INTEGER {
                    nonexistent(1),
                    initialized(2),
                    openrec(3),
                    opensent(4),
                    operational(5)
                }
    MAX-ACCESS  read-only
    STATUS      current
    DESCRIPTION
        "The value of vRtrLdpNgSessState indicates the current state 
         of the LDP session. All of the states 1 - 5 are based on the 
         state machine for session negotiation behavior."
    ::= { vRtrLdpNgSessionEntry 7 }

vRtrLdpNgSessAdjacencyType    OBJECT-TYPE
    SYNTAX      TmnxLdpAdjacencyType
    MAX-ACCESS  read-only
    STATUS      current
    DESCRIPTION
        "The value of vRtrLdpNgSessAdjacencyType indicates the adjacency
         type(s) supporting this LDP Session."
    ::= { vRtrLdpNgSessionEntry 8 }

vRtrLdpNgSessProtocolVersion    OBJECT-TYPE
    SYNTAX      Unsigned32
    MAX-ACCESS  read-only
    STATUS      current
    DESCRIPTION
        "The value of vRtrLdpNgSessProtocolVersion indicates the version
         of the LDP Protocol used by this session."
    ::= { vRtrLdpNgSessionEntry 9 }

vRtrLdpNgSessLocalUdpPort    OBJECT-TYPE
    SYNTAX      Unsigned32 (0..65535)
    MAX-ACCESS  read-only
    STATUS      current
    DESCRIPTION
        "The value of vRtrLdpNgSessLocalUdpPort indicates the UDP port
         used locally for LDP discovery."
    ::= { vRtrLdpNgSessionEntry 10 }

vRtrLdpNgSessPeerUdpPort    OBJECT-TYPE
    SYNTAX      Unsigned32 (0..65535)
    MAX-ACCESS  read-only
    STATUS      current
    DESCRIPTION
        "The value of vRtrLdpNgSessPeerUdpPort indicates the UDP port 
         used on the remote end for LDP discovery."
    ::= { vRtrLdpNgSessionEntry 11 }

vRtrLdpNgSessLocalTcpPort    OBJECT-TYPE
    SYNTAX      Unsigned32 (0..65535)
    MAX-ACCESS  read-only
    STATUS      current
    DESCRIPTION
        "The value of vRtrLdpNgSessLocalTcpPort indicates the TCP port 
         used locally for the LDP Session."
    ::= { vRtrLdpNgSessionEntry 12 }

vRtrLdpNgSessPeerTcpPort    OBJECT-TYPE
    SYNTAX      Unsigned32 (0..65535)
    MAX-ACCESS  read-only
    STATUS      current
    DESCRIPTION
        "The value of vRtrLdpNgSessPeerTcpPort indicates the TCP port 
         used on the remote end for the LDP Session."
    ::= { vRtrLdpNgSessionEntry 13 }

vRtrLdpNgSessLocalAddrType    OBJECT-TYPE
    SYNTAX      InetAddressType
    MAX-ACCESS  read-only
    STATUS      current
    DESCRIPTION
        "The value of vRtrLdpNgSessLocalAddrType indicates the type of
         address indicated by vRtrLdpNgSessLocalAddress."
    ::= { vRtrLdpNgSessionEntry 14 }
    
vRtrLdpNgSessLocalAddress    OBJECT-TYPE
    SYNTAX      InetAddress (SIZE (0|4|16))
    MAX-ACCESS  read-only
    STATUS      current
    DESCRIPTION
        "The value of vRtrLdpNgSessLocalAddress indicates the IP address
         used locally for the LDP Session."
    ::= { vRtrLdpNgSessionEntry 15 }

vRtrLdpNgSessPeerAddrType    OBJECT-TYPE
    SYNTAX      InetAddressType
    MAX-ACCESS  read-only
    STATUS      current
    DESCRIPTION
        "The value of vRtrLdpNgSessPeerAddrType indicates the type of
         address indicated by vRtrLdpNgSessPeerAddress."
    ::= { vRtrLdpNgSessionEntry 16 }
    
vRtrLdpNgSessPeerAddress    OBJECT-TYPE
    SYNTAX      InetAddress (SIZE (0|4|16))
    MAX-ACCESS  read-only
    STATUS      current
    DESCRIPTION
        "The value of vRtrLdpNgSessPeerAddress indicates the IP address
         used on the remote end for the LDP Session."
    ::= { vRtrLdpNgSessionEntry 17 }

vRtrLdpNgSessKAHoldTimeRemaining    OBJECT-TYPE
    SYNTAX      TimeInterval
    UNITS       "seconds"
    MAX-ACCESS  read-only
    STATUS      current
    DESCRIPTION
        "The value of vRtrLdpNgSessKAHoldTimeRemaining indicates the 
         keep alive hold time remaining for this LDP session."
    ::= { vRtrLdpNgSessionEntry 18 }

vRtrLdpNgSessMaxPduLength    OBJECT-TYPE
    SYNTAX      Unsigned32 (1..65535)
    MAX-ACCESS  read-only
    STATUS      current
    DESCRIPTION
        "The value of vRtrLdpNgSessMaxPduLength indicates the maximum
         allowable length for LDP PDUs for this session. This value may 
         have been negotiated during Session Initialization."
    ::= { vRtrLdpNgSessionEntry 19 }

vRtrLdpNgSessUpTime    OBJECT-TYPE
    SYNTAX      TimeInterval
    UNITS       "hundreds of seconds"
    MAX-ACCESS  read-only
    STATUS      current
    DESCRIPTION
        "The value of vRtrLdpNgSessUpTime indicates the time since the session 
        was established."
    ::= { vRtrLdpNgSessionEntry 20 }

vRtrLdpNgSessLocalKATimeout    OBJECT-TYPE
    SYNTAX      TmnxLdpNewKeepAliveTimeout
    MAX-ACCESS  read-only
    STATUS      current
    DESCRIPTION
        "The value of vRtrLdpNgSessLocalKATimeout indicates the keepalive 
         timeout used locally for the LDP Session."
    ::= { vRtrLdpNgSessionEntry 21 }

vRtrLdpNgSessPeerKATimeout    OBJECT-TYPE
    SYNTAX      TmnxLdpNewKeepAliveTimeout
    MAX-ACCESS  read-only
    STATUS      current
    DESCRIPTION
        "The value of vRtrLdpNgSessPeerKATimeout indicates the keepalive 
         timeout used at the remote end of the LDP Session."
    ::= { vRtrLdpNgSessionEntry 22 }

vRtrLdpNgSessAdvertise    OBJECT-TYPE
    SYNTAX      INTEGER {
                   address (1),
                   service (2),
                   addressAndService (3)
                }
    MAX-ACCESS  read-only
    STATUS      current
    DESCRIPTION
        "The value of vRtrLdpNgSessAdvertise indicates the type of FECs
         that will be transported by the session."
    ::= { vRtrLdpNgSessionEntry 23 }

vRtrLdpNgSessLclGRHelperState    OBJECT-TYPE
    SYNTAX      TruthValue
    MAX-ACCESS  read-only
    STATUS      current
    DESCRIPTION
        "The value of vRtrLdpNgSessLclGRHelperState indicates whether the local 
         entity of this session is graceful restart helper capable or not."
    ::= { vRtrLdpNgSessionEntry 24 }

vRtrLdpNgSessPeerGRState    OBJECT-TYPE
    SYNTAX      TruthValue
    MAX-ACCESS  read-only
    STATUS      current
    DESCRIPTION
        "The value of vRtrLdpNgSessPeerGRState indicates whether the 
         peer entity of this session is capable of supporting graceful restart."
    ::= { vRtrLdpNgSessionEntry 25 }

vRtrLdpNgSessPeerNumRestart    OBJECT-TYPE
    SYNTAX      Counter32 
    MAX-ACCESS  read-only
    STATUS      current
    DESCRIPTION
        "The value of vRtrLdpNgSessPeerNumRestart indicates the number of 
         times graceful restart helper was initiated for this session."
    ::= { vRtrLdpNgSessionEntry 26 }

vRtrLdpNgSessLastRestartTime    OBJECT-TYPE
    SYNTAX      TimeStamp 
    MAX-ACCESS  read-only
    STATUS      current
    DESCRIPTION
        "The value of vRtrLdpNgSessLastRestartTime indicates the last time 
         graceful restart helper was initiated."
    ::= { vRtrLdpNgSessionEntry 27 }

vRtrLdpNgSessLocalFtReconTime   OBJECT-TYPE
    SYNTAX      Unsigned32
    UNITS       "seconds"
    MAX-ACCESS  read-only
    STATUS      current
    DESCRIPTION
       "The value of vRtrLdpNgSessLocalFtReconTime indicates the session's
        local entity Fault Tolerant(FT) Reconnect Timeout."
    ::= { vRtrLdpNgSessionEntry 28 }

vRtrLdpNgSessPeerFtReconTime OBJECT-TYPE
    SYNTAX      Unsigned32
    UNITS       "seconds"
    MAX-ACCESS  read-only
    STATUS      current
    DESCRIPTION
       "The value of vRtrLdpNgSessPeerFtReconTime indicates the session's
        peer entity Fault Tolerant(FT) Reconnect Timeout."
    ::= { vRtrLdpNgSessionEntry 29 } 

vRtrLdpNgSessLocalFtRecovTime OBJECT-TYPE
    SYNTAX      Unsigned32
    UNITS       "seconds"
    MAX-ACCESS  read-only
    STATUS      current
    DESCRIPTION
       "The value of vRtrLdpNgSessLocalFtRecovTime indicates the session's
        local entity Fault Tolerant(FT) recovery timeout."
    ::= { vRtrLdpNgSessionEntry 30 }

vRtrLdpNgSessPeerFtRecovTime OBJECT-TYPE
    SYNTAX      Unsigned32
    UNITS       "seconds"
    MAX-ACCESS  read-only
    STATUS      current
    DESCRIPTION
       "The value of vRtrLdpNgSessPeerFtRecovTime indicates the session's
        peer entity Fault Tolerant(FT) recovery timeout."
    ::= { vRtrLdpNgSessionEntry 31 }

vRtrLdpNgSessFtReconTimeRem  OBJECT-TYPE
    SYNTAX      Unsigned32
    UNITS       "seconds"
    MAX-ACCESS  read-only
    STATUS      current
    DESCRIPTION
       "The value of vRtrLdpNgSessFtReconTimeRem indicates the amount 
        of time left before session's Fault Tolerant(FT) reconnect timeout 
        expires. This value is set to lesser of the neighbor advertised FT 
        recovery timeout, vRtrLdpNgSessPeerFtRecovTime and the local recovery
        timeout, vRtrLdpNgSessLocalFtRecovTime."
    ::= { vRtrLdpNgSessionEntry 32 } 
 
vRtrLdpNgSessFtRecovTimeRem OBJECT-TYPE
    SYNTAX      Unsigned32
    UNITS       "seconds"
    MAX-ACCESS  read-only
    STATUS      current
    DESCRIPTION
       "The value of vRtrLdpNgSessFtRecovTimeRem indicates the amount of time 
        left before session's Fault Tolerant(FT) recovery timeout
        expires. This value is set to lesser of the neighbor advertised FT 
        recovery timeout, vRtrLdpNgSessPeerFtRecovTime and the local recovery 
        timeout, vRtrLdpNgSessLocalFtRecovTime."
    ::= { vRtrLdpNgSessionEntry 33 }

vRtrLdpNgSessBfdStatus  OBJECT-TYPE
    SYNTAX      INTEGER {
                   noService (1),
                   inService (2),
                   outOfService (3)
                }
    MAX-ACCESS  read-only
    STATUS      current
    DESCRIPTION
        "The value of vRtrLdpNgSessBfdStatus indicates the BFD operational
         status for the LDP session.

         If the value of vRtrLdpNgSessBfdStatus is 'noService', BFD is 
         not enabled for the LDP session. If the value of the object is
         'outOfService', BFD is enabled but it is down and not running.
         If the value of object is 'inService', BFD is enabled and it is
         running."
    ::= { vRtrLdpNgSessionEntry 34 }

vRtrLdpNgSessLocalP2MPCap    OBJECT-TYPE
    SYNTAX      TruthValue
    MAX-ACCESS  read-only
    STATUS      current
    DESCRIPTION
        "The value of vRtrLdpNgSessLocalP2MPCap indicates whether the 
         local entity of this session is capable of exchanging P2MP FECs."
    ::= { vRtrLdpNgSessionEntry 35 }

vRtrLdpNgSessPeerP2MPCap    OBJECT-TYPE
    SYNTAX      TruthValue
    MAX-ACCESS  read-only
    STATUS      current
    DESCRIPTION
        "The value of vRtrLdpNgSessPeerP2MPCap indicates whether the 
         peer entity of this session is capable of exchanging P2MP FECs."
    ::= { vRtrLdpNgSessionEntry 36 }

vRtrLdpNgSessLocalMPMBBCap    OBJECT-TYPE
    SYNTAX      TruthValue
    MAX-ACCESS  read-only
    STATUS      current
    DESCRIPTION
        "The value of vRtrLdpNgSessLocalMPMBBCap indicates whether the 
         local entity of this session is capable of Multipoint MBB."
    ::= { vRtrLdpNgSessionEntry 37 }

vRtrLdpNgSessPeerMPMBBCap    OBJECT-TYPE
    SYNTAX      TruthValue
    MAX-ACCESS  read-only
    STATUS      current
    DESCRIPTION
        "The value of vRtrLdpNgSessPeerMPMBBCap indicates whether the 
         peer entity of this session is capable of Multipoint MBB."
    ::= { vRtrLdpNgSessionEntry 38 }

vRtrLdpNgSessLocalDynCap    OBJECT-TYPE
    SYNTAX      TruthValue
    MAX-ACCESS  read-only
    STATUS      current
    DESCRIPTION
        "The value of vRtrLdpNgSessLocalDynCap indicates whether the 
         local entity of this session supports negotiation of LDP session 
         capabilities dynamically."
    ::= { vRtrLdpNgSessionEntry 39 }

vRtrLdpNgSessPeerDynCap    OBJECT-TYPE
    SYNTAX      TruthValue
    MAX-ACCESS  read-only
    STATUS      current
    DESCRIPTION
        "The value of vRtrLdpNgSessPeerDynCap indicates whether the 
         peer entity of this session supports negotiation of LDP session 
         capabilities dynamically."
    ::= { vRtrLdpNgSessionEntry 40 }

vRtrLdpNgSessLocalOLoadCap    OBJECT-TYPE
    SYNTAX      TruthValue
    MAX-ACCESS  read-only
    STATUS      current
    DESCRIPTION
        "The value of vRtrLdpNgSessLocalOLoadCap indicates whether the
         local entity of this session is capable of signaling LSR Overload 
         Notification."
    ::= { vRtrLdpNgSessionEntry 41 }

vRtrLdpNgSessPeerOLoadCap    OBJECT-TYPE
    SYNTAX      TruthValue
    MAX-ACCESS  read-only
    STATUS      current
    DESCRIPTION
        "The value of vRtrLdpNgSessPeerOLoadCap indicates whether the
         peer entity of this session is capable of signaling LSR Overload 
         Notification."
    ::= { vRtrLdpNgSessionEntry 42 }

vRtrLdpNgSessIPv4PfxFecOLoadSent    OBJECT-TYPE
    SYNTAX      TruthValue
    MAX-ACCESS  read-only
    STATUS      current
    DESCRIPTION
        "The value of vRtrLdpNgSessIPv4PfxFecOLoadSent indicates whether LSR 
         Overload Notification has been sent to the LDP peer for IPv4 Prefix 
         FEC Type.

         The value of 'true' indicates that Local LSR has set the 
         LDP session as overloaded for IPv4 Prefix FEC type and is not ready 
         to receive new Label Mappings for IPv4 Prefix FEC Type. In this 
         state if a Label Mapping Message is received from peer for any IPv4 
         Prefix FEC type then the Label is returned with a Label Release 
         Message."
    ::= { vRtrLdpNgSessionEntry 43 }

vRtrLdpNgSessIPv6PfxFecOLoadSent    OBJECT-TYPE
    SYNTAX      TruthValue
    MAX-ACCESS  read-only
    STATUS      current
    DESCRIPTION
        "The value of vRtrLdpNgSessIPv6PfxFecOLoadSent indicates whether LSR 
         Overload Notification has been sent to the LDP peer for IPv6 Prefix 
         FEC Type.

         The value of 'true' indicates that Local LSR has set the 
         LDP session as overloaded for IPv6 Prefix FEC type and is not ready 
         to receive new Label Mappings for IPv6 Prefix FEC Type. In this 
         state if a Label Mapping Message is received from peer for any IPv6 
         Prefix FEC type then the Label is returned with a Label Release 
         Message."
    ::= { vRtrLdpNgSessionEntry 44 }

vRtrLdpNgSessIPv4PfxFecOLoadRecv    OBJECT-TYPE
    SYNTAX      TruthValue
    MAX-ACCESS  read-only
    STATUS      current
    DESCRIPTION
        "The value of vRtrLdpNgSessIPv4PfxFecOLoadRecv indicates whether LSR 
         Overload Notification has been received from the LDP peer for IPv4 
         Prefix FEC Type.

         The value of 'true' indicates that Peer LSR has set the 
         LDP session as overloaded for IPv4 Prefix FEC type and is not ready 
         to receive new Label Mappings for any IPv4 Prefix FEC Type. In this 
         state no new Label Mapping Message would be sent to peer for any 
         IPv4 Prefix FEC Type."
    ::= { vRtrLdpNgSessionEntry 45 }

vRtrLdpNgSessIPv6PfxFecOLoadRecv    OBJECT-TYPE
    SYNTAX      TruthValue
    MAX-ACCESS  read-only
    STATUS      current
    DESCRIPTION
        "The value of vRtrLdpNgSessIPv6PfxFecOLoadRecv indicates whether LSR 
         Overload Notification has been received from the LDP peer for IPv6 
         Prefix FEC Type.

         The value of 'true' indicates that Peer LSR has set the 
         LDP session as overloaded for IPv6 Prefix FEC type and is not ready 
         to receive new Label Mappings for any IPv6 Prefix FEC Type. In this 
         state no new Label Mapping Message would be sent to peer for any
         IPv6 Prefix FEC Type."
    ::= { vRtrLdpNgSessionEntry 46 }

vRtrLdpNgSessIPv4P2MPFecOLSent    OBJECT-TYPE
    SYNTAX      TruthValue
    MAX-ACCESS  read-only
    STATUS      current
    DESCRIPTION
        "The value of vRtrLdpNgSessIPv4P2MPFecOLSent indicates whether LSR 
         Overload Notification has been sent to the LDP peer for IPv4 P2MP 
         FEC Type.

         The value of 'true' indicates that Local LSR has set the 
         LDP session as overloaded for IPv4 P2MP FEC type and is not ready 
         to receive new Label Mappings for IPv4 P2MP FEC Type. In this 
         state if a Label Mapping Message is received from peer for IPv4 
         P2MP FEC type then the Label is returned with a Label Release 
         Message."
    ::= { vRtrLdpNgSessionEntry 47 }

vRtrLdpNgSessIPv6P2MPFecOLSent    OBJECT-TYPE
    SYNTAX      TruthValue
    MAX-ACCESS  read-only
    STATUS      current
    DESCRIPTION
        "The value of vRtrLdpNgSessIPv6P2MPFecOLSent indicates whether LSR 
         Overload Notification has been sent to the LDP peer for IPv6 P2MP 
         FEC Type.

         The value of 'true' indicates that Local LSR has set the 
         LDP session as overloaded for IPv6 P2MP FEC type and is not ready 
         to receive new Label Mappings for IPv6 P2MP FEC Type. In this 
         state if a Label Mapping Message is received from peer for IPv6 
         P2MP FEC type then the Label is returned with a Label Release 
         Message."
    ::= { vRtrLdpNgSessionEntry 48 }

vRtrLdpNgSessIPv4P2MPFecOLRecv    OBJECT-TYPE
    SYNTAX      TruthValue
    MAX-ACCESS  read-only
    STATUS      current
    DESCRIPTION
        "The value of vRtrLdpNgSessIPv4P2MPFecOLRecv indicates whether LSR 
         Overload Notification has been received from the LDP peer for IPv4 
         P2MP FEC Type.

         The value of 'true' indicates that Peer LSR has set the 
         LDP session as overloaded for IPv4 P2MP FEC type and is not ready 
         to receive new Label Mappings for IPv4 P2MP FEC Type. In this 
         state no new Label Mapping Message would be sent to peer for IPv4 
         P2MP FEC Type."
    ::= { vRtrLdpNgSessionEntry 49 }

vRtrLdpNgSessIPv6P2MPFecOLRecv    OBJECT-TYPE
    SYNTAX      TruthValue
    MAX-ACCESS  read-only
    STATUS      current
    DESCRIPTION
        "The value of vRtrLdpNgSessIPv6P2MPFecOLRecv indicates whether LSR 
         Overload Notification has been received from the LDP peer for IPv6 
         P2MP FEC Type.

         The value of 'true' indicates that Peer LSR has set the 
         LDP session as overloaded for IPv6 P2MP FEC type and is not ready 
         to receive new Label Mappings for IPv6 P2MP FEC Type. In this 
         state no new Label Mapping Message would be sent to peer for IPv6
         P2MP FEC Type."
    ::= { vRtrLdpNgSessionEntry 50 }

vRtrLdpNgSessSvcFec128OLoadSent    OBJECT-TYPE
    SYNTAX      TruthValue
    MAX-ACCESS  read-only
    STATUS      current
    DESCRIPTION
        "The value of vRtrLdpNgSessSvcFec128OLoadSent indicates whether LSR 
         Overload Notification has been sent to the LDP peer for Service
         FEC 128 Type.

         The value of 'true' indicates that Local LSR has set the 
         LDP session as overloaded for Service FEC 128 type and is not ready 
         to receive new Label Mappings for Service FEC 128 Type. In this 
         state if a Label Mapping Message is received from peer for Service 
         FEC 128 type then the Label is returned with a Label Release Message."
    ::= { vRtrLdpNgSessionEntry 51 }

vRtrLdpNgSessSvcFec128OLoadRecv    OBJECT-TYPE
    SYNTAX      TruthValue
    MAX-ACCESS  read-only
    STATUS      current
    DESCRIPTION
        "The value of vRtrLdpNgSessSvcFec128OLoadRecv indicates whether LSR 
         Overload Notification has been received from the LDP peer for Service
         FEC 128 Type.

         The value of 'true' indicates that Peer LSR has set the 
         LDP session as overloaded for Service FEC 128 type and is not ready 
         to receive new Label Mappings for Service FEC 128 Type. In this 
         state no new Label Mapping Message would be sent to peer for 
         any Service FEC 128 Type."
    ::= { vRtrLdpNgSessionEntry 52 }

vRtrLdpNgSessSvcFec129OLoadSent    OBJECT-TYPE
    SYNTAX      TruthValue
    MAX-ACCESS  read-only
    STATUS      current
    DESCRIPTION
        "The value of vRtrLdpNgSessSvcFec129OLoadSent indicates whether LSR 
         Overload Notification has been sent to the LDP peer for 
         Service FEC 129 Type.

         The value of 'true' indicates that Local LSR has set the 
         LDP session as overloaded for Service FEC 129 type and is not ready 
         to receive new Label Mappings for any Service FEC 129 Type. In this 
         state if a Label Mapping Message is received from peer for Service 
         FEC 129 type then the Label is returned with a Label Release Message."
    ::= { vRtrLdpNgSessionEntry 53 }

vRtrLdpNgSessSvcFec129OLoadRecv    OBJECT-TYPE
    SYNTAX      TruthValue
    MAX-ACCESS  read-only
    STATUS      current
    DESCRIPTION
        "The value of vRtrLdpNgSessSvcFec129OLoadRecv indicates whether LSR 
         Overload Notification has been received from the LDP peer for 
         Service FEC 129 Type.

         The value of 'true' indicates that Peer LSR has set the 
         LDP session as overloaded for Service FEC 129 type and is not ready 
         to receive new Label Mappings for any Service FEC 129 Type. In this 
         state no new Label Mapping Message would be sent to peer for 
         any Service FEC 129 Type."
    ::= { vRtrLdpNgSessionEntry 54 }
 
vRtrLdpNgSessLocalIPv4PfxFecCap    OBJECT-TYPE
    SYNTAX      TruthValue
    MAX-ACCESS  read-only
    STATUS      current
    DESCRIPTION
        "The value of vRtrLdpNgSessLocalIPv4PfxFecCap indicates whether the 
         local entity of this session is capable of exchanging IPv4 FECs."
    ::= { vRtrLdpNgSessionEntry 55 }
    
vRtrLdpNgSessPeerIPv4PfxFecCap    OBJECT-TYPE
    SYNTAX      TruthValue
    MAX-ACCESS  read-only
    STATUS      current
    DESCRIPTION
        "The value of vRtrLdpNgSessPeerIPv4PfxFecCap indicates whether the 
         peer entity of this session is capable of exchanging IPv4 FECs."
    ::= { vRtrLdpNgSessionEntry 56 }

vRtrLdpNgSessLocalIPv6PfxFecCap    OBJECT-TYPE
    SYNTAX      TruthValue
    MAX-ACCESS  read-only
    STATUS      current
    DESCRIPTION
        "The value of vRtrLdpNgSessLocalIPv6PfxFecCap indicates whether the 
         local entity of this session is capable of exchanging IPv6 FECs."
    ::= { vRtrLdpNgSessionEntry 57 }

vRtrLdpNgSessPeerIPv6PfxFecCap    OBJECT-TYPE
    SYNTAX      TruthValue
    MAX-ACCESS  read-only
    STATUS      current
    DESCRIPTION
        "The value of vRtrLdpNgSessPeerIPv6PfxFecCap indicates whether the 
         peer entity of this session is capable of exchanging IPv6 FECs."
    ::= { vRtrLdpNgSessionEntry 58 }

vRtrLdpNgSessLocalSvcFec128Cap    OBJECT-TYPE
    SYNTAX      TruthValue
    MAX-ACCESS  read-only
    STATUS      current
    DESCRIPTION
        "The value of vRtrLdpNgSessLocalSvcFec128Cap indicates whether the
         local entity of this session is capable of exchanging PW ID FECs."
    ::= { vRtrLdpNgSessionEntry 59 }

vRtrLdpNgSessPeerSvcFec128Cap    OBJECT-TYPE
    SYNTAX      TruthValue
    MAX-ACCESS  read-only
    STATUS      current
    DESCRIPTION
        "The value of vRtrLdpNgSessPeerSvcFec128Cap indicates whether the peer 
         entity of this session is capable of exchanging PW ID FECs."
    ::= { vRtrLdpNgSessionEntry 60 }

vRtrLdpNgSessLocalSvcFec129Cap    OBJECT-TYPE
    SYNTAX      TruthValue
    MAX-ACCESS  read-only
    STATUS      current
    DESCRIPTION
        "The value of vRtrLdpNgSessLocalSvcFec129Cap indicates whether the
         local entity of this session is capable of exchanging General PW ID FECs."
    ::= { vRtrLdpNgSessionEntry 61 }

vRtrLdpNgSessPeerSvcFec129Cap    OBJECT-TYPE
    SYNTAX      TruthValue
    MAX-ACCESS  read-only
    STATUS      current
    DESCRIPTION
        "The value of vRtrLdpNgSessPeerSvcFec129Cap indicates whether the peer 
         entity of this session is capable of exchanging General PW ID FECs over 
         the session."
    ::= { vRtrLdpNgSessionEntry 62 }

vRtrLdpNgSessOperMaxFecThreshold    OBJECT-TYPE
    SYNTAX      Unsigned32
    UNITS       "percentage"
    MAX-ACCESS  read-only
    STATUS      current
    DESCRIPTION
        " The value of vRtrLdpNgSessOperMaxFecThreshold indicates the 
          operational percentage of vRtrLdpNgSessParamMaxFec. "
    ::= { vRtrLdpNgSessionEntry 63 }

--
--  The Label Distribution Protocol (LDP) Peer Tunneling Lsp Table
--

vRtrLdpNgTargPeerTunlLspTblLstCh OBJECT-TYPE
    SYNTAX     TimeStamp
    MAX-ACCESS read-only
    STATUS     current
    DESCRIPTION
        "The value of vRtrLdpNgTargPeerTunlLspTblLstCh indicates the last
         timestamp when an entry in the vRtrLdpNgTargPeerTunnelLspTable was last 
         changed."
    ::= { tmnxLdpNgObjs 5 }

vRtrLdpNgTargPeerTunnelLspTable  OBJECT-TYPE
     SYNTAX      SEQUENCE OF VRtrLdpNgTargPeerTunnelLspEntry
     MAX-ACCESS  not-accessible
     STATUS      current
     DESCRIPTION
         "The vRtrLdpNgTargPeerTunnelLspTable keeps the list of LDP-over-RSVP LSP 
          ids which are currently supported by the application.
      
          Each LSP ID in the list corresponds to the vRtrMplsLspIndex of 
          the given MPLS LSP."
     ::= { tmnxLdpNgObjs 6 }

vRtrLdpNgTargPeerTunnelLspEntry OBJECT-TYPE
    SYNTAX      VRtrLdpNgTargPeerTunnelLspEntry
    MAX-ACCESS  not-accessible
    STATUS      current
    DESCRIPTION
        "A row in this table contains the LSP id information about an LDP
         interface or targeted peer.
         
         Row entry can be only created if there is corresponding targeted
         peer entry in vRtrLdpNgTargPeerTable.

         Row entries can be created or deleted via SNMP SET requests. 
         A row is created by setting vRtrLdpNgTargPeerLspRowStatus to 'createAndGo'
         provided the corresponding LSP id exists as an MPLS lsp.
         A row entry can be destroyed by setting vRtrLdpNgTargPeerLspRowStatus to 
         'destroy'."
    INDEX  { vRtrID, 
             vRtrLdpNgPeerAddressType,
             vRtrLdpNgPeerAddress,
             vRtrLdpNgTargPeerLspId }
    ::= { vRtrLdpNgTargPeerTunnelLspTable 1 }

VRtrLdpNgTargPeerTunnelLspEntry ::= SEQUENCE {
    vRtrLdpNgTargPeerLspId               TmnxVRtrMplsLspID,
    vRtrLdpNgTargPeerLspRowStatus        RowStatus
}

vRtrLdpNgTargPeerLspId    OBJECT-TYPE
    SYNTAX      TmnxVRtrMplsLspID
    MAX-ACCESS  not-accessible
    STATUS      current
    DESCRIPTION
        "The value of vRtrLdpNgTargPeerLspId specifies the LSP id of the LSP
         associated with the specified interface or targeted peer."
    ::= { vRtrLdpNgTargPeerTunnelLspEntry 1 }

vRtrLdpNgTargPeerLspRowStatus  OBJECT-TYPE
    SYNTAX      RowStatus
    MAX-ACCESS  read-create
    STATUS      current
    DESCRIPTION
        "vRtrLdpNgTargPeerLspRowStatus is used to create, delete or 
         control entries in the vRtrLdpNgTargPeerTunnelLspTable.
 
         An entry is created by setting vRtrLdpNgTargPeerLspRowStatus 
         to 'createAndGo'.
 
         An entry is deleted by setting vRtrLdpNgTargPeerLspRowStatus 
         to 'destroy'."
    ::= { vRtrLdpNgTargPeerTunnelLspEntry 2 }

--
--  LDP Peer Parameter Table
--

vRtrLdpNgSessionParamsTableLstCh OBJECT-TYPE
    SYNTAX     TimeStamp
    MAX-ACCESS read-only
    STATUS     current
    DESCRIPTION
        "The value of vRtrLdpNgSessionParamsTableLstCh indicates the last
         timestamp when an entry in the vRtrLdpNgSessionParamsTable was last 
         changed."
    ::= { tmnxLdpNgObjs 7 }
    
vRtrLdpNgSessionParamsTable    OBJECT-TYPE
    SYNTAX      SEQUENCE OF VRtrLdpNgSessionParamsEntry
    MAX-ACCESS  not-accessible
    STATUS      current
    DESCRIPTION
        "The vRtrLdpNgSessionParamsTable is used to configure parameters
         applicable to an LDP session."
    ::= { tmnxLdpNgObjs 8 }

vRtrLdpNgSessionParamsEntry    OBJECT-TYPE
    SYNTAX      VRtrLdpNgSessionParamsEntry
    MAX-ACCESS  not-accessible
    STATUS      current
    DESCRIPTION
        "Each row entry represents an LDP session to a far end peer.

         Row entries can be created or deleted via SNMP SET requests. 
         A row with default attribute values is created by setting 
         vRtrLdpNgSessParamRowStatus to 'createAndGo'. A row entry can be 
         destroyed by setting vRtrLdpNgSessParamRowStatus to 'destroy'."
   INDEX  { vRtrID,
            vRtrLdpNgPeerAddressType,
            vRtrLdpNgPeerAddress }
   ::= { vRtrLdpNgSessionParamsTable 1 }

VRtrLdpNgSessionParamsEntry ::= SEQUENCE {
    vRtrLdpNgSessParamRowStatus                RowStatus,
    vRtrLdpNgSessParamAuth                     TruthValue,
    vRtrLdpNgSessParamAuthKey                  OCTET STRING,
    vRtrLdpNgSessParamMinTTLValue              Unsigned32,
    vRtrLdpNgSessParamTTLLogId                 TFilterLogId,
    vRtrLdpNgSessParamAuthKeyChain             TNamedItemOrEmpty,
    vRtrLdpNgSessParamDODLblDistrib            TruthValue,
    vRtrLdpNgSessParamImportPolicy1            TPolicyStatementNameOrEmpty,
    vRtrLdpNgSessParamImportPolicy2            TPolicyStatementNameOrEmpty,
    vRtrLdpNgSessParamImportPolicy3            TPolicyStatementNameOrEmpty,
    vRtrLdpNgSessParamImportPolicy4            TPolicyStatementNameOrEmpty,
    vRtrLdpNgSessParamImportPolicy5            TPolicyStatementNameOrEmpty, 
    vRtrLdpNgSessParamExportPolicy1            TPolicyStatementNameOrEmpty,
    vRtrLdpNgSessParamExportPolicy2            TPolicyStatementNameOrEmpty,
    vRtrLdpNgSessParamExportPolicy3            TPolicyStatementNameOrEmpty,
    vRtrLdpNgSessParamExportPolicy4            TPolicyStatementNameOrEmpty,
    vRtrLdpNgSessParamExportPolicy5            TPolicyStatementNameOrEmpty,
    vRtrLdpNgSessFec129CiscoInterop            TruthValue,
    vRtrLdpNgSessParamPMTUDiscovery            TruthValue,
    vRtrLdpNgSessParamAdvAdjAddrOnly           TruthValue,
    vRtrLdpNgSessPeIDMacFlushInterop           TruthValue,
    vRtrLdpNgSessParamIPv4PfxFecCap            TmnxEnabledDisabled,
    vRtrLdpNgSessParamIPv6PfxFecCap            TmnxEnabledDisabled,
    vRtrLdpNgSessParamP2MPFecCap               TmnxEnabledDisabled,
    vRtrLdpNgSessParamMaxFec                   Unsigned32,   
    vRtrLdpNgSessParamMaxFecLogOnly            TruthValue,
    vRtrLdpNgSessParamMaxFecThold              Unsigned32

}

vRtrLdpNgSessParamRowStatus    OBJECT-TYPE
    SYNTAX      RowStatus
    MAX-ACCESS  read-create
    STATUS      current
    DESCRIPTION
        "vRtrLdpNgSessParamRowStatus is used to control the creation and deletion
         of rows in the vRtrLdpNgSessionParamsTable. 

         A row can be created by setting vRtrLdpNgSessParamRowStatus to 'createAndGo'.
         The agent should assign the default attribute values and change 
         the row status to 'active'.

         A row entry can be destroyed by setting vRtrLdpNgSessParamRowStatus to
         'destroy'."
    ::= { vRtrLdpNgSessionParamsEntry 1 }
  
vRtrLdpNgSessParamAuth    OBJECT-TYPE
    SYNTAX      TruthValue
    MAX-ACCESS  read-create
    STATUS      current
    DESCRIPTION
        "When the value of vRtrLdpNgSessParamAuth is 'true', authentication
         using MD5 message based digest protocol is enabled.  When 'false',
         no authentication is used."
    DEFVAL { false }
    ::= { vRtrLdpNgSessionParamsEntry 2 }
        
vRtrLdpNgSessParamAuthKey    OBJECT-TYPE
    SYNTAX      OCTET STRING (SIZE(0..16))
    MAX-ACCESS  read-create
    STATUS      current
    DESCRIPTION
        "The string specified in vRtrLdpNgSessParamAuthKey is the authentication
         key to be used between LDP neighbors before establishing sessions. 
         Authentication is done using the MD-5 message based digest protocol.
         The authentication key can be any combination of letters or numbers.
         Note that the string may contain embedded nulls.

         An SNMP Get request on this object should return an OCTET STRING of
         length 0."
    DEFVAL { ''H }   -- the empty string
    ::= { vRtrLdpNgSessionParamsEntry 3 }

vRtrLdpNgSessParamMinTTLValue  OBJECT-TYPE
    SYNTAX      Unsigned32 (0 | 1..255)
    MAX-ACCESS  read-create
    STATUS      current
    DESCRIPTION
        "The value of vRtrLdpNgSessParamMinTTLValue specifies the minimum
         TTL value for an incoming LDP packet.
         
         If vRtrLdpNgSessParamMinTTLValue is set to zero (0), the 
         TTL Security feature is disabled."
    DEFVAL { 0 }
    ::= { vRtrLdpNgSessionParamsEntry 4 }

vRtrLdpNgSessParamTTLLogId  OBJECT-TYPE
    SYNTAX      TFilterLogId
    MAX-ACCESS  read-create
    STATUS      current
    DESCRIPTION
        "The value of vRtrLdpNgSessParamTTLLogId specifies the filter
         log to use for packets that fail TTL security check.
         The value zero indicates that logging is disabled."
    DEFVAL { 0 }
    ::= { vRtrLdpNgSessionParamsEntry 5 }

vRtrLdpNgSessParamAuthKeyChain  OBJECT-TYPE
    SYNTAX      TNamedItemOrEmpty
    MAX-ACCESS  read-create
    STATUS      current
    DESCRIPTION
        "The value of vRtrLdpNgSessParamAuthKeyChain specifies the 
        keychain which will be used to sign and/or authenticate  the LDP
        protocol stream.

        The keychain name is defined by tmnxKeyChainName and is the index for
        TIMETRA-SECURITY-MIB::tmnxKeyChainTable"
    DEFVAL { ''H }      
    ::= { vRtrLdpNgSessionParamsEntry 6 }

vRtrLdpNgSessParamDODLblDistrib  OBJECT-TYPE
    SYNTAX      TruthValue
    MAX-ACCESS  read-create
    STATUS      current
    DESCRIPTION
        "The value of vRtrLdpNgSessParamDODLblDistrib specifies whether 
          or not Downstream-On-Demand (DOD) has been enabled for the 
          LDP session. When the value is set to 'true' DOD is enabled
          for the LDP session."
    DEFVAL { false }      
    ::= { vRtrLdpNgSessionParamsEntry 7 }

vRtrLdpNgSessParamImportPolicy1 OBJECT-TYPE
    SYNTAX       TPolicyStatementNameOrEmpty
    MAX-ACCESS   read-create
    STATUS       current
    DESCRIPTION
        "The value of vRtrLdpNgSessParamImportPolicy1 specifies the first import
         policy used to determine which FEC prefixes received from other LDP 
         and TLDP peers should be re-distributed to this LDP peer."
    DEFVAL { ''H }
    ::= { vRtrLdpNgSessionParamsEntry 8 }

vRtrLdpNgSessParamImportPolicy2 OBJECT-TYPE
    SYNTAX       TPolicyStatementNameOrEmpty
    MAX-ACCESS   read-create
    STATUS       current
    DESCRIPTION
        "The value of vRtrLdpNgSessParamImportPolicy2 specifies the second import
         policy used to determine which FEC prefixes received from other LDP 
         and TLDP peers should be re-distributed to this LDP peer."
    DEFVAL { ''H }
    ::= { vRtrLdpNgSessionParamsEntry 9 }

vRtrLdpNgSessParamImportPolicy3 OBJECT-TYPE
    SYNTAX       TPolicyStatementNameOrEmpty
    MAX-ACCESS   read-create
    STATUS       current
    DESCRIPTION
        "The value of vRtrLdpNgSessParamImportPolicy3 specifies the third import
         policy used to determine which FEC prefixes received from other LDP 
         and TLDP peers should be re-distributed to this LDP peer."
    DEFVAL { ''H }
    ::= { vRtrLdpNgSessionParamsEntry 10 }

vRtrLdpNgSessParamImportPolicy4 OBJECT-TYPE
    SYNTAX       TPolicyStatementNameOrEmpty
    MAX-ACCESS   read-create
    STATUS       current
    DESCRIPTION
        "The value of vRtrLdpNgSessParamImportPolicy4 specifies the fourth import
         policy used to determine which FEC prefixes received from other LDP 
         and TLDP peers should be re-distributed to this LDP peer."
    DEFVAL { ''H }
    ::= { vRtrLdpNgSessionParamsEntry 11 }

vRtrLdpNgSessParamImportPolicy5 OBJECT-TYPE
    SYNTAX       TPolicyStatementNameOrEmpty
    MAX-ACCESS   read-create
    STATUS       current
    DESCRIPTION
        "The value of vRtrLdpNgSessParamImportPolicy5 specifies the fifth import
         policy used to determine which FEC prefixes received from other LDP 
         and TLDP peers should be re-distributed to this LDP peer."
    DEFVAL { ''H }
    ::= { vRtrLdpNgSessionParamsEntry 12 }

vRtrLdpNgSessParamExportPolicy1 OBJECT-TYPE
    SYNTAX       TPolicyStatementNameOrEmpty
    MAX-ACCESS   read-create
    STATUS       current
    DESCRIPTION
        "The value of vRtrLdpNgSessParamExportPolicy1 specifies the first export
         policy used to determine which FEC prefixes received from this LDP
         peer should be re-distributed to other LDP and TLDP peers."
    DEFVAL { ''H }
    ::= { vRtrLdpNgSessionParamsEntry 13 }

vRtrLdpNgSessParamExportPolicy2 OBJECT-TYPE
    SYNTAX       TPolicyStatementNameOrEmpty
    MAX-ACCESS   read-create
    STATUS       current
    DESCRIPTION
        "The value of vRtrLdpNgSessParamExportPolicy2 specifies the second export
         policy used to determine which FEC prefixes received from this LDP
         peer should be re-distributed to other LDP and TLDP peers."
    DEFVAL { ''H }
    ::= { vRtrLdpNgSessionParamsEntry 14 }

vRtrLdpNgSessParamExportPolicy3 OBJECT-TYPE
    SYNTAX       TPolicyStatementNameOrEmpty
    MAX-ACCESS   read-create
    STATUS       current
    DESCRIPTION
        "The value of vRtrLdpNgSessParamExportPolicy3 specifies the third export
         policy used to determine which FEC prefixes received from this LDP
         peer should be re-distributed to other LDP and TLDP peers."
    DEFVAL { ''H }
    ::= { vRtrLdpNgSessionParamsEntry 15 }

vRtrLdpNgSessParamExportPolicy4 OBJECT-TYPE
    SYNTAX       TPolicyStatementNameOrEmpty
    MAX-ACCESS   read-create
    STATUS       current
    DESCRIPTION
        "The value of vRtrLdpNgSessParamExportPolicy4 specifies the fourth export
         policy used to determine which FEC prefixes received from this LDP
         peer should be re-distributed to other LDP and TLDP peers."
    DEFVAL { ''H }
    ::= { vRtrLdpNgSessionParamsEntry 16 }

vRtrLdpNgSessParamExportPolicy5 OBJECT-TYPE
    SYNTAX       TPolicyStatementNameOrEmpty
    MAX-ACCESS   read-create
    STATUS       current
    DESCRIPTION
        "The value of vRtrLdpNgSessParamExportPolicy5 specifies the fifth export
         policy used to determine which FEC prefixes received from this LDP
         peer should be re-distributed to other LDP and TLDP peers."
    DEFVAL { ''H }
    ::= { vRtrLdpNgSessionParamsEntry 17 }

vRtrLdpNgSessFec129CiscoInterop OBJECT-TYPE
    SYNTAX      TruthValue
    MAX-ACCESS  read-create
    STATUS      current
    DESCRIPTION
        "The value of vRtrLdpNgSessFec129CiscoInterop specifies whether 
         LDP will provide translation between non-compliant FEC 129 formats of 
         Cisco. 

         Peer LDP sessions must be manually configured towards the 
         non-compliant Cisco PEs. 

         When the value of vRtrLdpNgSessFec129CiscoInterop is 'true', Cisco 
         non-compliant format will be used to send and interpret received Label 
         Release messages i.e. the FEC129 SAII and TAII fields will be reversed.

         When the value of vRtrLdpNgSessFec129CiscoInterop is 'false', 
         Cisco non-compliant format will not be used or supported."
    DEFVAL  { false }
    ::= { vRtrLdpNgSessionParamsEntry 18 }

vRtrLdpNgSessParamPMTUDiscovery  OBJECT-TYPE
    SYNTAX      TruthValue
    MAX-ACCESS  read-create
    STATUS      current
    DESCRIPTION
        "The value of vRtrLdpNgSessParamPMTUDiscovery specifies whether path MTU 
         discovery is enabled for this LDP peer.

         When the value is set to 'true', path MTU discovery is enabled for 
         this LDP peer. When the value is set to 'false', path MTU discovery
         is disabled."
    DEFVAL { false }
    ::= { vRtrLdpNgSessionParamsEntry 19 }  

vRtrLdpNgSessParamAdvAdjAddrOnly  OBJECT-TYPE
    SYNTAX      TruthValue
    MAX-ACCESS  read-create
    STATUS      current
    DESCRIPTION
        "The value of vRtrLdpNgSessParamAdvAdjAddrOnly specifies whether to only
         distribute the local addresses used by hello adjacencies with this LDP
         peer.

         When the value is SET to 'true', local addresses that are used by
         hello adjacencies with this LDP peer are only distributed to the peer
         session . When the value is SET to 'false', all known local addresses
         are distributed to the peer session"
    DEFVAL { false }
    ::= { vRtrLdpNgSessionParamsEntry 20 }

vRtrLdpNgSessPeIDMacFlushInterop OBJECT-TYPE
    SYNTAX      TruthValue
    MAX-ACCESS  read-create
    STATUS      current
    DESCRIPTION
        "The value of vRtrLdpNgSessPeIDMacFlushInterop specifies whether 
         LDP will react to and send the non-standard  PE-ID TLV (type 0x405) in
         an address withdraw message to effect 'flush-all-from-me' behavior. It
         is used to provide interoperability with other vendors that use this 
         TLV for the MAC flush mechanism. Only FEC type 128 is currently 
         supported.
    
         Peer LDP sessions must be manually configured towards the PEs requiring
         support for this TLV.
    
         When the value of vRtrLdpNgSessPeIDMacFlushInterop is set to 'true', 
         the receipt of an address withdraw message with empty MAC list including
         the non-standard TLV will trigger 'flush-all-from-me' behavior instead
         of the normal 'flush-all-but-mine'. The TLV will be included in any
         forwarding towards like-configured peers.
    
         When the value of vRtrLdpNgSessPeIDMacFlushInterop is set to 
         'false', the non-standard TLV will be ignored and will not be included
         in any address withdraw messages sent to the peer."
    DEFVAL  { false }
    ::= { vRtrLdpNgSessionParamsEntry 21 }

vRtrLdpNgSessParamIPv4PfxFecCap OBJECT-TYPE
     SYNTAX      TmnxEnabledDisabled
     MAX-ACCESS  read-create
     STATUS      current
     DESCRIPTION
         "The value of vRtrLdpNgSessParamIPv4PfxFecCap specifies whether IPv4
          prefix FECs can be exchanged over this session"
     DEFVAL { enabled }
    ::= { vRtrLdpNgSessionParamsEntry 22 }

vRtrLdpNgSessParamIPv6PfxFecCap  OBJECT-TYPE
     SYNTAX      TmnxEnabledDisabled 
     MAX-ACCESS  read-create
     STATUS      current
     DESCRIPTION
         "The value of vRtrLdpNgSessParamIPv6PfxFecCap specifies whether IPv6
          prefix FECs can be exchanged over this session"
     DEFVAL { enabled }
    ::= { vRtrLdpNgSessionParamsEntry 23 }

vRtrLdpNgSessParamP2MPFecCap  OBJECT-TYPE
     SYNTAX      TmnxEnabledDisabled
     MAX-ACCESS  read-create
     STATUS      current
     DESCRIPTION
         "The value of vRtrLdpNgSessParamP2MPFecCap specifies whether P2MP FECs
          can be exchanged over this session"
     DEFVAL { enabled }
    ::= { vRtrLdpNgSessionParamsEntry 24 }

vRtrLdpNgSessParamMaxFec   OBJECT-TYPE
    SYNTAX      Unsigned32 (0 | 1..4294967295)
    MAX-ACCESS  read-create
    STATUS      current
    DESCRIPTION
        " The value of vRtrLdpNgSessParamMaxFec specifies the maximum number of 
          FECs that will be accepted from this peer LSR.

          A value of zero specifies there is no limit to the number of FECs
          accepted from this peer LSR.

          The vRtrLdpNgSessMaxFecThresReached notification is sent when the number
          of FECs receive from this peer LSR exceeds a percentage of this limit
          as specified by vRtrLdpPeerMaxFecThreshold.

          Furthermore, once the limit is exhausted, following actions are taken
          if vRtrLdpNgSessParamMaxFecLogOnly has value of 'false'.

          (1) If LSR Overload capability is supported, this LSR will follow the
              LSR Overload procedure.

          (2) If LSR Overload capability is not supported, any further Label
              Mapping Message is returned with Label Release Message with LDP 
              status code 'No_Label_Resources'. "
    DEFVAL  { 0 }
    ::= { vRtrLdpNgSessionParamsEntry 25 }

vRtrLdpNgSessParamMaxFecLogOnly  OBJECT-TYPE
    SYNTAX      TruthValue
    MAX-ACCESS  read-create
    STATUS      current
    DESCRIPTION
        " The value of vRtrLdpNgSessParamMaxFecLogOnly specifies whether to only
          generate vRtrLdpNgSessMaxFecThresReached notification or take further
          action when FECs received exceeds vRtrLdpNgSessParamMaxFec limit.
        
          When this value is set to 'false', trap will be generated and one of
          the following action is taken:
        
          (1) If LSR Overload capability is supported, this LSR will follow the
              LSR Overload procedure.
        
          (2) If LSR Overload capability is not supported, any further Label
              Mapping Message is returned with Label Release Message with LDP
              status code 'No_Label_Resources'.
        
          When this value is set to 'true', trap will be generated only. "
    DEFVAL  { false }
    ::= { vRtrLdpNgSessionParamsEntry 26 }

vRtrLdpNgSessParamMaxFecThold    OBJECT-TYPE
    SYNTAX      Unsigned32  (1..100)
    UNITS       "percentage"
    MAX-ACCESS  read-create
    STATUS      current
    DESCRIPTION
        " The value of vRtrLdpNgSessParamMaxFecThold specifies a percentage of
          vRtrLdpNgSessParamMaxFec. "
    DEFVAL { 90 }
    ::= { vRtrLdpNgSessionParamsEntry 27 }

--
--  Alcatel-Lucent SROS series LDP Session Address Table
--

vRtrLdpNgSessionAddrTable    OBJECT-TYPE
    SYNTAX      SEQUENCE OF VRtrLdpNgSessionAddrEntry
    MAX-ACCESS  not-accessible
    STATUS      current
    DESCRIPTION
        "The vRtrLdpNgSessionInAddrTable is a read-only table that represents all
         local addresses either sent to or received from an LDP peer for a
         single session between an LDP entity and an LDP Peer."
    ::= { tmnxLdpNgObjs 9 }

vRtrLdpNgSessionAddrEntry    OBJECT-TYPE
    SYNTAX      VRtrLdpNgSessionAddrEntry
    MAX-ACCESS  not-accessible
    STATUS      current
    DESCRIPTION
        "Each row entry represents an instance of all local addresses sent to
         or received from an LDP peer."
    INDEX  { vRtrID,
             vRtrLdpNgPeerLdpIdType,
             vRtrLdpNgPeerLdpId }
    ::= { vRtrLdpNgSessionAddrTable 1 }

VRtrLdpNgSessionAddrEntry ::= SEQUENCE {
    vRtrLdpNgSessAddrLclLdpIdType       TmnxMplsLdpNgIdType,
    vRtrLdpNgSessionAddrLocalLdpId      TmnxMplsLdpNgIdentifier,
    vRtrLdpNgSessionAddrNumInAddrs      Unsigned32,
    vRtrLdpNgSessionAddrNumOutAddrs     Unsigned32
}

vRtrLdpNgSessAddrLclLdpIdType    OBJECT-TYPE
    SYNTAX      TmnxMplsLdpNgIdType
    MAX-ACCESS  read-only
    STATUS      current
    DESCRIPTION
        "The value of vRtrLdpNgSessAddrLclLdpIdType indicates the local LDP 
         identifier type for the LDP session indicated by 
         vRtrLdpNgSessionAddrLocalLdpId."
    ::= { vRtrLdpNgSessionAddrEntry 1 }
    
vRtrLdpNgSessionAddrLocalLdpId    OBJECT-TYPE
    SYNTAX      TmnxMplsLdpNgIdentifier (SIZE (6|18))
    MAX-ACCESS  read-only
    STATUS      current
    DESCRIPTION
        "The value of vRtrLdpNgSessionAddrLocalLdpId indicates the local LDP 
         identifier for this LDP session."
    ::= { vRtrLdpNgSessionAddrEntry 2 }

vRtrLdpNgSessionAddrNumInAddrs    OBJECT-TYPE
    SYNTAX      Unsigned32
    MAX-ACCESS  read-only
    STATUS      current
    DESCRIPTION
        "The value of vRtrLdpNgSessionAddrNumInAddrs indicates the number
         of local addresses that have been received from the peer for
         this session."
    ::= { vRtrLdpNgSessionAddrEntry 3 }

vRtrLdpNgSessionAddrNumOutAddrs    OBJECT-TYPE
    SYNTAX      Unsigned32
    MAX-ACCESS  read-only
    STATUS      current
    DESCRIPTION
        "The value of vRtrLdpNgSessionAddrNumOutAddrs indicates the number of
         local addresses that have been sent to the peer for this session."
    ::= { vRtrLdpNgSessionAddrEntry 4 }

--
--  Alcatel-Lucent SROS series LDP Session In Address Table
--

vRtrLdpNgSessionInAddrTable    OBJECT-TYPE
    SYNTAX      SEQUENCE OF VRtrLdpNgSessionInAddrEntry
    MAX-ACCESS  not-accessible
    STATUS      current
    DESCRIPTION
        "The vRtrLdpNgSessionInAddrTable is a read-only table that represents all
         local addresses received from an LDP peer for a single session between
         an LDP entity and an LDP Peer."
    ::= { tmnxLdpNgObjs 10 }

vRtrLdpNgSessionInAddrEntry    OBJECT-TYPE
    SYNTAX      VRtrLdpNgSessionInAddrEntry
    MAX-ACCESS  not-accessible
    STATUS      current
    DESCRIPTION
        "Each row entry represents an instance of a local address received from an
         LDP peer."
    INDEX  { vRtrID,
             vRtrLdpNgPeerLdpIdType,
             vRtrLdpNgPeerLdpId,
             vRtrLdpNgSessionInAddrAddrType,
             vRtrLdpNgSessionInAddrAddress }
    ::= { vRtrLdpNgSessionInAddrTable 1 }

VRtrLdpNgSessionInAddrEntry ::= SEQUENCE {
    vRtrLdpNgSessionInAddrAddrType       InetAddressType,
    vRtrLdpNgSessionInAddrAddress        InetAddress,
    vRtrLdpNgSessInAddrLclLdpIdType      TmnxMplsLdpNgIdType,
    vRtrLdpNgSessionInAddrLocalLdpId     TmnxMplsLdpNgIdentifier
}

vRtrLdpNgSessionInAddrAddrType    OBJECT-TYPE
    SYNTAX      InetAddressType
    MAX-ACCESS  not-accessible
    STATUS      current
    DESCRIPTION
        "The value of vRtrLdpNgSessionInAddrAddrType indicates the address
         type of vRtrLdpNgSessionInAddrAddress."
    ::= { vRtrLdpNgSessionInAddrEntry 1 }

vRtrLdpNgSessionInAddrAddress    OBJECT-TYPE
    SYNTAX      InetAddress (SIZE(4|16))
    MAX-ACCESS  not-accessible
    STATUS      current
    DESCRIPTION
        "The value of vRtrLdpNgSessionInAddrAddress indicates the IP address
         received from the peer for this LDP session."
    ::= { vRtrLdpNgSessionInAddrEntry 2 }

vRtrLdpNgSessInAddrLclLdpIdType    OBJECT-TYPE
    SYNTAX      TmnxMplsLdpNgIdType
    MAX-ACCESS  read-only
    STATUS      current
    DESCRIPTION
        "The value of vRtrLdpNgSessionInAddrLocalLdpId indicates the local LDP 
         identifier type for the LDP session indicated by 
         vRtrLdpNgSessionInAddrLocalLdpId."
    ::= { vRtrLdpNgSessionInAddrEntry 3 }
    
vRtrLdpNgSessionInAddrLocalLdpId    OBJECT-TYPE
    SYNTAX      TmnxMplsLdpNgIdentifier (SIZE (6|18))
    MAX-ACCESS  read-only
    STATUS      current
    DESCRIPTION
        "The value of vRtrLdpNgSessionInAddrLocalLdpId indicates the local LDP 
         identifier for this LDP session."
    ::= { vRtrLdpNgSessionInAddrEntry 4 }

--
--  Alcatel-Lucent SROS series LDP Session Out Address Table
--

vRtrLdpNgSessionOutAddrTable    OBJECT-TYPE
    SYNTAX      SEQUENCE OF VRtrLdpNgSessionOutAddrEntry
    MAX-ACCESS  not-accessible
    STATUS      current
    DESCRIPTION
        "The vRtrLdpNgSessionOutAddrTable is a read-only table that represents all
         local addresses sent to an LDP peer for a single session between
         an LDP entity and an LDP Peer."
    ::= { tmnxLdpNgObjs 11 }

vRtrLdpNgSessionOutAddrEntry    OBJECT-TYPE
    SYNTAX      VRtrLdpNgSessionOutAddrEntry
    MAX-ACCESS  not-accessible
    STATUS      current
    DESCRIPTION
        "Each row entry represents an instance of a local address sent to an
         LDP peer."
    INDEX  { vRtrID,
             vRtrLdpNgPeerLdpIdType,
             vRtrLdpNgPeerLdpId,
             vRtrLdpNgSessionOutAddrAddrType,
             vRtrLdpNgSessionOutAddrAddress }
    ::= { vRtrLdpNgSessionOutAddrTable 1 }

VRtrLdpNgSessionOutAddrEntry ::= SEQUENCE {
    vRtrLdpNgSessionOutAddrAddrType       InetAddressType,
    vRtrLdpNgSessionOutAddrAddress        InetAddress,
    vRtrLdpNgSessOutAddrLclLdpIdType      TmnxMplsLdpNgIdType,
    vRtrLdpNgSessionOutAddrLclLdpId       TmnxMplsLdpNgIdentifier
}

vRtrLdpNgSessionOutAddrAddrType    OBJECT-TYPE
    SYNTAX      InetAddressType
    MAX-ACCESS  not-accessible
    STATUS      current
    DESCRIPTION
        "The value of vRtrLdpNgSessionOutAddrAddrType indicates the address
         type of vRtrLdpNgSessionOutAddrAddress."
    ::= { vRtrLdpNgSessionOutAddrEntry 1 }

vRtrLdpNgSessionOutAddrAddress    OBJECT-TYPE
    SYNTAX      InetAddress (SIZE(4|16))
    MAX-ACCESS  not-accessible
    STATUS      current
    DESCRIPTION
        "The value of vRtrLdpNgSessionOutAddrAddress indicates the IP address
         sent to the peer for this LDP session."
    ::= { vRtrLdpNgSessionOutAddrEntry 2 }

vRtrLdpNgSessOutAddrLclLdpIdType    OBJECT-TYPE
    SYNTAX      TmnxMplsLdpNgIdType
    MAX-ACCESS  read-only
    STATUS      current
    DESCRIPTION
        "The value of vRtrLdpNgSessionOutAddrLclLdpId indicates the local LDP 
         identifier type for the LDP session, indicated by 
         vRtrLdpNgSessionOutAddrLclLdpId."
    ::= { vRtrLdpNgSessionOutAddrEntry 3 }

vRtrLdpNgSessionOutAddrLclLdpId    OBJECT-TYPE
    SYNTAX      TmnxMplsLdpNgIdentifier (SIZE (6|18))
    MAX-ACCESS  read-only
    STATUS      current
    DESCRIPTION
        "The value of vRtrLdpNgSessionOutAddrLclLdpId indicates the local LDP 
         identifier for this LDP session."
    ::= { vRtrLdpNgSessionOutAddrEntry 4 }

--
--  Alcatel-Lucent SROS series LDP Address FEC Table
--

vRtrLdpNgAddrFecTable    OBJECT-TYPE
    SYNTAX      SEQUENCE OF VRtrLdpNgAddrFecEntry
    MAX-ACCESS  not-accessible
    STATUS      current
    DESCRIPTION
        "The vRtrLdpNgAddrFecTable is a read-only table that represents all
         address FECs either sent to or received from an LDP peer known
         to the Virtual Router."
    ::= { tmnxLdpNgObjs 12 }

vRtrLdpNgAddrFecEntry    OBJECT-TYPE
    SYNTAX      VRtrLdpNgAddrFecEntry
    MAX-ACCESS  not-accessible
    STATUS      current
    DESCRIPTION
        "Each row entry represents an instance of an address FEC sent
         to or received from an LDP peer."
    INDEX  { vRtrID,
             vRtrLdpNgAddrFecFecType,
             vRtrLdpNgAddrFecIpPrefixType,
             vRtrLdpNgAddrFecIpPrefix,
             vRtrLdpNgAddrFecIpPrefixLen,
             vRtrLdpNgPeerLdpIdType,
             vRtrLdpNgPeerLdpId }
    ::= { vRtrLdpNgAddrFecTable 1 }

VRtrLdpNgAddrFecEntry ::= SEQUENCE {
    vRtrLdpNgAddrFecFecType               TmnxLdpFECType,
    vRtrLdpNgAddrFecIpPrefixType          InetAddressType,
    vRtrLdpNgAddrFecIpPrefix              InetAddress,
    vRtrLdpNgAddrFecIpPrefixLen           InetAddressPrefixLength,
    vRtrLdpNgAddrFecFlags                 TmnxLdpFECFlags,
    vRtrLdpNgAddrFecNumInLabels           Unsigned32,
    vRtrLdpNgAddrFecNumOutLabels          Unsigned32
}
vRtrLdpNgAddrFecFecType    OBJECT-TYPE
    SYNTAX      TmnxLdpFECType
    MAX-ACCESS  not-accessible
    STATUS      current
    DESCRIPTION
        "The value of vRtrLdpNgAddrFecFecType specifies the FEC type."
    ::= { vRtrLdpNgAddrFecEntry 1 }

vRtrLdpNgAddrFecIpPrefixType    OBJECT-TYPE
    SYNTAX      InetAddressType
    MAX-ACCESS  not-accessible
    STATUS      current
    DESCRIPTION
        "The value of vRtrLdpNgAddrFecIpPrefixType indicates the address-type
         of vRtrLdpNgAddrFecIpPrefix."
    ::= { vRtrLdpNgAddrFecEntry 2 }

vRtrLdpNgAddrFecIpPrefix    OBJECT-TYPE
    SYNTAX      InetAddress (SIZE (4|16))
    MAX-ACCESS  not-accessible
    STATUS      current
    DESCRIPTION
        "The value of vRtrLdpNgAddrFecIpPrefix specifies the IP Address
         Prefix for this address FEC."
    ::= { vRtrLdpNgAddrFecEntry 3 }

vRtrLdpNgAddrFecIpPrefixLen    OBJECT-TYPE
    SYNTAX      InetAddressPrefixLength (0..128)
    MAX-ACCESS  not-accessible
    STATUS      current
    DESCRIPTION
        "The value of vRtrLdpNgAddrFecIpPrefixLen indicates the prefix length
         of the subnet associated with vRtrLdpNgAddrFecIpPrefix."
    ::= { vRtrLdpNgAddrFecEntry 4 }

vRtrLdpNgAddrFecFlags    OBJECT-TYPE
    SYNTAX      TmnxLdpFECFlags
    MAX-ACCESS  read-only
    STATUS      current
    DESCRIPTION
        "The bit flags of vRtrLdpNgAddrFecFlags indicate the characteristics
         of the FEC."
    ::= { vRtrLdpNgAddrFecEntry 5 }

vRtrLdpNgAddrFecNumInLabels    OBJECT-TYPE
    SYNTAX      Unsigned32
    MAX-ACCESS  read-only
    STATUS      current
    DESCRIPTION
        "The value of vRtrLdpNgAddrFecNumInLabels indicates the number of
         labels that have been sent to the peer associated with this
         FEC."
    ::= { vRtrLdpNgAddrFecEntry 6 }

vRtrLdpNgAddrFecNumOutLabels    OBJECT-TYPE
    SYNTAX      Unsigned32
    MAX-ACCESS  read-only
    STATUS      current
    DESCRIPTION
        "The value of vRtrLdpNgAddrFecNumOutLabels indicates the number of
         labels that have been received from the peer associated with this
         FEC."
    ::= { vRtrLdpNgAddrFecEntry 7 }

--
--  Alcatel-Lucent SROS series LDP Address FEC In Label Table
--

vRtrLdpNgAddrFecInLblTable    OBJECT-TYPE
    SYNTAX      SEQUENCE OF VRtrLdpAddrFecInLblEntry
    MAX-ACCESS  not-accessible
    STATUS      current
    DESCRIPTION
        "The vRtrLdpNgAddrFecInLblTable is a read-only table that represents all
         address FECs received from an LDP peer known to the Virtual Router."
    ::= { tmnxLdpNgObjs 13 }

vRtrLdpNgAddrFecInLblEntry    OBJECT-TYPE
    SYNTAX      VRtrLdpAddrFecInLblEntry
    MAX-ACCESS  not-accessible
    STATUS      current
    DESCRIPTION
        "Each row entry represents an instance of an address FEC received from
         an LDP peer."
    INDEX  { vRtrID,
             vRtrLdpNgAddrFecFecType,
             vRtrLdpNgAddrFecIpPrefixType,
             vRtrLdpNgAddrFecIpPrefix,
             vRtrLdpNgAddrFecIpPrefixLen,
             vRtrLdpNgPeerLdpIdType,
             vRtrLdpNgPeerLdpId,
             vRtrLdpNgAddrFecInLblId }
    ::= { vRtrLdpNgAddrFecInLblTable 1 }

VRtrLdpAddrFecInLblEntry ::= SEQUENCE {
    vRtrLdpNgAddrFecInLblId        Unsigned32,
    vRtrLdpNgAddrFecInLbl          Unsigned32,
    vRtrLdpNgAddrFecInLblStatus    TmnxLabelStatus,
    vRtrLdpNgAddrFecInLblIfIndex   InterfaceIndexOrZero
}

vRtrLdpNgAddrFecInLblId        OBJECT-TYPE
    SYNTAX      Unsigned32
    MAX-ACCESS  not-accessible
    STATUS      current
    DESCRIPTION
        "The value of vRtrLdpNgAddrFecInLblId indicates the label number of
         the ingress label exchanged."
    ::= { vRtrLdpNgAddrFecInLblEntry 1 }

vRtrLdpNgAddrFecInLbl    OBJECT-TYPE
    SYNTAX      Unsigned32
    MAX-ACCESS  read-only
    STATUS      current
    DESCRIPTION
        "The value of vRtrLdpNgAddrFecInLbl indicates the ingress label
         exchanged."
    ::= { vRtrLdpNgAddrFecInLblEntry 2 }

vRtrLdpNgAddrFecInLblStatus    OBJECT-TYPE
    SYNTAX      TmnxLabelStatus
    MAX-ACCESS  read-only
    STATUS      current
    DESCRIPTION
        "The value of vRtrLdpNgAddrFecInLblStatus indicates the status of the
         ingress label."
    ::= { vRtrLdpNgAddrFecInLblEntry 3 }

vRtrLdpNgAddrFecInLblIfIndex    OBJECT-TYPE
    SYNTAX      InterfaceIndexOrZero
    MAX-ACCESS  read-only
    STATUS      current
    DESCRIPTION
        "The value of vRtrLdpNgAddrFecInLblIfIndex indicates the interface
         index for ingress label."
    ::= { vRtrLdpNgAddrFecInLblEntry 4 }

--
--  Alcatel-Lucent SROS series LDP Address FEC Out Label Table
--

vRtrLdpNgAddrFecOutLblTable    OBJECT-TYPE
    SYNTAX      SEQUENCE OF VRtrLdpNgAddrFecOutLblEntry
    MAX-ACCESS  not-accessible
    STATUS      current
    DESCRIPTION
        "The vRtrLdpNgAddrFecOutLblTable is a read-only table that represents all
         address FECs sent to an LDP peer known to the Virtual Router."
    ::= { tmnxLdpNgObjs 14 }

vRtrLdpNgAddrFecOutLblEntry    OBJECT-TYPE
    SYNTAX      VRtrLdpNgAddrFecOutLblEntry
    MAX-ACCESS  not-accessible
    STATUS      current
    DESCRIPTION
        "Each row entry represents an instance of an address FEC received from
         an LDP peer."
    INDEX  { vRtrID,
             vRtrLdpNgAddrFecFecType,
             vRtrLdpNgAddrFecIpPrefixType,
             vRtrLdpNgAddrFecIpPrefix,
             vRtrLdpNgAddrFecIpPrefixLen,
             vRtrLdpNgPeerLdpIdType,
             vRtrLdpNgPeerLdpId,
             vRtrLdpNgAddrFecOutLblId }
    ::= { vRtrLdpNgAddrFecOutLblTable 1 }

VRtrLdpNgAddrFecOutLblEntry ::= SEQUENCE {
    vRtrLdpNgAddrFecOutLblId           Unsigned32,
    vRtrLdpNgAddrFecOutLbl             Unsigned32,
    vRtrLdpNgAddrFecOutLblStatus       TmnxLabelStatus,
    vRtrLdpNgAddrFecOutLblIfIndex      InterfaceIndexOrZero,
    vRtrLdpNgAddrFecOutLblNHType       InetAddressType,
    vRtrLdpNgAddrFecOutLblNHAddr       InetAddress,
    vRtrLdpNgAddrFecOutLblMetric       Unsigned32,
    vRtrLdpNgAddrFecOutLblMtu          Unsigned32,
    vRtrLdpNgAddrFecOutLblLspId        TmnxVRtrMplsLspID
}

vRtrLdpNgAddrFecOutLblId        OBJECT-TYPE
    SYNTAX      Unsigned32
    MAX-ACCESS  not-accessible
    STATUS      current
    DESCRIPTION
        "The value of vRtrLdpNgAddrFecOutLblId indicates the label number of
         the egress label exchanged."
    ::= { vRtrLdpNgAddrFecOutLblEntry 1 }

vRtrLdpNgAddrFecOutLbl    OBJECT-TYPE
    SYNTAX      Unsigned32
    MAX-ACCESS  read-only
    STATUS      current
    DESCRIPTION
        "The value of vRtrLdpNgAddrFecOutLbl indicates the egress label
         exchanged"
    ::= { vRtrLdpNgAddrFecOutLblEntry 2 }

vRtrLdpNgAddrFecOutLblStatus    OBJECT-TYPE
    SYNTAX      TmnxLabelStatus
    MAX-ACCESS  read-only
    STATUS      current
    DESCRIPTION
        "The value of vRtrLdpNgAddrFecOutLblStatus indicates the status of the
         egress label."
    ::= { vRtrLdpNgAddrFecOutLblEntry 3 }

vRtrLdpNgAddrFecOutLblIfIndex    OBJECT-TYPE
    SYNTAX      InterfaceIndexOrZero
    MAX-ACCESS  read-only
    STATUS      current
    DESCRIPTION
        "The value of vRtrLdpNgAddrFecOutLblIfIndex indicates the interface
         index for egress label."
    ::= { vRtrLdpNgAddrFecOutLblEntry 4 }

vRtrLdpNgAddrFecOutLblNHType    OBJECT-TYPE
    SYNTAX      InetAddressType
    MAX-ACCESS  read-only
    STATUS      current
    DESCRIPTION
        "The value of vRtrLdpNgAddrFecOutLblNHType indicates the address
         type of vRtrLdpNgAddrFecOutLblNHAddr."
    ::= { vRtrLdpNgAddrFecOutLblEntry 5 }

vRtrLdpNgAddrFecOutLblNHAddr    OBJECT-TYPE
    SYNTAX      InetAddress (SIZE(4|16))
    MAX-ACCESS  read-only
    STATUS      current
    DESCRIPTION
        "The value of vRtrLdpNgAddrFecOutLblNHAddr indicates the IP address
         of the next hop for egress label."
    ::= { vRtrLdpNgAddrFecOutLblEntry 6 }

vRtrLdpNgAddrFecOutLblMetric    OBJECT-TYPE
    SYNTAX      Unsigned32
    MAX-ACCESS  read-only
    STATUS      current
    DESCRIPTION
        "The value of vRtrLdpNgAddrFecOutLblMetric indicates the relative cost
         of the tunnel represented by this address FEC egress label."
    ::= { vRtrLdpNgAddrFecOutLblEntry 7 }

vRtrLdpNgAddrFecOutLblMtu    OBJECT-TYPE
    SYNTAX      Unsigned32
    MAX-ACCESS  read-only
    STATUS      current
    DESCRIPTION
        "The value of vRtrLdpNgAddrFecOutLblMtu indicates the maximum transfer
         unit for payloads represented by this address FEC egress label."
    ::= { vRtrLdpNgAddrFecOutLblEntry 8 }

vRtrLdpNgAddrFecOutLblLspId    OBJECT-TYPE
    SYNTAX      TmnxVRtrMplsLspID
    MAX-ACCESS  read-only
    STATUS      current
    DESCRIPTION
        "The value of vRtrLdpNgAddrFecOutLblLspId indicates the LSP id of the
         LSP for the RSVP tunnel used by LDP in LDP over RSVP associated with
         egress label."
    ::= { vRtrLdpNgAddrFecOutLblEntry 9 }

--
--  Alcatel-Lucent SROS series LDP Address FEC Mapping Table
--

vRtrLdpNgAddrFecMapTable    OBJECT-TYPE
    SYNTAX      SEQUENCE OF VRtrLdpNgAddrFecMapEntry
    MAX-ACCESS  not-accessible
    STATUS      current
    DESCRIPTION
        "The vRtrLdpNgAddrFecMapTable is a read-only table which maps to the
         vRtrLdpNgAddrFecTable. This table has the same indexes as the
         vRtrLdpNgAddrFecTable but the order in which these indexes are
         specified is different for the two tables."
    ::= { tmnxLdpNgObjs 15 }

vRtrLdpNgAddrFecMapEntry    OBJECT-TYPE
    SYNTAX      VRtrLdpNgAddrFecMapEntry
    MAX-ACCESS  not-accessible
    STATUS      current
    DESCRIPTION
        "Each row entry represents an instance of an address FEC sent
         to or received from an LDP peer."
    INDEX  { vRtrID,
             vRtrLdpNgPeerLdpIdType,
             vRtrLdpNgPeerLdpId,
             vRtrLdpNgAddrFecFecType,
             vRtrLdpNgAddrFecIpPrefixType,
             vRtrLdpNgAddrFecIpPrefix,
             vRtrLdpNgAddrFecIpPrefixLen }
    ::= { vRtrLdpNgAddrFecMapTable 1 }

VRtrLdpNgAddrFecMapEntry ::= SEQUENCE {
    vRtrLdpNgAddrFecMapFlags                 TmnxLdpFECFlags,
    vRtrLdpNgAddrFecMapNumInLabels           Unsigned32,
    vRtrLdpNgAddrFecMapNumOutLabels          Unsigned32
}

vRtrLdpNgAddrFecMapFlags    OBJECT-TYPE
    SYNTAX      TmnxLdpFECFlags
    MAX-ACCESS  read-only
    STATUS      current
    DESCRIPTION
        "The bit flags of vRtrLdpNgAddrFecMapFlags indicate the characteristics
         of the FEC."
    ::= { vRtrLdpNgAddrFecMapEntry 1 }

vRtrLdpNgAddrFecMapNumInLabels    OBJECT-TYPE
    SYNTAX      Unsigned32
    MAX-ACCESS  read-only
    STATUS      current
    DESCRIPTION
        "The value of vRtrLdpNgAddrFecMapNumInLabels indicates the number of
         labels that have been sent to the peer associated with this
         FEC."
    ::= { vRtrLdpNgAddrFecMapEntry 2 }

vRtrLdpNgAddrFecMapNumOutLabels    OBJECT-TYPE
    SYNTAX      Unsigned32
    MAX-ACCESS  read-only
    STATUS      current
    DESCRIPTION
        "The value of vRtrLdpNgAddrFecMapNumOutLabels indicates the number of
         labels that have been received from the peer associated with this
         FEC."
    ::= { vRtrLdpNgAddrFecMapEntry 3 }

--
--  Alcatel-Lucent SROS series LDP Point to Multipoint Forward Equivalence Class
--  (P2MP FEC) Table
--

vRtrLdpNgExtP2MPFecTable    OBJECT-TYPE
    SYNTAX      SEQUENCE OF VRtrLdpNgExtP2MPFecEntry
    MAX-ACCESS  not-accessible
    STATUS      current
    DESCRIPTION
        "The vRtrLdpNgExtP2MPFecTable is a read-only table that represents operational
         information of P2MP FECs either sent to or received from an LDP peer
         known to the Virtual Router."
    ::= { tmnxLdpNgObjs 16 }

vRtrLdpNgExtP2MPFecEntry    OBJECT-TYPE
    SYNTAX      VRtrLdpNgExtP2MPFecEntry
    MAX-ACCESS  not-accessible
    STATUS      current
    DESCRIPTION
        "Each row entry represents an instance of operational information
         of a P2MP FEC sent to or received from an LDP peer."
    INDEX  { vRtrID,
             vRtrLdpNgExtP2MPFecRootAddrType,
             vRtrLdpNgExtP2MPFecRootAddress,
             vRtrLdpNgExtP2MPFecOpaqueType,
             vRtrLdpNgExtP2MPFecOpaqueLength,
             vRtrLdpNgExtP2MPFecOpaqueValue,
             vRtrLdpNgPeerLdpIdType,
             vRtrLdpNgPeerLdpId }
    ::= { vRtrLdpNgExtP2MPFecTable 1 }

VRtrLdpNgExtP2MPFecEntry ::= SEQUENCE {
    vRtrLdpNgExtP2MPFecOpaqueType             Unsigned32,
    vRtrLdpNgExtP2MPFecOpaqueLength           Unsigned32,
    vRtrLdpNgExtP2MPFecOpaqueValue            OCTET STRING,
    vRtrLdpNgExtP2MPFecRootAddrType           InetAddressType,
    vRtrLdpNgExtP2MPFecRootAddress            InetAddress,
    vRtrLdpNgExtP2MPFecFlags                  TmnxLdpFECFlags,
    vRtrLdpNgExtP2MPFecNumInLabels            Gauge32,
    vRtrLdpNgExtP2MPFecNumOutLabels           Gauge32,
    vRtrLdpNgExtP2MPFecTunnelIfId             Unsigned32,
    vRtrLdpNgExtP2MPFecMetric                 Unsigned32,
    vRtrLdpNgExtP2MPFecMTU                    Unsigned32
    }

vRtrLdpNgExtP2MPFecOpaqueType    OBJECT-TYPE
    SYNTAX      Unsigned32 (0..255)
    MAX-ACCESS  not-accessible
    STATUS      current
    DESCRIPTION
        "The value of vRtrLdpNgExtP2MPFecOpaqueType indicates the type of a
         Multi-Point Opaque Value Element."
    ::= { vRtrLdpNgExtP2MPFecEntry 1 }

vRtrLdpNgExtP2MPFecOpaqueLength    OBJECT-TYPE
    SYNTAX      Unsigned32 (0..65535)
    MAX-ACCESS  not-accessible
    STATUS      current
    DESCRIPTION
        "The value of vRtrLdpNgExtP2MPFecOpaqueLength indicates the length of a
        Multi-Point Opaque Value Element."
    ::= { vRtrLdpNgExtP2MPFecEntry 2 }

vRtrLdpNgExtP2MPFecOpaqueValue    OBJECT-TYPE
    SYNTAX      OCTET STRING (SIZE(0..32))
    MAX-ACCESS  not-accessible
    STATUS      current
    DESCRIPTION
        "The value of vRtrLdpNgExtP2MPFecOpaqueValue indicates the value of a
        Multi-Point Opaque Value Element."
    ::= { vRtrLdpNgExtP2MPFecEntry 3 }

vRtrLdpNgExtP2MPFecRootAddrType    OBJECT-TYPE
    SYNTAX      InetAddressType
    MAX-ACCESS  not-accessible
    STATUS      current
    DESCRIPTION
        "The value of vRtrLdpNgExtP2MPFecRootAddrType indicates the type of
         ip address of the root for this P2MP FEC."
    ::= { vRtrLdpNgExtP2MPFecEntry 4 }

vRtrLdpNgExtP2MPFecRootAddress    OBJECT-TYPE
    SYNTAX      InetAddress (SIZE (4|16))
    MAX-ACCESS  not-accessible
    STATUS      current
    DESCRIPTION
        "The value of vRtrLdpNgExtP2MPFecRootAddress indicates the ip address
         of the root for this P2MP FEC."
    ::= { vRtrLdpNgExtP2MPFecEntry 5 }

vRtrLdpNgExtP2MPFecFlags    OBJECT-TYPE
    SYNTAX      TmnxLdpFECFlags
    MAX-ACCESS  read-only
    STATUS      current
    DESCRIPTION
        "The bit flags of vRtrLdpNgExtP2MPFecFlags indicates the characteristics
         of the FEC."
    ::= { vRtrLdpNgExtP2MPFecEntry 6 }

vRtrLdpNgExtP2MPFecNumInLabels    OBJECT-TYPE
    SYNTAX      Gauge32
    MAX-ACCESS  read-only
    STATUS      current
    DESCRIPTION
        "The value of vRtrLdpNgExtP2MPFecNumInLabels indicates the number of
         labels that have been sent to the peer associated with this
         FEC."
    ::= { vRtrLdpNgExtP2MPFecEntry 7 }

vRtrLdpNgExtP2MPFecNumOutLabels    OBJECT-TYPE
    SYNTAX      Gauge32
    MAX-ACCESS  read-only
    STATUS      current
    DESCRIPTION
        "The value of vRtrLdpNgExtP2MPFecNumOutLabels indicates the number of
         labels that have been received from the peer associated with this
         FEC."
    ::= { vRtrLdpNgExtP2MPFecEntry 8 }

vRtrLdpNgExtP2MPFecTunnelIfId    OBJECT-TYPE
    SYNTAX      Unsigned32
    MAX-ACCESS  read-only
    STATUS      current
    DESCRIPTION
        "The value of vRtrLdpNgExtP2MPFecTunnelIfId indicates the tunnel interface
         identifier for this P2MP FEC."
    ::= { vRtrLdpNgExtP2MPFecEntry 9 }

vRtrLdpNgExtP2MPFecMetric    OBJECT-TYPE
    SYNTAX      Unsigned32
    MAX-ACCESS  read-only
    STATUS      current
    DESCRIPTION
        "The value of vRtrLdpNgExtP2MPFecMetric indicates the relative cost
         of the tunnel represented by this P2MP FEC"
    ::= { vRtrLdpNgExtP2MPFecEntry 10 }

vRtrLdpNgExtP2MPFecMTU    OBJECT-TYPE
    SYNTAX      Unsigned32
    MAX-ACCESS  read-only
    STATUS      current
    DESCRIPTION
    "The value of vRtrLdpNgExtP2MPFecMTU indicates the maximum transfer
     unit for payloads represented by this P2MP FEC"
    ::= { vRtrLdpNgExtP2MPFecEntry 11 }

--
--  Alcatel-Lucent SROS series LDP P2MP FEC In Label Table
--

vRtrLdpNgExtP2MPFecInLblTable    OBJECT-TYPE
    SYNTAX      SEQUENCE OF VRtrLdpNgExtP2MPFecInLblEntry
    MAX-ACCESS  not-accessible
    STATUS      current
    DESCRIPTION
        "The vRtrLdpNgExtP2MPFecInLblTable is a read-only table that represents all
         P2MP FECs received from an LDP peer known to the virtual router."
    ::= { tmnxLdpNgObjs 17 }

vRtrLdpNgExtP2MPFecInLblEntry    OBJECT-TYPE
    SYNTAX      VRtrLdpNgExtP2MPFecInLblEntry
    MAX-ACCESS  not-accessible
    STATUS      current
    DESCRIPTION
        "Each row entry represents an instance of a P2MP FEC
         received from an LDP peer."
    INDEX  { vRtrID,
             vRtrLdpNgExtP2MPFecRootAddrType,
             vRtrLdpNgExtP2MPFecRootAddress,
             vRtrLdpNgExtP2MPFecOpaqueType,
             vRtrLdpNgExtP2MPFecOpaqueLength,
             vRtrLdpNgExtP2MPFecOpaqueValue,
             vRtrLdpNgPeerLdpIdType,
             vRtrLdpNgPeerLdpId,
             vRtrLdpNgExtP2MPFecInLblId }
    ::= { vRtrLdpNgExtP2MPFecInLblTable 1 }

VRtrLdpNgExtP2MPFecInLblEntry ::= SEQUENCE {
    vRtrLdpNgExtP2MPFecInLblId             Unsigned32,
    vRtrLdpNgExtP2MPFecInLbl               Unsigned32,
    vRtrLdpNgExtP2MPFecInLblStatus         TmnxLabelStatus
    }

vRtrLdpNgExtP2MPFecInLblId        OBJECT-TYPE
    SYNTAX      Unsigned32
    MAX-ACCESS  not-accessible
    STATUS      current
    DESCRIPTION
        "The value of vRtrLdpNgExtP2MPFecInLblId indicates the
         label number of the ingress label exchanged."
    ::= { vRtrLdpNgExtP2MPFecInLblEntry 1 }

vRtrLdpNgExtP2MPFecInLbl          OBJECT-TYPE
    SYNTAX      Unsigned32
    MAX-ACCESS  read-only
    STATUS      current
    DESCRIPTION
        "The value of vRtrLdpNgExtP2MPFecInLbl indicates the
         ingress label exchanged."
    ::= { vRtrLdpNgExtP2MPFecInLblEntry 2 }

vRtrLdpNgExtP2MPFecInLblStatus    OBJECT-TYPE
    SYNTAX      TmnxLabelStatus
    MAX-ACCESS  read-only
    STATUS      current
    DESCRIPTION
        "The value of vRtrLdpNgExtP2MPFecInLblStatus indicates the
         status of the ingress label."
    ::= { vRtrLdpNgExtP2MPFecInLblEntry 3 }

--
--  Alcatel-Lucent SROS series LDP P2MP FEC Out Label Table
--

vRtrLdpNgExtP2MPFecOutLblTable    OBJECT-TYPE
    SYNTAX      SEQUENCE OF VRtrLdpNgExtP2MPFecOutLblEntry
    MAX-ACCESS  not-accessible
    STATUS      current
    DESCRIPTION
        "The vRtrLdpNgExtP2MPFecTable is a read-only table that represents all
         P2MP FECs sent to an LDP peer known to the Virtual Router."
    ::= { tmnxLdpNgObjs 18 }

vRtrLdpNgExtP2MPFecOutLblEntry    OBJECT-TYPE
    SYNTAX      VRtrLdpNgExtP2MPFecOutLblEntry
    MAX-ACCESS  not-accessible
    STATUS      current
    DESCRIPTION
        "Each row entry represents an instance of a P2MP FEC sent
         to a LDP peer."
    INDEX  { vRtrID,
             vRtrLdpNgExtP2MPFecRootAddrType,
             vRtrLdpNgExtP2MPFecRootAddress,
             vRtrLdpNgExtP2MPFecOpaqueType,
             vRtrLdpNgExtP2MPFecOpaqueLength,
             vRtrLdpNgExtP2MPFecOpaqueValue,
             vRtrLdpNgPeerLdpIdType,
             vRtrLdpNgPeerLdpId,
             vRtrLdpNgExtP2MPFecOutLblId }
    ::= { vRtrLdpNgExtP2MPFecOutLblTable 1 }

VRtrLdpNgExtP2MPFecOutLblEntry ::= SEQUENCE {
    vRtrLdpNgExtP2MPFecOutLblId              Unsigned32,
    vRtrLdpNgExtP2MPFecOutLbl                Unsigned32,
    vRtrLdpNgExtP2MPFecOutLblStatus          TmnxLabelStatus,
    vRtrLdpNgExtP2MPFecOutLblNHType          InetAddressType,
    vRtrLdpNgExtP2MPFecOutLblNHAdr           InetAddress,
    vRtrLdpNgExtP2MPFecOutLblIfIndex         InterfaceIndexOrZero,
    vRtrLdpNgExtP2MPFecOutLblLspId           TmnxVRtrMplsLspID
    }

vRtrLdpNgExtP2MPFecOutLblId        OBJECT-TYPE
    SYNTAX      Unsigned32
    MAX-ACCESS  not-accessible
    STATUS      current
    DESCRIPTION
        "The value of vRtrLdpNgExtP2MPFecOutLblId indicates the
         label number of the egress label exchanged."
    ::= { vRtrLdpNgExtP2MPFecOutLblEntry 1 }

vRtrLdpNgExtP2MPFecOutLbl          OBJECT-TYPE
    SYNTAX      Unsigned32
    MAX-ACCESS  read-only
    STATUS      current
    DESCRIPTION
        "The value of vRtrLdpNgExtP2MPFecOutLbl indicates the
         egress label exchanged."
    ::= { vRtrLdpNgExtP2MPFecOutLblEntry 2 }

vRtrLdpNgExtP2MPFecOutLblStatus    OBJECT-TYPE
    SYNTAX      TmnxLabelStatus
    MAX-ACCESS  read-only
    STATUS      current
    DESCRIPTION
        "The value of vRtrLdpNgExtP2MPFecOutLblStatus indicates the
         status of the egress label."
    ::= { vRtrLdpNgExtP2MPFecOutLblEntry 3 }

vRtrLdpNgExtP2MPFecOutLblNHType     OBJECT-TYPE
    SYNTAX      InetAddressType
    MAX-ACCESS  read-only
    STATUS      current
    DESCRIPTION
        "The value of vRtrLdpNgExtP2MPFecOutLblNHType indicates the
         address type of vRtrLdpNgExtP2MPFecOutLblNHAdr."
    ::= { vRtrLdpNgExtP2MPFecOutLblEntry 4 }

vRtrLdpNgExtP2MPFecOutLblNHAdr    OBJECT-TYPE
    SYNTAX      InetAddress (SIZE(4|16))
    MAX-ACCESS  read-only
    STATUS      current
    DESCRIPTION
        "The value of vRtrLdpNgExtP2MPFecOutLblNHAdr indicates the
         IP address of the next hop for egress label."
    ::= { vRtrLdpNgExtP2MPFecOutLblEntry 5 }

vRtrLdpNgExtP2MPFecOutLblIfIndex   OBJECT-TYPE
    SYNTAX      InterfaceIndexOrZero
    MAX-ACCESS  read-only
    STATUS      current
    DESCRIPTION
        "The value of vRtrLdpNgExtP2MPFecOutLblIfIndex indicates the
         interface index for egress label."
    ::= { vRtrLdpNgExtP2MPFecOutLblEntry 6 }

vRtrLdpNgExtP2MPFecOutLblLspId    OBJECT-TYPE
    SYNTAX      TmnxVRtrMplsLspID
    MAX-ACCESS  read-only
    STATUS      current
    DESCRIPTION
        "The value of vRtrLdpNgExtP2MPFecOutLblLspId indicates the LSP id of the 
         LSP for the RSVP tunnel used by LDP in LDP over RSVP associated with 
         egress label."
    ::= { vRtrLdpNgExtP2MPFecOutLblEntry 7 }

--
--  Alcatel-Lucent SROS series LDP Address FEC Mapping Table
--

vRtrLdpNgExtP2MPFecMapTable    OBJECT-TYPE
    SYNTAX      SEQUENCE OF VRtrLdpNgExtP2MPFecMapEntry
    MAX-ACCESS  not-accessible
    STATUS      current
    DESCRIPTION
        "The vRtrLdpNgExtP2MPFecMapTable is a read-only table which maps to the
         vRtrLdpNgExtP2MPFecTable. This table has the same indexes as the
         vRtrLdpNgExtP2MPFecTable but the order in which these indexes are
         specified is different for the two tables."
    ::= { tmnxLdpNgObjs 19 }

vRtrLdpNgExtP2MPFecMapEntry    OBJECT-TYPE
    SYNTAX      VRtrLdpNgExtP2MPFecMapEntry
    MAX-ACCESS  not-accessible
    STATUS      current
    DESCRIPTION
        "Each row entry represents an instance of a P2MP FEC sent
         to or received from an LDP peer."
    INDEX  { vRtrID,
             vRtrLdpNgPeerLdpIdType,
             vRtrLdpNgPeerLdpId,
             vRtrLdpNgExtP2MPFecRootAddrType,
             vRtrLdpNgExtP2MPFecRootAddress,
             vRtrLdpNgExtP2MPFecOpaqueType,
             vRtrLdpNgExtP2MPFecOpaqueLength,
             vRtrLdpNgExtP2MPFecOpaqueValue }
    ::= { vRtrLdpNgExtP2MPFecMapTable 1 }

VRtrLdpNgExtP2MPFecMapEntry ::= SEQUENCE {
    vRtrLdpNgExtP2MPFecMapFlags                  TmnxLdpFECFlags,
    vRtrLdpNgExtP2MPFecMapNumInLbls              Gauge32,
    vRtrLdpNgExtP2MPFecMapNumOutLbls             Gauge32,
    vRtrLdpNgExtP2MPFecMapTunnelIfId             Unsigned32,
    vRtrLdpNgExtP2MPFecMapMetric                 Unsigned32,
    vRtrLdpNgExtP2MPFecMapMTU                    Unsigned32
}

vRtrLdpNgExtP2MPFecMapFlags    OBJECT-TYPE
    SYNTAX      TmnxLdpFECFlags
    MAX-ACCESS  read-only
    STATUS      current
    DESCRIPTION
        "The bit flags of vRtrLdpNgExtP2MPFecMapFlags indicates the characteristics
         of the FEC."
    ::= { vRtrLdpNgExtP2MPFecMapEntry 1 }

vRtrLdpNgExtP2MPFecMapNumInLbls    OBJECT-TYPE
    SYNTAX      Gauge32
    MAX-ACCESS  read-only
    STATUS      current
    DESCRIPTION
        "The value of vRtrLdpNgExtP2MPFecMapNumInLbls indicates the number of
         labels that have been sent to the peer associated with this FEC."
    ::= { vRtrLdpNgExtP2MPFecMapEntry 2 }

vRtrLdpNgExtP2MPFecMapNumOutLbls    OBJECT-TYPE
    SYNTAX      Gauge32
    MAX-ACCESS  read-only
    STATUS      current
    DESCRIPTION
        "The value of vRtrLdpNgExtP2MPFecMapNumOutLbls indicates the number of
         labels that have been received from the peer associated with this
         FEC."
    ::= { vRtrLdpNgExtP2MPFecMapEntry 3 }

vRtrLdpNgExtP2MPFecMapTunnelIfId    OBJECT-TYPE
    SYNTAX      Unsigned32
    MAX-ACCESS  read-only
    STATUS      current
    DESCRIPTION
        "The value of vRtrLdpNgExtP2MPFecMapTunnelIfId indicates the tunnel
         interface identifier for this P2MP FEC."
    ::= { vRtrLdpNgExtP2MPFecMapEntry 4 }

vRtrLdpNgExtP2MPFecMapMetric    OBJECT-TYPE
    SYNTAX      Unsigned32
    MAX-ACCESS  read-only
    STATUS      current
    DESCRIPTION
        "The value of vRtrLdpNgExtP2MPFecMapMetric indicates the relative cost
         of the tunnel represented by this P2MP FEC"
    ::= { vRtrLdpNgExtP2MPFecMapEntry 5 }

vRtrLdpNgExtP2MPFecMapMTU    OBJECT-TYPE
    SYNTAX      Unsigned32
    MAX-ACCESS  read-only
    STATUS      current
    DESCRIPTION
        "The value of vRtrLdpNgExtP2MPFecMapMTU indicates the maximum transfer
         unit for payloads represented by this P2MP FEC"
    ::= { vRtrLdpNgExtP2MPFecMapEntry 6 }

--
-- LDP Interface/Targeted Peer Statistics Table
--

vRtrLdpNgInetIfStatsTable    OBJECT-TYPE
    SYNTAX      SEQUENCE OF VRtrLdpNgInetIfStatsEntry
    MAX-ACCESS  not-accessible
    STATUS      current
    DESCRIPTION
        "The vRtrLdpNgInetIfStatsTable is a read-only table. The purpose of this 
         table is to keep statistical information about the LDP Interfaces for
         given Inet address family on this LSR.

         Use of AUGMENTS clause implies a one-to-one dependent relationship
         between the base table, vRtrLdpNgInetIfTable, and the augmenting table,
         vRtrLdpNgInetIfStatsTable. This in effect extends the vRtrLdpNgInetIfTable 
         with additional columns. Creation or deletion of a row in the 
         vRtrLdpNgInetIfTable results in the same fate for the row in the 
         vRtrLdpNgInetIfStatsTable."
    ::= { tmnxLdpNgObjs 20 }
    
vRtrLdpNgInetIfStatsEntry OBJECT-TYPE
    SYNTAX      VRtrLdpNgInetIfStatsEntry
    MAX-ACCESS  not-accessible
    STATUS      current
    DESCRIPTION
        "A row in this table contains statistical information about an LDP
         Interface for given Inet address family. 

        Some counters contained in a row are for fatal errors received 
        during a former LDP Session associated with this entry. For example,
        an LDP Pdu received on a TCP connection during an LDP Session 
        contains a fatal error.  That error is counted here, because the
        session is terminated.

        If the error is NOT fatal (i.e. and the Session remains), then the
        error is counted in the vRtrLdpNgSessionStatsEntry."
    AUGMENTS  { vRtrLdpNgInetIfEntry }
    ::= { vRtrLdpNgInetIfStatsTable 1 }

VRtrLdpNgInetIfStatsEntry ::= SEQUENCE {
    vRtrLdpNgInetIfStatsExistingAdj                Gauge32
}

vRtrLdpNgInetIfStatsExistingAdj    OBJECT-TYPE
    SYNTAX      Gauge32
    MAX-ACCESS  read-only
    STATUS      current
    DESCRIPTION
        "The value of vRtrLdpNgInetIfStatsExistingAdj indicates a count of the total
         active adjacencies on this LDP interface for given Inet address family."
    ::= { vRtrLdpNgInetIfStatsEntry 1 }

-- 
-- LDP Session Statistics table
--

vRtrLdpNgSessionStatsTable    OBJECT-TYPE
    SYNTAX      SEQUENCE OF VRtrLdpNgSessionStatsEntry
    MAX-ACCESS  not-accessible
    STATUS      current
    DESCRIPTION
        "The vRtrLdpNgSessionStatsTable is a read-only table. The purpose of 
         this table is to keep statistical information about a single session
         between an LDP entity and an LDP Peer.

         Use of AUGMENTS clause implies a one-to-one dependent relationship
         between the base table, vRtrLdpNgSessionTable, and the augmenting 
         table, vRtrLdpNgSessionStatsTable. This in effect extends the 
         vRtrLdpNgSessionTable with additional columns. Creation or deletion
         of a row in the vRtrLdpNgSessionTable results in the same fate for 
         the row in the vRtrLdpNgSessionStatsTable."
    ::= { tmnxLdpNgObjs 21 }

vRtrLdpNgSessionStatsEntry OBJECT-TYPE
    SYNTAX      VRtrLdpNgSessionStatsEntry
    MAX-ACCESS  not-accessible
    STATUS      current
    DESCRIPTION
        "A row in this table represents statistical information about a 
         single session between an LDP entity and an LDP Peer."
    AUGMENTS  { vRtrLdpNgSessionEntry }
    ::= { vRtrLdpNgSessionStatsTable 1 }

VRtrLdpNgSessionStatsEntry ::= SEQUENCE {
    vRtrLdpNgSessStatsTargAdj           Gauge32,
    vRtrLdpNgSessStatsLinkAdj           Gauge32,
    vRtrLdpNgSessStatsHelloIn           Counter32, 
    vRtrLdpNgSessStatsHelloOut          Counter32, 
    vRtrLdpNgSessStatsKeepaliveIn       Counter32,  
    vRtrLdpNgSessStatsKeepaliveOut      Counter32,  
    vRtrLdpNgSessStatsInitIn            Counter32,  
    vRtrLdpNgSessStatsInitOut           Counter32,  
    vRtrLdpNgSessStatsLblMappingIn      Counter32,  
    vRtrLdpNgSessStatsLblMappingOut     Counter32,  
    vRtrLdpNgSessStatsLblRequestIn      Counter32,  
    vRtrLdpNgSessStatsLblRequestOut     Counter32,  
    vRtrLdpNgSessStatsLblReleaseIn      Counter32,  
    vRtrLdpNgSessStatsLblReleaseOut     Counter32,  
    vRtrLdpNgSessStatsLblWithdrawIn     Counter32,  
    vRtrLdpNgSessStatsLblWithdrawOut    Counter32,  
    vRtrLdpNgSessStatsLblAbortIn        Counter32,  
    vRtrLdpNgSessStatsLblAbortOut       Counter32,  
    vRtrLdpNgSessStatsAddrIn            Counter32,  
    vRtrLdpNgSessStatsAddrOut           Counter32,  
    vRtrLdpNgSessStatsAddrWithdrIn      Counter32,
    vRtrLdpNgSessStatsAddrWithdrOut     Counter32,  
    vRtrLdpNgSessStatsNotifIn           Counter32,  
    vRtrLdpNgSessStatsNotifOut          Counter32,
    vRtrLdpNgSessStatsIPv4PfxFecRcv     Counter32,
    vRtrLdpNgSessStatsIPv6PfxFecRcv     Counter32,
    vRtrLdpNgSessStatsIPv4PfxFecSnt     Counter32,
    vRtrLdpNgSessStatsIPv6PfxFecSnt     Counter32,
    vRtrLdpNgSessStatsIPv4P2MPFecRcv    Counter32,
    vRtrLdpNgSessStatsIPv6P2MPFecRcv    Counter32,
    vRtrLdpNgSessStatsIPv4P2MPFecSnt    Counter32,
    vRtrLdpNgSessStatsIPv6P2MPFecSnt    Counter32,
    vRtrLdpNgSessStatsSvcFec128Recv     Counter32,
    vRtrLdpNgSessStatsSvcFec128Sent     Counter32,
    vRtrLdpNgSessStatsSvcFec129Recv     Counter32,
    vRtrLdpNgSessStatsSvcFec129Sent     Counter32,
    vRtrLdpNgSessStatsIPv4AddrRecv      Counter32,
    vRtrLdpNgSessStatsIPv6AddrRecv      Counter32,
    vRtrLdpNgSessStatsIPv4AddrSent      Counter32,
    vRtrLdpNgSessStatsIPv6AddrSent      Counter32,
    vRtrLdpNgSessStatsCapabilityIn      Counter32,
    vRtrLdpNgSessStatsCapabilityOut     Counter32
}

vRtrLdpNgSessStatsTargAdj    OBJECT-TYPE
    SYNTAX      Gauge32
    MAX-ACCESS  read-only
    STATUS      current
    DESCRIPTION
        "The value of vRtrLdpNgSessStatsTargAdj indicates the number of
         targeted adjacencies for this session."
    ::= { vRtrLdpNgSessionStatsEntry 1 }

vRtrLdpNgSessStatsLinkAdj    OBJECT-TYPE
    SYNTAX      Gauge32
    MAX-ACCESS  read-only
    STATUS      current
    DESCRIPTION
        "The value of vRtrLdpNgSessStatsLinkAdj indicates the number of
         link adjacencies for this session."
    ::= { vRtrLdpNgSessionStatsEntry 2 }

vRtrLdpNgSessStatsHelloIn    OBJECT-TYPE
    SYNTAX      Counter32
    MAX-ACCESS  read-only
    STATUS      current
    DESCRIPTION
        "The value of vRtrLdpNgSessStatsHelloIn counts the number of 
         Hello Messages that have been received during this session."
    ::= { vRtrLdpNgSessionStatsEntry 3 }

vRtrLdpNgSessStatsHelloOut    OBJECT-TYPE
    SYNTAX      Counter32
    MAX-ACCESS  read-only
    STATUS      current
    DESCRIPTION
        "The value of vRtrLdpNgSessStatsHelloOut counts the number of 
         Hello Messages that have been sent during this session."
    ::= { vRtrLdpNgSessionStatsEntry 4 }

vRtrLdpNgSessStatsKeepaliveIn    OBJECT-TYPE
    SYNTAX      Counter32
    MAX-ACCESS  read-only
    STATUS      current
    DESCRIPTION
        "The value of vRtrLdpNgSessStatsKeepaliveIn counts the number of 
         Keepalive Messages that have been received during this session."
    ::= { vRtrLdpNgSessionStatsEntry 5 }

vRtrLdpNgSessStatsKeepaliveOut    OBJECT-TYPE
    SYNTAX      Counter32
    MAX-ACCESS  read-only
    STATUS      current
    DESCRIPTION
        "The value of vRtrLdpNgSessStatsKeepaliveOut counts the number of 
         Keepalive Messages that have been sent during this session."
    ::= { vRtrLdpNgSessionStatsEntry 6 }

vRtrLdpNgSessStatsInitIn    OBJECT-TYPE
    SYNTAX      Counter32
    MAX-ACCESS  read-only
    STATUS      current
    DESCRIPTION
        "The value of vRtrLdpNgSessStatsInitIn counts the number of 
         Init Messages that have been received during this session."
    ::= { vRtrLdpNgSessionStatsEntry 7 }

vRtrLdpNgSessStatsInitOut    OBJECT-TYPE
    SYNTAX      Counter32
    MAX-ACCESS  read-only
    STATUS      current
    DESCRIPTION
        "The value of vRtrLdpNgSessStatsInitOut counts the number of 
         Init Messages that have been sent during this session."
    ::= { vRtrLdpNgSessionStatsEntry 8 }

vRtrLdpNgSessStatsLblMappingIn    OBJECT-TYPE
    SYNTAX      Counter32
    MAX-ACCESS  read-only
    STATUS      current
    DESCRIPTION
        "The value of vRtrLdpNgSessStatsLblMappingIn counts the number of
         Label Mapping Messages that have been received during this session."
    ::= { vRtrLdpNgSessionStatsEntry 9 }

vRtrLdpNgSessStatsLblMappingOut    OBJECT-TYPE
    SYNTAX      Counter32
    MAX-ACCESS  read-only
    STATUS      current
    DESCRIPTION
        "The value of vRtrLdpNgSessStatsLblMappingOut counts the number of
         Label Mapping Messages that have been sent during this session."
    ::= { vRtrLdpNgSessionStatsEntry 10 }

vRtrLdpNgSessStatsLblRequestIn    OBJECT-TYPE
    SYNTAX      Counter32
    MAX-ACCESS  read-only
    STATUS      current
    DESCRIPTION
        "The value of vRtrLdpNgSessStatsLblRequestIn counts the number of
         Label Request Messages that have been received during this session."
    ::= { vRtrLdpNgSessionStatsEntry 11 }

vRtrLdpNgSessStatsLblRequestOut    OBJECT-TYPE
    SYNTAX      Counter32
    MAX-ACCESS  read-only
    STATUS      current
    DESCRIPTION
        "The value of vRtrLdpNgSessStatsLblRequestOut counts the number of
         Label Request Messages that have been sent during this session."
    ::= { vRtrLdpNgSessionStatsEntry 12 }

vRtrLdpNgSessStatsLblReleaseIn    OBJECT-TYPE
    SYNTAX      Counter32
    MAX-ACCESS  read-only
    STATUS      current
    DESCRIPTION
        "The value of vRtrLdpNgSessStatsLblReleaseIn counts the number of
         Label Release Messages that have been received during this session."
    ::= { vRtrLdpNgSessionStatsEntry 13 }

vRtrLdpNgSessStatsLblReleaseOut    OBJECT-TYPE
    SYNTAX      Counter32
    MAX-ACCESS  read-only
    STATUS      current
    DESCRIPTION
        "The value of vRtrLdpNgSessStatsLblReleaseOut counts the number of
         Label Release Messages that have been sent during this session."
    ::= { vRtrLdpNgSessionStatsEntry 14 }

vRtrLdpNgSessStatsLblWithdrawIn    OBJECT-TYPE
    SYNTAX      Counter32
    MAX-ACCESS  read-only
    STATUS      current
    DESCRIPTION
        "The value of vRtrLdpNgSessStatsLblWithdrawIn counts the number of
         Label Withdraw Messages that have been received during this session."
    ::= { vRtrLdpNgSessionStatsEntry 15 }

vRtrLdpNgSessStatsLblWithdrawOut    OBJECT-TYPE
    SYNTAX      Counter32
    MAX-ACCESS  read-only
    STATUS      current
    DESCRIPTION
        "The value of vRtrLdpNgSessStatsLblWithdrawOut counts the number of
         Label Withdraw Messages that have been sent during this session."
    ::= { vRtrLdpNgSessionStatsEntry 16 }

vRtrLdpNgSessStatsLblAbortIn    OBJECT-TYPE
    SYNTAX      Counter32
    MAX-ACCESS  read-only
    STATUS      current
    DESCRIPTION
        "The value of vRtrLdpNgSessStatsLblAbortIn counts the number of
         Label Abort Messages that have been received during this session."
    ::= { vRtrLdpNgSessionStatsEntry 17 }

vRtrLdpNgSessStatsLblAbortOut    OBJECT-TYPE
    SYNTAX      Counter32
    MAX-ACCESS  read-only
    STATUS      current
    DESCRIPTION
        "The value of vRtrLdpNgSessStatsLblAbortOut counts the number of
         Label Abort Messages that have been sent during this session."
    ::= { vRtrLdpNgSessionStatsEntry 18 }

vRtrLdpNgSessStatsAddrIn    OBJECT-TYPE
    SYNTAX      Counter32
    MAX-ACCESS  read-only
    STATUS      current
    DESCRIPTION
        "The value of vRtrLdpNgSessStatsAddrIn counts the number of 
         Address Messages that have been received during this session."
    ::= { vRtrLdpNgSessionStatsEntry 19 }

vRtrLdpNgSessStatsAddrOut    OBJECT-TYPE
    SYNTAX      Counter32
    MAX-ACCESS  read-only
    STATUS      current
    DESCRIPTION
        "The value of vRtrLdpNgSessStatsAddrOut counts the number of 
         Address Messages that have been sent during this session."
    ::= { vRtrLdpNgSessionStatsEntry 20 }

vRtrLdpNgSessStatsAddrWithdrIn    OBJECT-TYPE
    SYNTAX      Counter32
    MAX-ACCESS  read-only
    STATUS      current
    DESCRIPTION
        "The value of vRtrLdpNgSessStatsAddrWithdrIn counts the number of
         Address Withdraw Messages that have been received during this 
         session."
    ::= { vRtrLdpNgSessionStatsEntry 21 }

vRtrLdpNgSessStatsAddrWithdrOut    OBJECT-TYPE
    SYNTAX      Counter32
    MAX-ACCESS  read-only
    STATUS      current
    DESCRIPTION
        "The value of vRtrLdpNgSessStatsAddrWithdrOut counts the number of
         Address Withdraw Messages that have been sent during this session."
    ::= { vRtrLdpNgSessionStatsEntry 22 }

vRtrLdpNgSessStatsNotifIn    OBJECT-TYPE
    SYNTAX      Counter32
    MAX-ACCESS  read-only
    STATUS      current
    DESCRIPTION
        "The value of vRtrLdpNgSessStatsNotifIn counts the number of
         Notification Messages that have been received during this session."
    ::= { vRtrLdpNgSessionStatsEntry 23 }

vRtrLdpNgSessStatsNotifOut    OBJECT-TYPE
    SYNTAX      Counter32
    MAX-ACCESS  read-only
    STATUS      current
    DESCRIPTION
        "The value of vRtrLdpNgSessStatsNotifOut counts the number of
         Notification Messages that have been sent during this session."
    ::= { vRtrLdpNgSessionStatsEntry 24 }

vRtrLdpNgSessStatsIPv4PfxFecRcv    OBJECT-TYPE
    SYNTAX      Counter32
    MAX-ACCESS  read-only
    STATUS      current
    DESCRIPTION
        "The value of vRtrLdpNgSessStatsIPv4PfxFecRcv counts the number of IPv4
         prefix FECs received for this session."
    ::= { vRtrLdpNgSessionStatsEntry 25 }

vRtrLdpNgSessStatsIPv6PfxFecRcv    OBJECT-TYPE
    SYNTAX      Counter32
    MAX-ACCESS  read-only
    STATUS      current
    DESCRIPTION
        "The value of vRtrLdpNgSessStatsIPv6PfxFecRcv counts the number of IPv6
         prefix FECs received for this session."
    ::= { vRtrLdpNgSessionStatsEntry 26 }

vRtrLdpNgSessStatsIPv4PfxFecSnt    OBJECT-TYPE
    SYNTAX      Counter32
    MAX-ACCESS  read-only
    STATUS      current
    DESCRIPTION
        "The value of vRtrLdpNgSessStatsIPv4PfxFecSnt counts the number of IPv4 
         prefix FECs sent for this session."
    ::= { vRtrLdpNgSessionStatsEntry 27 }

vRtrLdpNgSessStatsIPv6PfxFecSnt    OBJECT-TYPE
    SYNTAX      Counter32
    MAX-ACCESS  read-only
    STATUS      current
    DESCRIPTION
        "The value of vRtrLdpNgSessStatsIPv6PfxFecSnt counts the number of IPv6 
         prefix FECs sent for this session."
    ::= { vRtrLdpNgSessionStatsEntry 28 }

vRtrLdpNgSessStatsIPv4P2MPFecRcv    OBJECT-TYPE
    SYNTAX      Counter32
    MAX-ACCESS  read-only
    STATUS      current
    DESCRIPTION
        "The value of vRtrLdpNgSessStatsIPv4P2MPFecRcv counts the number of IPv4
         P2MP FECs received for this session."
    ::= { vRtrLdpNgSessionStatsEntry 29 }

vRtrLdpNgSessStatsIPv6P2MPFecRcv    OBJECT-TYPE
    SYNTAX      Counter32
    MAX-ACCESS  read-only
    STATUS      current
    DESCRIPTION
        "The value of vRtrLdpNgSessStatsIPv6P2MPFecRcv counts the number of IPv6
         P2MP FECs received for this session."
    ::= { vRtrLdpNgSessionStatsEntry 30 }

vRtrLdpNgSessStatsIPv4P2MPFecSnt    OBJECT-TYPE
    SYNTAX      Counter32
    MAX-ACCESS  read-only
    STATUS      current
    DESCRIPTION
        "The value of vRtrLdpNgSessStatsIPv4P2MPFecSnt counts the number of IPv4 
         P2MP FECs sent for this session."
    ::= { vRtrLdpNgSessionStatsEntry 31 }

vRtrLdpNgSessStatsIPv6P2MPFecSnt    OBJECT-TYPE
    SYNTAX      Counter32
    MAX-ACCESS  read-only
    STATUS      current
    DESCRIPTION
        "The value of vRtrLdpNgSessStatsIPv6P2MPFecSnt counts the number of IPv6 
         P2MP FECs sent for this session."
    ::= { vRtrLdpNgSessionStatsEntry 32 }

vRtrLdpNgSessStatsSvcFec128Recv    OBJECT-TYPE
    SYNTAX      Counter32
    MAX-ACCESS  read-only
    STATUS      current
    DESCRIPTION
        "The value of vRtrLdpNgSessStatsSvcFec128Recv counts the number of service
         FEC 128 received for this session."
    ::= { vRtrLdpNgSessionStatsEntry 33 }

vRtrLdpNgSessStatsSvcFec128Sent    OBJECT-TYPE
    SYNTAX      Counter32
    MAX-ACCESS  read-only
    STATUS      current
    DESCRIPTION
        "The value of vRtrLdpNgSessStatsSvcFec128Sent counts the number of 
         service FEC 128 sent for this session."
    ::= { vRtrLdpNgSessionStatsEntry 34 }

vRtrLdpNgSessStatsSvcFec129Recv    OBJECT-TYPE
    SYNTAX      Counter32
    MAX-ACCESS  read-only
    STATUS      current
    DESCRIPTION
        "The value of vRtrLdpNgSessStatsSvcFec129Recv counts the number of 
         service FEC 129 received for this session."
    ::= { vRtrLdpNgSessionStatsEntry 35 }

vRtrLdpNgSessStatsSvcFec129Sent    OBJECT-TYPE
    SYNTAX      Counter32
    MAX-ACCESS  read-only
    STATUS      current
    DESCRIPTION
        "The value of vRtrLdpNgSessStatsSvcFec129Sent counts the number of 
         service FEC 129 sent for this session."
    ::= { vRtrLdpNgSessionStatsEntry 36 }

vRtrLdpNgSessStatsIPv4AddrRecv    OBJECT-TYPE
    SYNTAX      Counter32
    MAX-ACCESS  read-only
    STATUS      current
    DESCRIPTION
        "The value of vRtrLdpNgSessStatsIPv4AddrRecv counts the number of IPv4
         local addresses received for this session."
    ::= { vRtrLdpNgSessionStatsEntry 37 }

vRtrLdpNgSessStatsIPv6AddrRecv    OBJECT-TYPE
    SYNTAX      Counter32
    MAX-ACCESS  read-only
    STATUS      current
    DESCRIPTION
        "The value of vRtrLdpNgSessStatsIPv6AddrRecv counts the number of IPv6
         local addresses received for this session."
    ::= { vRtrLdpNgSessionStatsEntry 38 }

vRtrLdpNgSessStatsIPv4AddrSent    OBJECT-TYPE
    SYNTAX      Counter32
    MAX-ACCESS  read-only
    STATUS      current
    DESCRIPTION
        "The value of vRtrLdpNgSessStatsIPv4AddrSent counts the number of IPv4
         local addresses sent for this session."
    ::= { vRtrLdpNgSessionStatsEntry 39 }

vRtrLdpNgSessStatsIPv6AddrSent    OBJECT-TYPE
    SYNTAX      Counter32
    MAX-ACCESS  read-only
    STATUS      current
    DESCRIPTION
        "The value of vRtrLdpNgSessStatsIPv6AddrSent counts the number of IPv6
         local addresses sent for this session."
    ::= { vRtrLdpNgSessionStatsEntry 40 }

vRtrLdpNgSessStatsCapabilityIn    OBJECT-TYPE
    SYNTAX      Counter32
    MAX-ACCESS  read-only
    STATUS      current
    DESCRIPTION
        "The value of vRtrLdpNgSessStatsCapabilityIn counts the number of
         Capability Messages that have been received during this session."
    ::= { vRtrLdpNgSessionStatsEntry 41 }

vRtrLdpNgSessStatsCapabilityOut    OBJECT-TYPE
    SYNTAX      Counter32
    MAX-ACCESS  read-only
    STATUS      current
    DESCRIPTION
        "The value of vRtrLdpNgSessStatsCapabilityOut counts the number of
         Capability Messages that have been sent during this session."
    ::= { vRtrLdpNgSessionStatsEntry 42 }

--
--  Alcatel-Lucent SROS series LDP Service FEC Table
--

vLdpNgSvcFec128Table     OBJECT-TYPE
    SYNTAX      SEQUENCE OF VLdpNgSvcFec128Entry 
    MAX-ACCESS  not-accessible
    STATUS      current
    DESCRIPTION
        "The vLdpNgSvcFec128Table is a read-only table that represents 
         operational information of Service FEC 128 either sent to or received 
         from an LDP peer known to the Virtual Router."
    ::= { tmnxLdpNgObjs 22 }

vLdpNgSvcFec128Entry    OBJECT-TYPE
    SYNTAX      VLdpNgSvcFec128Entry
    MAX-ACCESS  not-accessible
    STATUS      current
    DESCRIPTION
        "Each row entry represents an instance of a service FEC 128 sent to 
         or received from an LDP peer."
    INDEX  { vRtrID, 
             vLdpNgFec128FecType,
             vLdpNgFec128VcType,
             vLdpNgFec128VcId,
             vRtrLdpNgPeerLdpIdType,
             vRtrLdpNgPeerLdpId } 
    ::= { vLdpNgSvcFec128Table 1 }

VLdpNgSvcFec128Entry ::= SEQUENCE {
    vLdpNgFec128FecType                  TmnxLdpFECType,
    vLdpNgFec128VcType                   TmnxVcType,     
    vLdpNgFec128VcId                     TmnxVcId,
    vLdpNgFec128ServType                 ServType,
    vLdpNgFec128ServId                   TmnxServId,
    vLdpNgFec128VpnId                    TmnxVpnId,
    vLdpNgFec128Flags                    TmnxLdpFECFlags,
    vLdpNgFec128NumInLabels              Unsigned32,
    vLdpNgFec128NumOutLabels             Unsigned32,
    vLdpNgFec128SdpId                    SdpId,
    vLdpNgFec128MateEndptVcId            TmnxVcId,
    vLdpNgFec128MateEndptSdpId           SdpId
}

vLdpNgFec128FecType    OBJECT-TYPE 
    SYNTAX      TmnxLdpFECType
    MAX-ACCESS  not-accessible
    STATUS      current
    DESCRIPTION
        "The value of vLdpNgFec128FecType specifies the FEC type associated 
         with this service FEC."
    ::= { vLdpNgSvcFec128Entry 1 }

vLdpNgFec128VcType    OBJECT-TYPE 
    SYNTAX      TmnxVcType
    MAX-ACCESS  not-accessible
    STATUS      current
    DESCRIPTION
        "The value of vLdpNgFec128VcType specifies the VC type  
         associated with this service FEC."
    ::= { vLdpNgSvcFec128Entry 2 }

vLdpNgFec128VcId    OBJECT-TYPE
    SYNTAX      TmnxVcId
    MAX-ACCESS  not-accessible
    STATUS      current
    DESCRIPTION
        "The value of vLdpNgFec128VcId specifies the VC identifier 
         associated with this service FEC."
    ::= { vLdpNgSvcFec128Entry 3 }

vLdpNgFec128ServType    OBJECT-TYPE 
    SYNTAX      ServType
    MAX-ACCESS  read-only
    STATUS      current
    DESCRIPTION
        "The value of vLdpNgFec128ServType indicates the Service type
         associated with this service FEC."
    ::= { vLdpNgSvcFec128Entry 4 }

vLdpNgFec128ServId    OBJECT-TYPE
    SYNTAX      TmnxServId (1..2147483647)
    MAX-ACCESS  read-only
    STATUS      current
    DESCRIPTION
        "The value of vLdpNgFec128ServId indicates the Service identifier
         associated with this service FEC."
    ::= { vLdpNgSvcFec128Entry 5 }

vLdpNgFec128VpnId    OBJECT-TYPE
    SYNTAX      TmnxVpnId
    MAX-ACCESS  read-only
    STATUS      current
    DESCRIPTION
        "The value of vLdpNgFec128VpnId identifies the VPN associated 
         with the FEC."
    ::= { vLdpNgSvcFec128Entry 6 }

vLdpNgFec128Flags    OBJECT-TYPE 
    SYNTAX      TmnxLdpFECFlags
    MAX-ACCESS  read-only
    STATUS      current
    DESCRIPTION
        "The bit flags of vLdpNgFec128Flags indicate the characteristics
         of the FEC."
    ::= { vLdpNgSvcFec128Entry 7 }

vLdpNgFec128NumInLabels    OBJECT-TYPE
    SYNTAX      Unsigned32
    MAX-ACCESS  read-only
    STATUS      current
    DESCRIPTION
        "The value of vLdpNgFec128NumInLabels indicates the number of 
         labels that have been sent to the peer associated with this 
         FEC."
    ::= { vLdpNgSvcFec128Entry 8 }

vLdpNgFec128NumOutLabels    OBJECT-TYPE
    SYNTAX      Unsigned32
    MAX-ACCESS  read-only
    STATUS      current
    DESCRIPTION
        "The value of vLdpNgFec128NumOutLabels indicates the number of
         labels that have been received from the peer associated with this
         FEC."
    ::= { vLdpNgSvcFec128Entry 9 }

vLdpNgFec128SdpId    OBJECT-TYPE
    SYNTAX      SdpId                        
    MAX-ACCESS  read-only
    STATUS      current
    DESCRIPTION
        "The value of vLdpNgFec128SdpId identifies the SDP associated
         with this peer."
    ::= { vLdpNgSvcFec128Entry 10 }

vLdpNgFec128MateEndptVcId    OBJECT-TYPE
    SYNTAX      TmnxVcId
    MAX-ACCESS  read-only
    STATUS      current
    DESCRIPTION
        "The value of vLdpNgFec128MateEndptVcId indicates the VC identifier 
         associated with this service FEC mate endpoint for vc-switching."
    ::= { vLdpNgSvcFec128Entry 11 }

vLdpNgFec128MateEndptSdpId    OBJECT-TYPE
    SYNTAX      SdpId                        
    MAX-ACCESS  read-only
    STATUS      current
    DESCRIPTION
        "The value of vLdpNgFec128MateEndptSdpId identifies the SDP
         associated with this service FEC mate endpoint for vc-switching."
    ::= { vLdpNgSvcFec128Entry 12 }

--
--  Alcatel-Lucent SROS series LDP Service FEC In Label Table
--

vLdpNgSvcFec128InLblTable     OBJECT-TYPE
    SYNTAX      SEQUENCE OF VLdpNgSvcFec128InLblEntry 
    MAX-ACCESS  not-accessible
    STATUS      current
    DESCRIPTION
        "The vLdpNgSvcFec128InLblTable is a read-only table that represents 
         all service FEC 128 received from an LDP peer known to the Virtual 
         Router."
    ::= { tmnxLdpNgObjs 23 }

vLdpNgSvcFec128InLblEntry    OBJECT-TYPE
    SYNTAX      VLdpNgSvcFec128InLblEntry
    MAX-ACCESS  not-accessible
    STATUS      current
    DESCRIPTION
        "Each row entry represents an instance of a service FEC received from 
         an LDP peer."
    INDEX  { vRtrID, 
             vLdpNgFec128FecType,
             vLdpNgFec128VcType,
             vLdpNgFec128VcId,
             vRtrLdpNgPeerLdpIdType,
             vRtrLdpNgPeerLdpId,
             vLdpNgFec128InLabelId } 
    ::= { vLdpNgSvcFec128InLblTable 1 }

VLdpNgSvcFec128InLblEntry ::= SEQUENCE {
    vLdpNgFec128InLabelId                Unsigned32,
    vLdpNgFec128InLabel                  Unsigned32,
    vLdpNgFec128InLabelStatus            TmnxLabelStatus,
    vLdpNgFec128InLabelSigStatus         TmnxLabelSigStatus,
    vLdpNgFec128InLblWdwReason           TmnxLdpInLblWdrawalReasonCode,
    vLdpNgFec128InLblMaxCellConcat       Unsigned32,
    vLdpNgFec128InLblFLTxCap             TruthValue,
    vLdpNgFec128InLblFLRxCap             TruthValue,
    vLdpNgFec128InLblIPv4CeIpAdType      InetAddressType,
    vLdpNgFec128InLblIPv4CeIpAddr        InetAddress,
    vLdpNgFec128InLblIPv4Cap             TruthValue,
    vLdpNgFec128InLblIPv6Cap             TruthValue,
    vLdpNgFec128InLblMTU                 Unsigned32,
    vLdpNgFec128InLblVlanTag             Unsigned32,
    vLdpNgFec128InLblVccvCV              BITS,   
    vLdpNgFec128InLblVccvCC              BITS, 
    vLdpNgFec128InLblPwStatus            TruthValue
}

vLdpNgFec128InLabelId     OBJECT-TYPE
    SYNTAX      Unsigned32
    MAX-ACCESS  not-accessible
    STATUS      current
    DESCRIPTION
        "The value of vLdpNgFec128InLabelId identifies the ingress label 
         exchanged."
    ::= { vLdpNgSvcFec128InLblEntry 1 }

vLdpNgFec128InLabel    OBJECT-TYPE
    SYNTAX      Unsigned32
    MAX-ACCESS  read-only
    STATUS      current
    DESCRIPTION
        "The value of vLdpNgFec128InLabel indicates the ingress 
         label exchanged."
    ::= { vLdpNgSvcFec128InLblEntry 2 }

vLdpNgFec128InLabelStatus    OBJECT-TYPE
    SYNTAX      TmnxLabelStatus
    MAX-ACCESS  read-only
    STATUS      current
    DESCRIPTION
        "The value of vLdpNgFec128InLabelStatus indicates the 
         status of the ingress label."
    ::= { vLdpNgSvcFec128InLblEntry 3 }

vLdpNgFec128InLabelSigStatus     OBJECT-TYPE
    SYNTAX      TmnxLabelSigStatus
    MAX-ACCESS  read-only
    STATUS      current
    DESCRIPTION
        "The value of vLdpNgFec128InLabelSigStatus indicates the signaling
         status for vLdpNgFec128InLabel."
    ::= { vLdpNgSvcFec128InLblEntry 4 }

vLdpNgFec128InLblWdwReason    OBJECT-TYPE
    SYNTAX      TmnxLdpInLblWdrawalReasonCode                         
    MAX-ACCESS  read-only
    STATUS      current
    DESCRIPTION
        "The value of vLdpNgFec128InLblWdwReason indicates the reason 
         of withdrawal of ingress label value in vLdpNgFec128InLabel."
    ::= { vLdpNgSvcFec128InLblEntry 5 }

vLdpNgFec128InLblMaxCellConcat    OBJECT-TYPE
    SYNTAX      Unsigned32                       
    MAX-ACCESS  read-only
    STATUS      current
    DESCRIPTION
        "The value of vLdpNgFec128InLblMaxCellConcat indicates the local 
         maximum number of ATM cells to concatenate on a ATM cell-mode VC 
         type SDP binding."
    ::= { vLdpNgSvcFec128InLblEntry 6 }

vLdpNgFec128InLblFLTxCap    OBJECT-TYPE
    SYNTAX      TruthValue
    MAX-ACCESS  read-only
    STATUS      current
    DESCRIPTION
        "The value of vLdpNgFec128InLblFLTxCap indicates whether or not
         this LDP peer is capable of sending Flow Label in its pseudowire (PW)
         packet.
        
         The value of vLdpNgFec128InLblFLTxCap is 'true' when this LDP
         peer is capable of sending Flow Label and the value is 'false' when 
         the peer is not capable of sending Flow Label in pseudowire packet."
    ::= { vLdpNgSvcFec128InLblEntry 7 }

vLdpNgFec128InLblFLRxCap    OBJECT-TYPE
    SYNTAX      TruthValue
    MAX-ACCESS  read-only
    STATUS      current
    DESCRIPTION
        "The value of vLdpNgFec128InLblFLRxCap indicates whether or not
         this LDP peer is capable of receiving Flow Label in its pseudowire
         packet.
        
         The value of vLdpNgFec128InLblFLRxCap is 'true' when this LDP
         peer is capable of receiving Flow Label and the value is 'false' when 
         the peer is not capable of receiving Flow Label in pseudowire packet."
    ::= { vLdpNgSvcFec128InLblEntry 8 }

vLdpNgFec128InLblIPv4CeIpAdType    OBJECT-TYPE
        SYNTAX      InetAddressType                  
        MAX-ACCESS  read-only
        STATUS      current
        DESCRIPTION
            "The value of vLdpNgFec128InLblIPv4CeIpAdType indicates the local 
             ipv4 CE Address type."
        ::= { vLdpNgSvcFec128InLblEntry 9 }

vLdpNgFec128InLblIPv4CeIpAddr    OBJECT-TYPE
    SYNTAX      InetAddress  (SIZE (0|4))                      
    MAX-ACCESS  read-only
    STATUS      current
    DESCRIPTION
        "The value of vLdpNgFec128InLblIPv4CeIpAddr indicates the local ipv4
         CE Address."
    ::= { vLdpNgSvcFec128InLblEntry 10 }

vLdpNgFec128InLblIPv4Cap    OBJECT-TYPE
    SYNTAX      TruthValue                        
    MAX-ACCESS  read-only
    STATUS      current
    DESCRIPTION
        "The value of vLdpNgFec128InLblIPv4Cap indicates whether or not
         the local ipv4 stack capability is supported for this LDP peer.
         
         The value of vLdpNgFec128InLblIPv4Cap is 'true' when the local 
         ipv4 stack capability is supported and the value is 'false' when the
         local ipv4 stack capability is not supported."
    ::= { vLdpNgSvcFec128InLblEntry 11 }

vLdpNgFec128InLblIPv6Cap    OBJECT-TYPE
    SYNTAX      TruthValue                        
    MAX-ACCESS  read-only
    STATUS      current
    DESCRIPTION
        "The value of vLdpNgFec128InLblIPv6Cap indicates whether or not
         the local ipv6 stack capability is supported for this LDP peer.
          
         The value of vLdpNgFec128InLblIPv6Cap is 'true' when the local 
         ipv6 stack capability is supported and the value is 'false' when the
         local ipv6 stack capability is not supported."
    ::= { vLdpNgSvcFec128InLblEntry 12 }

vLdpNgFec128InLblMTU    OBJECT-TYPE
    SYNTAX      Unsigned32                       
    MAX-ACCESS  read-only
    STATUS      current
    DESCRIPTION
        "The value of vLdpNgFec128InLblMTU indicates the largest 
         service frame size (in octets) that can be handled by the 
         local ESR."
    ::= { vLdpNgSvcFec128InLblEntry 13 }

vLdpNgFec128InLblVlanTag    OBJECT-TYPE
    SYNTAX      Unsigned32                       
    MAX-ACCESS  read-only
    STATUS      current
    DESCRIPTION
        "The value of vLdpNgFec128InLblVlanTag indicates the local 
         tag on a VLAN VC type SDP binding."
    ::= { vLdpNgSvcFec128InLblEntry 14 }

vLdpNgFec128InLblVccvCV     OBJECT-TYPE
    SYNTAX      BITS {
        icmpPing                 (0),
        lspPing                  (1),
        bfdFaultDetect           (2),
        bfdFaultDetectSignalling (3)
    }
    MAX-ACCESS  read-only
    STATUS      current
    DESCRIPTION
        "The value of vLdpNgFec128InLblVccvCV indicates the CV (Connectivity
         Verification) types supported by peer LSR if it supports VCCV 
         (Circuit Connectivity Verification) on pseudowire. If VCCV is not
         supported, vLdpNgFec128InLblVccvCV will be set to 0."
    ::= { vLdpNgSvcFec128InLblEntry 15 }

vLdpNgFec128InLblVccvCC     OBJECT-TYPE
    SYNTAX      BITS {
        pwe3ControlWord   (0),
        routerAlertLabel  (1),
        mplsDemuxLabelTL1 (2)
    }
    MAX-ACCESS  read-only
    STATUS      current
    DESCRIPTION
        "The value of vLdpNgFec128InLblVccvCC indicates the CC (Control 
         Channel) types supported by peer LSR if it supports VCCV on pseudowire.
         If VCCV is not supported, vLdpNgFec128InLblVccvCC will be set to 0."
    ::= { vLdpNgSvcFec128InLblEntry 16 }

vLdpNgFec128InLblPwStatus   OBJECT-TYPE
    SYNTAX      TruthValue
    MAX-ACCESS  read-only
    STATUS      current
    DESCRIPTION
        "The value of vLdpNgFec128InLblPwStatus indicates whether the local 
         LSR supports pseudowire status signaling."
    ::= { vLdpNgSvcFec128InLblEntry 17 }

--
--  Alcatel-Lucent SROS series LDP Service FEC Out Label Table
--

vLdpNgSvcFec128OutLblTable     OBJECT-TYPE
    SYNTAX      SEQUENCE OF VLdpNgSvcFec128OutLblEntry 
    MAX-ACCESS  not-accessible
    STATUS      current
    DESCRIPTION
        "The vLdpNgSvcFec128OutLblTable is a read-only table that represents 
         all service FEC 128 sent to an LDP peer known to the Virtual Router." 
    ::= { tmnxLdpNgObjs 24 }

vLdpNgSvcFec128OutLblEntry    OBJECT-TYPE
    SYNTAX      VLdpNgSvcFec128OutLblEntry
    MAX-ACCESS  not-accessible
    STATUS      current
    DESCRIPTION
        "Each row entry represents an instance of a service FEC 128 sent to an 
         LDP peer."
    INDEX  { vRtrID, 
             vLdpNgFec128FecType,
             vLdpNgFec128VcType,
             vLdpNgFec128VcId,
             vRtrLdpNgPeerLdpIdType,
             vRtrLdpNgPeerLdpId,
             vLdpNgFec128OutLabelId } 
    ::= { vLdpNgSvcFec128OutLblTable 1 }

VLdpNgSvcFec128OutLblEntry ::= SEQUENCE {
    vLdpNgFec128OutLabelId              Unsigned32,
    vLdpNgFec128OutLabel                Unsigned32,
    vLdpNgFec128OutLabelStatus          TmnxLabelStatus,
    vLdpNgFec128OutLabelSigStatus       TmnxLabelSigStatus,
    vLdpNgFec128OutLblMaxCellConcat     Unsigned32,
    vLdpNgFec128OutLblFLTxCap           TruthValue,
    vLdpNgFec128OutLblFLRxCap           TruthValue,
    vLdpNgFec128OutLblIPv4CeAddrType    InetAddressType,
    vLdpNgFec128OutLblIPv4CeIpAddr      InetAddress,
    vLdpNgFec128OutLblIPv4Cap           TruthValue,
    vLdpNgFec128OutLblIPv6Cap           TruthValue,
    vLdpNgFec128OutLblMTU               Unsigned32,
    vLdpNgFec128OutLblVlanTag           Unsigned32,
    vLdpNgFec128OutLblVccvCV            BITS,   
    vLdpNgFec128OutLblVccvCC            BITS, 
    vLdpNgFec128OutLblPwStatus          TruthValue
}

vLdpNgFec128OutLabelId     OBJECT-TYPE
    SYNTAX      Unsigned32
    MAX-ACCESS  not-accessible
    STATUS      current
    DESCRIPTION
        "The value of vLdpNgFec128OutLabelId specifies the identifier."
    ::= { vLdpNgSvcFec128OutLblEntry 1 }

vLdpNgFec128OutLabel    OBJECT-TYPE
    SYNTAX      Unsigned32
    MAX-ACCESS  read-only
    STATUS      current
    DESCRIPTION
        "The value of vLdpNgFec128OutLabel indicates the egress
         label exchanged."
    ::= { vLdpNgSvcFec128OutLblEntry 2 }

vLdpNgFec128OutLabelStatus    OBJECT-TYPE
    SYNTAX      TmnxLabelStatus 
    MAX-ACCESS  read-only
    STATUS      current
    DESCRIPTION
        "The value of vLdpNgFec128OutLabelStatus indicates the 
         status of the egress label."
    ::= { vLdpNgSvcFec128OutLblEntry 3 }

vLdpNgFec128OutLabelSigStatus     OBJECT-TYPE
    SYNTAX      TmnxLabelSigStatus
    MAX-ACCESS  read-only
    STATUS      current
    DESCRIPTION
        "The value of vLdpNgFec128OutLabelSigStatus indicates the signaling
         status for vLdpNgFec128OutLabel."
    ::= { vLdpNgSvcFec128OutLblEntry 4 }

vLdpNgFec128OutLblMaxCellConcat    OBJECT-TYPE
    SYNTAX      Unsigned32                       
    MAX-ACCESS  read-only
    STATUS      current
    DESCRIPTION
        "The value of vLdpNgFec128OutLblMaxCellConcat indicates the remote
         maximum number of ATM cells to concatenate on a ATM cell-mode VC 
         type SDP binding."
    ::= { vLdpNgSvcFec128OutLblEntry 5 }

vLdpNgFec128OutLblFLTxCap    OBJECT-TYPE
    SYNTAX      TruthValue
    MAX-ACCESS  read-only
    STATUS      current
    DESCRIPTION
        "The value of vLdpNgFec128OutLblFLTxCap indicates whether or not
         the remote LDP peer is capable of sending Flow Label in its pseudowire
         packet.
        
         The value of vLdpNgFec128OutLblFLTxCap is 'true' when the remote
         LDP peer is capable of sending Flow Label and the value is 'false' when 
         the peer is not capable of sending Flow Label in pseudowire packet."
    ::= { vLdpNgSvcFec128OutLblEntry 6 }

vLdpNgFec128OutLblFLRxCap    OBJECT-TYPE
    SYNTAX      TruthValue
    MAX-ACCESS  read-only
    STATUS      current
    DESCRIPTION
        "The value of vLdpNgFec128OutLblFLRxCap indicates whether or not
         the remote LDP peer is capable of receiving Flow Label in its 
         pseudowire packet.
        
         The value of vLdpNgFec128OutLblFLRxCap is 'true' when the remote
         LDP peer is capable of receiving Flow Label and the value is 'false' 
         when the peer is not capable of receiving Flow Label in pseudowire 
         packet."
    ::= { vLdpNgSvcFec128OutLblEntry 7 }

vLdpNgFec128OutLblIPv4CeAddrType    OBJECT-TYPE
    SYNTAX      InetAddressType                     
    MAX-ACCESS  read-only
    STATUS      current
    DESCRIPTION
        "The value of vLdpNgFec128OutLblIPv4CeAddrType indicates the remote ipv4
         CE Address type."
    ::= { vLdpNgSvcFec128OutLblEntry 8 }

vLdpNgFec128OutLblIPv4CeIpAddr    OBJECT-TYPE
    SYNTAX      InetAddress  (SIZE (0|4))                      
    MAX-ACCESS  read-only
    STATUS      current
    DESCRIPTION
        "The value of vLdpNgFec128OutLblIPv4CeIpAddr indicates the remote ipv4
         CE Address."
    ::= { vLdpNgSvcFec128OutLblEntry 9 }

vLdpNgFec128OutLblIPv4Cap    OBJECT-TYPE
    SYNTAX      TruthValue                        
    MAX-ACCESS  read-only
    STATUS      current
    DESCRIPTION
        "The value of vLdpNgFec128OutLblIPv4Cap indicates whether or not
         the remote ipv4 stack capability is supported for this LDP peer.
          
         The value of vLdpNgFec128OutLblIPv4Cap is 'true' when the remote 
         ipv4 stack capability is supported and the value is 'false' when the
         remote ipv4 stack capability is not supported."
    ::= { vLdpNgSvcFec128OutLblEntry 10 }

vLdpNgFec128OutLblIPv6Cap    OBJECT-TYPE
    SYNTAX      TruthValue                        
    MAX-ACCESS  read-only
    STATUS      current
    DESCRIPTION
        "The value of vLdpNgFec128OutLblIPv6Cap indicates whether or not
         the remote ipv6 stack capability is supported for this LDP peer.
          
         The value of vLdpNgFec128OutLblIPv6Cap is 'true' when the remote 
         ipv6 stack capability is supported and the value is 'false' when the
         remote ipv6 stack capability is not supported."
    ::= { vLdpNgSvcFec128OutLblEntry 11 }

vLdpNgFec128OutLblMTU    OBJECT-TYPE
    SYNTAX      Unsigned32                       
    MAX-ACCESS  read-only
    STATUS      current
    DESCRIPTION
         "The value of vLdpNgFec128OutLblMTU indicates the largest 
         service frame size (in octets) that can be handled by the 
         remote ESR."
    ::= { vLdpNgSvcFec128OutLblEntry 12 }

vLdpNgFec128OutLblVlanTag    OBJECT-TYPE
    SYNTAX      Unsigned32                       
    MAX-ACCESS  read-only
    STATUS      current
    DESCRIPTION
        "The value of vLdpNgFec128OutLblVlanTag indicates the remote
         tag on a VLAN VC type SDP binding."
    ::= { vLdpNgSvcFec128OutLblEntry 13 }

vLdpNgFec128OutLblVccvCV     OBJECT-TYPE
    SYNTAX      BITS {
        icmpPing                 (0),
        lspPing                  (1),
        bfdFaultDetect           (2),
        bfdFaultDetectSignalling (3)
    }
    MAX-ACCESS  read-only
    STATUS      current
    DESCRIPTION
        "The value of vLdpNgFec128OutLblVccvCV indicates the CV (Connectivity
         Verification) types supported by local LSR if it supports VCCV 
         pseudowire. If VCCV is not supported, vLdpNgFec128OutLblVccvCV will 
         be set to 0."
    ::= { vLdpNgSvcFec128OutLblEntry 14 }

vLdpNgFec128OutLblVccvCC     OBJECT-TYPE
    SYNTAX      BITS {
        pwe3ControlWord   (0),
        routerAlertLabel  (1),
        mplsDemuxLabelTL1 (2)
    }
    MAX-ACCESS  read-only
    STATUS      current
    DESCRIPTION
        "The value of vLdpNgFec128OutLblVccvCC indicates the CC (Control
         Channel) types supported by local LSR if it supports VCCV on
         pseudowire. If VCCV is not supported, vLdpNgFec128OutLblVccvCC will 
         be set to 0."  
    ::= { vLdpNgSvcFec128OutLblEntry 15 }

vLdpNgFec128OutLblPwStatus   OBJECT-TYPE
    SYNTAX      TruthValue
    MAX-ACCESS  read-only
    STATUS      current
    DESCRIPTION
        "The value of vLdpNgFec128OutLblPwStatus indicates whether the remote
         LSR supports pseudowire status signaling."
    ::= { vLdpNgSvcFec128OutLblEntry 16 }

--
-- Alcatel-Lucent SROS series Hello Adjacency Mapping Table
--

vRtrLdpNgHelloAdjMapTable    OBJECT-TYPE
    SYNTAX      SEQUENCE OF VRtrLdpNgHelloAdjMapEntry
    MAX-ACCESS  not-accessible
    STATUS      current
    DESCRIPTION
        "The vRtrLdpNgHelloAdjMapTable is a read-only table which maps to the 
         vRtrLdpNgHelloAdjTable. This table has the same indexes as the 
         vRtrLdpNgHelloAdjTable but the order in which these indexes are 
         specified is different for the two tables."
    ::= { tmnxLdpNgObjs 25 }

vRtrLdpNgHelloAdjMapEntry    OBJECT-TYPE
    SYNTAX      VRtrLdpNgHelloAdjMapEntry
    MAX-ACCESS  not-accessible
    STATUS      current
    DESCRIPTION
        "Each row represents a single LDP Hello Adjacency. An LDP Session 
         can have one or more Hello adjacencies."
    INDEX  { vRtrID,
             vRtrLdpNgIfIndex,
             vRtrLdpNgPeerAddressType,
             vRtrLdpNgPeerAddress,
             vRtrLdpNgHelloAdjMapLdpIdType,
             vRtrLdpNgHelloAdjMapLdpId }
    ::= { vRtrLdpNgHelloAdjMapTable 1 }

VRtrLdpNgHelloAdjMapEntry ::= SEQUENCE {
    vRtrLdpNgHelloAdjMapLdpIdType           TmnxMplsLdpNgIdType,
    vRtrLdpNgHelloAdjMapLdpId               TmnxMplsLdpNgIdentifier,
    vRtrLdpNgHelloAdjMapIndex               Unsigned32
}

vRtrLdpNgHelloAdjMapLdpIdType    OBJECT-TYPE
    SYNTAX      TmnxMplsLdpNgIdType
    MAX-ACCESS  not-accessible
    STATUS      current
    DESCRIPTION
        "vRtrLdpNgHelloAdjMapLdpId is an index for the row entry. It indicates
         the LDP identifier type of the peer, indicated by 
         vRtrLdpNgHelloAdjMapLdpId"
    ::= { vRtrLdpNgHelloAdjMapEntry 1 }

vRtrLdpNgHelloAdjMapLdpId    OBJECT-TYPE
    SYNTAX      TmnxMplsLdpNgIdentifier (SIZE (6|18))
    MAX-ACCESS  not-accessible
    STATUS      current
    DESCRIPTION
        "vRtrLdpNgHelloAdjMapLdpId is an index for the row entry. It indicates
         the LDP identifier of the peer."
    ::= { vRtrLdpNgHelloAdjMapEntry 2 }

vRtrLdpNgHelloAdjMapIndex    OBJECT-TYPE
    SYNTAX      Unsigned32 (1..4294967295)
    MAX-ACCESS  read-only
    STATUS      current
    DESCRIPTION
        "The value of vRtrLdpNgHelloAdjMapIndex indicates the Hello adjacency index 
         which is an index for MPLS-LDP-MIB::mplsLdpHelloAdjacencyEntry."
    ::= { vRtrLdpNgHelloAdjMapEntry 3 }   

--
--  Alcatel-Lucent SROS series LDP Service FEC-129 Table
--

vLdpNgSvcFec129Table    OBJECT-TYPE
    SYNTAX      SEQUENCE OF VLdpNgSvcFec129Entry
    MAX-ACCESS  not-accessible
    STATUS      current
    DESCRIPTION
        "The vLdpNgSvcFec129Table is a read-only table that represents all
         service FEC-129s either sent to or received from an LDP peer known
         to the Virtual Router."   
    ::= { tmnxLdpNgObjs 26 }

vLdpNgSvcFec129Entry    OBJECT-TYPE
    SYNTAX      VLdpNgSvcFec129Entry
    MAX-ACCESS  not-accessible
    STATUS      current
    DESCRIPTION
        "Each row entry represents an instance of a service FEC-129 sent to 
         or received from an LDP peer."
    INDEX  { vRtrID,
             vLdpNgFec128VcType,
             vLdpNgFec129AgiType,
             vLdpNgFec129AgiLen,
             vLdpNgFec129AgiVal,
             vLdpNgFec129SrcAiiType,
             vLdpNgFec129SrcAiiLen,
             vLdpNgFec129SrcAiiVal,
             vLdpNgFec129TgtAiiType,
             vLdpNgFec129TgtAiiLen,
             vLdpNgFec129TgtAiiVal,
             vRtrLdpNgPeerLdpIdType,
             vRtrLdpNgPeerLdpId } 
    ::= { vLdpNgSvcFec129Table 1 }

VLdpNgSvcFec129Entry ::= SEQUENCE {
    vLdpNgFec129AgiType               Unsigned32,
    vLdpNgFec129AgiLen                Unsigned32,
    vLdpNgFec129AgiVal                OCTET STRING,
    vLdpNgFec129SrcAiiType            Unsigned32,
    vLdpNgFec129SrcAiiLen             Unsigned32,
    vLdpNgFec129SrcAiiVal             OCTET STRING,
    vLdpNgFec129TgtAiiType            Unsigned32,
    vLdpNgFec129TgtAiiLen             Unsigned32,
    vLdpNgFec129TgtAiiVal             OCTET STRING,
    vLdpNgFec129ServType              ServType,
    vLdpNgFec129ServId                TmnxServId,
    vLdpNgFec129VpnId                 TmnxVpnId,
    vLdpNgFec129Flags                 TmnxLdpFECFlags,
    vLdpNgFec129NumInLabels           Unsigned32,
    vLdpNgFec129NumOutLabels          Unsigned32,   
    vLdpNgFec129SdpId                 SdpId,
    vLdpNgFec129MateAgiType           Unsigned32,
    vLdpNgFec129MateAgiLen            Unsigned32,
    vLdpNgFec129MateAgiVal            OCTET STRING,
    vLdpNgFec129MateSrcAiiType        Unsigned32,
    vLdpNgFec129MateSrcAiiLen         Unsigned32,
    vLdpNgFec129MateSrcAiiVal         OCTET STRING,
    vLdpNgFec129MateTgtAiiType        Unsigned32,
    vLdpNgFec129MateTgtAiiLen         Unsigned32,
    vLdpNgFec129MateTgtAiiVal         OCTET STRING,
    vLdpNgFec129MateSdpId             SdpId
}

vLdpNgFec129AgiType    OBJECT-TYPE
    SYNTAX      Unsigned32 (0..255)
    MAX-ACCESS  not-accessible
    STATUS      current
    DESCRIPTION
        "The value of vLdpNgFec129AgiType specifies the type of the Attachment
         Group Identifier TLV associated with this service FEC."
    ::= { vLdpNgSvcFec129Entry 1 }

vLdpNgFec129AgiLen    OBJECT-TYPE
    SYNTAX      Unsigned32 (0..65535)
    MAX-ACCESS  not-accessible
    STATUS      current
    DESCRIPTION
        "The value of vLdpNgFec129AgiLen specifies the length of the Attachment
         Group Identifier TLV associated with this service FEC."
    ::= { vLdpNgSvcFec129Entry 2 }

vLdpNgFec129AgiVal    OBJECT-TYPE
    SYNTAX      OCTET STRING (SIZE(0..32))
    MAX-ACCESS  not-accessible
    STATUS      current
    DESCRIPTION
        "The value of vLdpNgFec129AgiVal specifies the value of the Attachment 
         Group Identifier TLV associated with this service FEC."
    ::= { vLdpNgSvcFec129Entry 3 }

vLdpNgFec129SrcAiiType    OBJECT-TYPE
    SYNTAX      Unsigned32 (0..255)
    MAX-ACCESS  not-accessible
    STATUS      current
    DESCRIPTION
        "The value of vLdpNgFec129SrcAiiType specifies the type of the Source
         Attachment Individual Identifier TLV associated with this service FEC."
    ::= { vLdpNgSvcFec129Entry 4 }

vLdpNgFec129SrcAiiLen    OBJECT-TYPE
    SYNTAX      Unsigned32 (0..65535)
    MAX-ACCESS  not-accessible
    STATUS      current
    DESCRIPTION
        "The value of vLdpNgFec129SrcAiiLen specifies the length of the Source 
         Attachment Individual Identifier TLV associated with this service FEC."
    ::= { vLdpNgSvcFec129Entry 5 }

vLdpNgFec129SrcAiiVal    OBJECT-TYPE
    SYNTAX      OCTET STRING (SIZE(0..32))
    MAX-ACCESS  not-accessible
    STATUS      current
    DESCRIPTION
        "The value of vLdpNgFec129SrcAiiVal specifies the value of the 
         Source Attachment Individual Identifier TLV associated with this 
         service FEC."
    ::= { vLdpNgSvcFec129Entry 6 }

vLdpNgFec129TgtAiiType    OBJECT-TYPE
    SYNTAX      Unsigned32 (0..255)
    MAX-ACCESS  not-accessible
    STATUS      current
    DESCRIPTION
        "The value of vLdpNgFec129TgtAiiType specifies the type of the Target 
         Attachment Individual Identifier TLV associated with this service FEC."
    ::= { vLdpNgSvcFec129Entry 7 }

vLdpNgFec129TgtAiiLen    OBJECT-TYPE
    SYNTAX      Unsigned32 (0..65535)
    MAX-ACCESS  not-accessible
    STATUS      current
    DESCRIPTION
        "The value of vLdpNgFec129TgtAiiLen specifies the length of the Target
         Attachment Individual Identifier TLV associated with this service FEC."
    ::= { vLdpNgSvcFec129Entry 8 }

vLdpNgFec129TgtAiiVal    OBJECT-TYPE
    SYNTAX      OCTET STRING (SIZE(0..32))
    MAX-ACCESS  not-accessible
    STATUS      current
    DESCRIPTION
        "The value of vLdpNgFec129TgtAiiVal specifies the value of the Target 
         Attachment Individual Identifier TLV associated with this service FEC."
    ::= { vLdpNgSvcFec129Entry 9 }

vLdpNgFec129ServType    OBJECT-TYPE 
    SYNTAX      ServType
    MAX-ACCESS  read-only
    STATUS      current
    DESCRIPTION
        "The value of vLdpNgFec129ServType indicates the Service type
         associated with this service FEC."
    ::= { vLdpNgSvcFec129Entry 10 }

vLdpNgFec129ServId    OBJECT-TYPE
    SYNTAX      TmnxServId (1..2147483647)
    MAX-ACCESS  read-only
    STATUS      current
    DESCRIPTION
        "The value of vLdpNgFec129ServId indicates the Service identifier
         associated with this service FEC."
    ::= { vLdpNgSvcFec129Entry 11 }

vLdpNgFec129VpnId    OBJECT-TYPE
    SYNTAX      TmnxVpnId
    MAX-ACCESS  read-only
    STATUS      current
    DESCRIPTION
        "The value of vLdpNgFec129VpnId identifies the VPN associated 
         with the FEC."
    ::= { vLdpNgSvcFec129Entry 12 }

vLdpNgFec129Flags    OBJECT-TYPE 
    SYNTAX      TmnxLdpFECFlags
    MAX-ACCESS  read-only
    STATUS      current
    DESCRIPTION
        "The value of vLdpNgFec129Flags indicates the characteristics
         of the FEC."
    ::= { vLdpNgSvcFec129Entry 13 }

vLdpNgFec129NumInLabels    OBJECT-TYPE
    SYNTAX      Unsigned32
    MAX-ACCESS  read-only
    STATUS      current
    DESCRIPTION
        "The value of vLdpNgFec129NumInLabels indicates the number of 
         labels that have been sent to the peer associated with this
         FEC."
    ::= { vLdpNgSvcFec129Entry 14 }

vLdpNgFec129NumOutLabels    OBJECT-TYPE
    SYNTAX      Unsigned32
    MAX-ACCESS  read-only
    STATUS      current
    DESCRIPTION
        "The value of vLdpNgFec129NumOutLabels indicates the number of
         labels that have been received from the peer associated with this 
         FEC."
    ::= { vLdpNgSvcFec129Entry 15 }

vLdpNgFec129SdpId    OBJECT-TYPE
    SYNTAX      SdpId                        
    MAX-ACCESS  read-only
    STATUS      current
    DESCRIPTION
        "The value of vLdpNgFec129SdpId indicates the SDP associated
         with this peer."
    ::= { vLdpNgSvcFec129Entry 16 }

vLdpNgFec129MateAgiType    OBJECT-TYPE
    SYNTAX      Unsigned32 (0..255)
    MAX-ACCESS  read-only
    STATUS      current
    DESCRIPTION
        "The value of vLdpNgFec129MateAgiType indicates the type of the 
         Attachment Group Identifier TLV switched with this service FEC."
    ::= { vLdpNgSvcFec129Entry 17 }

vLdpNgFec129MateAgiLen    OBJECT-TYPE
    SYNTAX      Unsigned32 (0..65535)
    MAX-ACCESS  read-only
    STATUS      current
    DESCRIPTION
        "The value of vLdpNgFec129MateAgiLen indicates the length of the 
         Attachment Group Identifier TLV switched with this service FEC."
    ::= { vLdpNgSvcFec129Entry 18 }

vLdpNgFec129MateAgiVal    OBJECT-TYPE
    SYNTAX      OCTET STRING (SIZE(0..32))
    MAX-ACCESS  read-only
    STATUS      current
    DESCRIPTION
        "The value of vLdpNgFec129MateAgiVal indicates the value of the 
         Attachment Group Identifier TLV switched with this service FEC."
    ::= { vLdpNgSvcFec129Entry 19 }

vLdpNgFec129MateSrcAiiType    OBJECT-TYPE
    SYNTAX      Unsigned32 (0..255)
    MAX-ACCESS  read-only
    STATUS      current
    DESCRIPTION
        "The value of vLdpNgFec129MateSrcAiiType indicates the type of the 
         Source Attachment Individual Identifier TLV switched with this service 
         FEC."
    ::= { vLdpNgSvcFec129Entry 20 }

vLdpNgFec129MateSrcAiiLen    OBJECT-TYPE
    SYNTAX      Unsigned32 (0..65535)
    MAX-ACCESS  read-only
    STATUS      current
    DESCRIPTION
        "The value of vLdpNgFec129MateSrcAiiLen indicates the length of the 
         Source Attachment Individual Identifier TLV switched with this service 
         FEC."
    ::= { vLdpNgSvcFec129Entry 21 }

vLdpNgFec129MateSrcAiiVal    OBJECT-TYPE
    SYNTAX      OCTET STRING (SIZE(0..32))
    MAX-ACCESS  read-only
    STATUS      current
    DESCRIPTION
        "The value of vLdpNgFec129MateSrcAiiVal indicates the value of the Source
         Attachment Individual Identifier TLV switched with this service FEC."
    ::= { vLdpNgSvcFec129Entry 22 }

vLdpNgFec129MateTgtAiiType    OBJECT-TYPE
    SYNTAX      Unsigned32 (0..255)
    MAX-ACCESS  read-only
    STATUS      current
    DESCRIPTION
        "The value of vLdpNgFec129MateTgtAiiType indicates the type of the 
         Target Attachment Individual Identifier TLV switched with this service 
         FEC."
    ::= { vLdpNgSvcFec129Entry 23 }

vLdpNgFec129MateTgtAiiLen    OBJECT-TYPE
    SYNTAX      Unsigned32 (0..65535)
    MAX-ACCESS  read-only
    STATUS      current
    DESCRIPTION
        "The value of vLdpNgFec129MateTgtAiiLen indicates the length of the 
         Target Attachment Individual Identifier TLV switched with this service
         FEC."
    ::= { vLdpNgSvcFec129Entry 24 }

vLdpNgFec129MateTgtAiiVal    OBJECT-TYPE
    SYNTAX      OCTET STRING (SIZE(0..32))
    MAX-ACCESS  read-only
    STATUS      current
    DESCRIPTION
        "The value of vLdpNgFec129MateTgtAiiVal indicates the value of the
         Target Attachment Individual Identifier TLV switched with this service
         FEC."
    ::= { vLdpNgSvcFec129Entry 25 }

vLdpNgFec129MateSdpId    OBJECT-TYPE
    SYNTAX      SdpId                        
    MAX-ACCESS  read-only
    STATUS      current
    DESCRIPTION
        "The value of vLdpNgFec129MateSdpId indicates the SDP switched
         with this peer."
    ::= { vLdpNgSvcFec129Entry 26 }

--
--  Alcatel-Lucent SROS series LDP Service FEC-129 In Label Table
--

vLdpNgSvcFec129InLblTable    OBJECT-TYPE
    SYNTAX      SEQUENCE OF VLdpNgSvcFec129InLblEntry
    MAX-ACCESS  not-accessible
    STATUS      current
    DESCRIPTION
        "The vLdpNgSvcFec129InLblTable is a read-only table that represents all
         service FEC-129s received from an LDP peer known
         to the Virtual Router."   
    ::= { tmnxLdpNgObjs 27 }

vLdpNgSvcFec129InLblEntry    OBJECT-TYPE
    SYNTAX      VLdpNgSvcFec129InLblEntry
    MAX-ACCESS  not-accessible
    STATUS      current
    DESCRIPTION
        "Each row entry represents an instance of a service FEC-129 received 
         from an LDP peer."
    INDEX  { vRtrID,
             vLdpNgFec128VcType,
             vLdpNgFec129AgiType,
             vLdpNgFec129AgiLen,
             vLdpNgFec129AgiVal,
             vLdpNgFec129SrcAiiType,
             vLdpNgFec129SrcAiiLen,
             vLdpNgFec129SrcAiiVal,
             vLdpNgFec129TgtAiiType,
             vLdpNgFec129TgtAiiLen,
             vLdpNgFec129TgtAiiVal,
             vRtrLdpNgPeerLdpIdType,
             vRtrLdpNgPeerLdpId,
             vLdpNgFec129InLblId } 
    ::= { vLdpNgSvcFec129InLblTable 1 }

VLdpNgSvcFec129InLblEntry ::= SEQUENCE {
    vLdpNgFec129InLblId              Unsigned32,
    vLdpNgFec129InLabel              Unsigned32,
    vLdpNgFec129InLabelStatus        TmnxLabelStatus,   
    vLdpNgFec129InLblMTU             Unsigned32,
    vLdpNgFec129InLblVlanTag         Unsigned32,
    vLdpNgFec129InLblMaxCellConcat   Unsigned32,
    vLdpNgFec129InLblSigStatus       TmnxLabelSigStatus,
    vLdpNgFec129InLblIPv4Cap         TruthValue,
    vLdpNgFec129InLblIPv6Cap         TruthValue,
    vLdpNgFec129InLblIPv4CeAddrType  InetAddressType,
    vLdpNgFec129InLblIPv4CeIpAddr    InetAddress,
    vLdpNgFec129InLblWdwReason       TmnxLdpInLblWdrawalReasonCode,
    vLdpNgFec129InLblFLTxCap         TruthValue,
    vLdpNgFec129InLblFLRxCap         TruthValue,
    vLdpNgFec129InLblVccvCV          BITS,
    vLdpNgFec129InLblVccvCC          BITS,
    vLdpNgFec129InLblPwStatus        TruthValue 
}

vLdpNgFec129InLblId    OBJECT-TYPE
    SYNTAX      Unsigned32
    MAX-ACCESS  not-accessible
    STATUS      current
    DESCRIPTION
        "The value of vLdpNgFec129InLblId indicates the label number of
         the ingress label exchanged."
    ::= { vLdpNgSvcFec129InLblEntry 1 }

vLdpNgFec129InLabel    OBJECT-TYPE
    SYNTAX      Unsigned32
    MAX-ACCESS  read-only
    STATUS      current
    DESCRIPTION
        "The value of vLdpNgFec129InLabel indicates the ingress label exchanged."
    ::= { vLdpNgSvcFec129InLblEntry 2 }

vLdpNgFec129InLabelStatus    OBJECT-TYPE
    SYNTAX      TmnxLabelStatus
    MAX-ACCESS  read-only
    STATUS      current
    DESCRIPTION
        "The value of vLdpNgFec129InLabelStatus indicates the 
         status of the ingress label."
    ::= { vLdpNgSvcFec129InLblEntry 3 }

vLdpNgFec129InLblMTU    OBJECT-TYPE
    SYNTAX      Unsigned32                       
    MAX-ACCESS  read-only
    STATUS      current
    DESCRIPTION
        "The value of vLdpNgFec129InLblMTU indicates the largest 
         service frame size (in octets) that can be handled by the 
         local ESR."
    ::= { vLdpNgSvcFec129InLblEntry 4 }

vLdpNgFec129InLblVlanTag    OBJECT-TYPE
    SYNTAX      Unsigned32                       
    MAX-ACCESS  read-only
    STATUS      current
    DESCRIPTION
        "The value of vLdpNgFec129InLblVlanTag indicates the local 
         tag on a VLAN VC type SDP binding."
    ::= { vLdpNgSvcFec129InLblEntry 5 }

vLdpNgFec129InLblMaxCellConcat    OBJECT-TYPE
    SYNTAX      Unsigned32                       
    MAX-ACCESS  read-only
    STATUS      current
    DESCRIPTION
        "The value of vLdpNgFec129InLblMaxCellConcat indicates the local 
         maximum number of ATM cells to concatenate on a ATM cell-mode VC 
         type SDP binding."
    ::= { vLdpNgSvcFec129InLblEntry 6 }

vLdpNgFec129InLblSigStatus     OBJECT-TYPE
    SYNTAX      TmnxLabelSigStatus
    MAX-ACCESS  read-only
    STATUS      current
    DESCRIPTION
        "The value of vLdpNgFec129InLblSigStatus indicates the signaling
         status for vLdpNgFec129InLabel."
    ::= { vLdpNgSvcFec129InLblEntry 7 }

vLdpNgFec129InLblIPv4Cap    OBJECT-TYPE
    SYNTAX      TruthValue                        
    MAX-ACCESS  read-only
    STATUS      current
    DESCRIPTION
        "The value of vLdpNgFec129InLblIPv4Cap indicates whether or not
         the local ipv4 stack capability is supported for this LDP peer.
         
         The value of vLdpNgFec129InLblIPv4Cap is 'true' when the local 
         ipv4 stack capability is supported and the value is 'false' when the
         local ipv4 stack capability is not supported."
    ::= { vLdpNgSvcFec129InLblEntry 8 }

vLdpNgFec129InLblIPv6Cap    OBJECT-TYPE
    SYNTAX      TruthValue                        
    MAX-ACCESS  read-only
    STATUS      current
    DESCRIPTION
        "The value of vLdpNgFec129InLblIPv6Cap indicates whether or not
         the local ipv6 stack capability is supported for this LDP peer.
         
         The value of vLdpNgFec129InLblIPv6Cap is 'true' when the local 
         ipv6 stack capability is supported and the value is 'false' when the
         local ipv6 stack capability is not supported."
    ::= { vLdpNgSvcFec129InLblEntry 9 }

vLdpNgFec129InLblIPv4CeAddrType    OBJECT-TYPE
    SYNTAX      InetAddressType                        
    MAX-ACCESS  read-only
    STATUS      current
    DESCRIPTION
        "The value of vLdpNgFec129InLblIPv4CeAddrType indicates the local 
        CE Address type of the object indicated by 
        vLdpNgFec129InLblIPv4CeIpAddr."
    ::= { vLdpNgSvcFec129InLblEntry 10 }

vLdpNgFec129InLblIPv4CeIpAddr    OBJECT-TYPE
    SYNTAX      InetAddress (SIZE (0|4))                      
    MAX-ACCESS  read-only
    STATUS      current
    DESCRIPTION
        "The value of vLdpNgFec129InLblIPv4CeIpAddr indicates the local
         CE Address."
    ::= { vLdpNgSvcFec129InLblEntry 11 }

vLdpNgFec129InLblWdwReason    OBJECT-TYPE
    SYNTAX      TmnxLdpInLblWdrawalReasonCode                         
    MAX-ACCESS  read-only
    STATUS      current
    DESCRIPTION
        "The value of vLdpNgFec129InLblWdwReason indicates the reason 
         of withdrawal of ingress label value in vLdpNgFec129InLabel."
    ::= { vLdpNgSvcFec129InLblEntry 12 }

vLdpNgFec129InLblFLTxCap    OBJECT-TYPE
    SYNTAX      TruthValue
    MAX-ACCESS  read-only
    STATUS      current
    DESCRIPTION
        "The value of vLdpNgFec129InLblFLTxCap indicates whether or not
         this LDP peer is capable of sending Flow Label in its pseudowire (PW)
         packet.

         The value of vLdpNgFec129InLblFLTxCap is 'true' when this LDP
         peer is capable of sending Flow Label and the value is 'false' when 
         the peer is not capable of sending Flow Label in pseudowire packet."
    ::= { vLdpNgSvcFec129InLblEntry 13 }

vLdpNgFec129InLblFLRxCap    OBJECT-TYPE
    SYNTAX      TruthValue
    MAX-ACCESS  read-only
    STATUS      current
    DESCRIPTION
        "The value of vLdpNgFec129InLblFLRxCap indicates whether or not
         this LDP peer is capable of receiving Flow Label in its pseudowire
         packet.

         The value of vLdpNgFec129InLblFLRxCap is 'true' when this LDP
         peer is capable of receiving Flow Label and the value is 'false' when 
         the peer is not capable of receiving Flow Label in pseudowire packet."
    ::= { vLdpNgSvcFec129InLblEntry 14 }

vLdpNgFec129InLblVccvCV    OBJECT-TYPE
    SYNTAX      BITS {
        icmpPing                 (0),
        lspPing                  (1),
        bfdFaultDetect           (2),
        bfdFaultDetectSignalling (3)
    }
    MAX-ACCESS  read-only
    STATUS      current
    DESCRIPTION
        "The value of vLdpNgFec129InLblVccvCV indicates the CV (Connectivity
         Verification) types supported by local LSR if it supports VCCV on
         pseudowire. If VCCV is not supported, vLdpNgFec129InLblVccvCV 
         will be set to 0."
    ::= { vLdpNgSvcFec129InLblEntry 15 }

vLdpNgFec129InLblVccvCC   OBJECT-TYPE
    SYNTAX      BITS {
        pwe3ControlWord   (0),
        routerAlertLabel  (1),
        mplsDemuxLabelTL1 (2)
    }    
    MAX-ACCESS  read-only
    STATUS      current
    DESCRIPTION
        "The value of vLdpNgFec129InLblVccvCC indicates the CC (Control
         Channel) types supported by local LSR if it supports VCCV on
         pseudowire. If VCCV is not supported, vLdpNgFec129InLblVccvCC 
         will be set to 0."
    ::= { vLdpNgSvcFec129InLblEntry 16 }

vLdpNgFec129InLblPwStatus   OBJECT-TYPE
    SYNTAX      TruthValue
    MAX-ACCESS  read-only
    STATUS      current
    DESCRIPTION
        "The value of vLdpNgFec129InLblPwStatus indicates whether the local LSR
         supports pseudowire status signaling."
    ::= { vLdpNgSvcFec129InLblEntry 17 }

--
--  Alcatel-Lucent SROS series LDP Service FEC-129 Out Label Table
--

vLdpNgSvcFec129OutLblTable    OBJECT-TYPE
    SYNTAX      SEQUENCE OF VLdpNgSvcFec129OutLblEntry
    MAX-ACCESS  not-accessible
    STATUS      current
    DESCRIPTION
        "The vLdpNgSvcFec129OutLblTable is a read-only table that represents all
         service FEC-129s sent to an LDP peer known to the Virtual Router."   
    ::= { tmnxLdpNgObjs 28 }

vLdpNgSvcFec129OutLblEntry    OBJECT-TYPE
    SYNTAX      VLdpNgSvcFec129OutLblEntry
    MAX-ACCESS  not-accessible
    STATUS      current
    DESCRIPTION
        "Each row entry represents an instance of a service FEC-129 sent to 
         an LDP peer."
    INDEX  { vRtrID,
             vLdpNgFec128VcType,
             vLdpNgFec129AgiType,
             vLdpNgFec129AgiLen,
             vLdpNgFec129AgiVal,
             vLdpNgFec129SrcAiiType,
             vLdpNgFec129SrcAiiLen,
             vLdpNgFec129SrcAiiVal,
             vLdpNgFec129TgtAiiType,
             vLdpNgFec129TgtAiiLen,
             vLdpNgFec129TgtAiiVal,
             vRtrLdpNgPeerLdpIdType,
             vRtrLdpNgPeerLdpId,
             vLdpNgFec129OutLblId} 
    ::= { vLdpNgSvcFec129OutLblTable 1 }

VLdpNgSvcFec129OutLblEntry ::= SEQUENCE {
    vLdpNgFec129OutLblId              Unsigned32,
    vLdpNgFec129OutLabel              Unsigned32,
    vLdpNgFec129OutLabelStatus        TmnxLabelStatus,   
    vLdpNgFec129OutLblMTU             Unsigned32,
    vLdpNgFec129OutLblVlanTag         Unsigned32,
    vLdpNgFec129OutLblMaxCellConcat   Unsigned32,
    vLdpNgFec129OutLblSigStatus       TmnxLabelSigStatus,
    vLdpNgFec129OutLblIPv4Cap         TruthValue,
    vLdpNgFec129OutLblIPv6Cap         TruthValue,
    vLdpNgFec129OutLblIPv4CeAddrType   InetAddressType,
    vLdpNgFec129OutLblIPv4CeIpAddr     InetAddress,
    vLdpNgFec129OutLblFLTxCap         TruthValue,
    vLdpNgFec129OutLblFLRxCap         TruthValue,
    vLdpNgFec129OutLblVccvCV          BITS,
    vLdpNgFec129OutLblVccvCC          BITS,
    vLdpNgFec129OutLblPwStatus        TruthValue
}

vLdpNgFec129OutLblId    OBJECT-TYPE
    SYNTAX      Unsigned32
    MAX-ACCESS  not-accessible
    STATUS      current
    DESCRIPTION
        "The value of vLdpNgFec129OutLblId indicates the label number of
         the egress label exchanged."
    ::= { vLdpNgSvcFec129OutLblEntry 1 }

vLdpNgFec129OutLabel    OBJECT-TYPE
    SYNTAX      Unsigned32
    MAX-ACCESS  read-only
    STATUS      current
    DESCRIPTION
        "The value of vLdpNgFec129OutLabel indicates the
         egress label exchanged."
    ::= { vLdpNgSvcFec129OutLblEntry 2 }

vLdpNgFec129OutLabelStatus    OBJECT-TYPE
    SYNTAX      TmnxLabelStatus 
    MAX-ACCESS  read-only
    STATUS      current
    DESCRIPTION
        "The value of vLdpNgFec129OutLabelStatus indicates the 
         status of the egress label"
    ::= { vLdpNgSvcFec129OutLblEntry 3 }

vLdpNgFec129OutLblMTU    OBJECT-TYPE
    SYNTAX      Unsigned32                       
    MAX-ACCESS  read-only
    STATUS      current
    DESCRIPTION
        "The value of vLdpNgFec129OutLblMTU indicates the largest 
         service frame size (in octets) that can be handled by the 
         remote ESR."
    ::= { vLdpNgSvcFec129OutLblEntry 4 }

vLdpNgFec129OutLblVlanTag    OBJECT-TYPE
    SYNTAX      Unsigned32                       
    MAX-ACCESS  read-only
    STATUS      current
    DESCRIPTION
        "The value of vLdpNgFec129OutLblVlanTag indicates the remote
         tag on a VLAN VC type SDP binding."
    ::= { vLdpNgSvcFec129OutLblEntry 5 }

vLdpNgFec129OutLblMaxCellConcat    OBJECT-TYPE
    SYNTAX      Unsigned32
    MAX-ACCESS  read-only
    STATUS      current
    DESCRIPTION
        "The value of vLdpNgFec129OutLblMaxCellConcat indicates the remote
         maximum number of ATM cells to concatenate on a ATM cell-mode VC 
         type SDP binding."
    ::= { vLdpNgSvcFec129OutLblEntry 6 }

vLdpNgFec129OutLblSigStatus     OBJECT-TYPE
    SYNTAX      TmnxLabelSigStatus
    MAX-ACCESS  read-only
    STATUS      current
    DESCRIPTION
        "The value of vLdpNgFec129OutLblSigStatus indicates the signaling
         status for vLdpNgFec129OutLabel."
    ::= { vLdpNgSvcFec129OutLblEntry 7 }

vLdpNgFec129OutLblIPv4Cap    OBJECT-TYPE
    SYNTAX      TruthValue                        
    MAX-ACCESS  read-only
    STATUS      current
    DESCRIPTION
        "The value of vLdpNgFec129OutLblIPv4Cap indicates whether or not
         the remote ipv4 stack capability is supported for this LDP peer.
          
         The value of vLdpNgFec129OutLblIPv4Cap is 'true' when the remote 
         ipv4 stack capability is supported and the value is 'false' when the
         remote ipv4 stack capability is not supported."
    ::= { vLdpNgSvcFec129OutLblEntry 8 }

vLdpNgFec129OutLblIPv6Cap    OBJECT-TYPE
    SYNTAX      TruthValue                        
    MAX-ACCESS  read-only
    STATUS      current
    DESCRIPTION
        "The value of vLdpNgFec129OutLblIPv6Cap indicates whether or not
         the remote ipv6 stack capability is supported for this LDP peer.
         
         The value of vLdpNgFec129OutLblIPv6Cap is 'true' when the remote 
         ipv6 stack capability is supported and the value is 'false' when the
         remote ipv6 stack capability is not supported."
    ::= { vLdpNgSvcFec129OutLblEntry 9 }

vLdpNgFec129OutLblIPv4CeAddrType    OBJECT-TYPE
    SYNTAX      InetAddressType                        
    MAX-ACCESS  read-only
    STATUS      current
    DESCRIPTION
        "The value of vLdpNgFec129OutLblIPv4CeAddrType indicates the remote 
        CE Address type of the object indicated by vLdpNgFec129OutLblIPv4CeIpAddr."
    ::= { vLdpNgSvcFec129OutLblEntry 10 }

vLdpNgFec129OutLblIPv4CeIpAddr    OBJECT-TYPE
    SYNTAX      InetAddress (SIZE (0|4))                     
    MAX-ACCESS  read-only
    STATUS      current
    DESCRIPTION
        "The value of vLdpNgFec129OutLblIPv4CeIpAddr indicates the remote
         CE Address."
    ::= { vLdpNgSvcFec129OutLblEntry 11 }

vLdpNgFec129OutLblFLTxCap    OBJECT-TYPE
    SYNTAX      TruthValue
    MAX-ACCESS  read-only
    STATUS      current
    DESCRIPTION
        "The value of vLdpNgFec129OutLblFLTxCap indicates whether or not
         the remote LDP peer is capable of sending Flow Label in its pseudowire
         packet.
 
         The value of vLdpNgFec129OutLblFLTxCap is 'true' when the remote
         LDP peer is capable of sending Flow Label and the value is 'false' when 
         the peer is not capable of sending Flow Label in pseudowire packet."
    ::= { vLdpNgSvcFec129OutLblEntry 12 }

vLdpNgFec129OutLblFLRxCap    OBJECT-TYPE
    SYNTAX      TruthValue
    MAX-ACCESS  read-only
    STATUS      current
    DESCRIPTION
        "The value of vLdpNgFec129OutLblFLRxCap indicates whether or not
         the remote LDP peer is capable of receiving Flow Label in its 
         pseudowire packet.
 
         The value of vLdpNgFec129OutLblFLRxCap is 'true' when the remote
         LDP peer is capable of receiving Flow Label and the value is 'false' when 
         the peer is not capable of receiving Flow Label in pseudowire packet."
    ::= { vLdpNgSvcFec129OutLblEntry 13 }

vLdpNgFec129OutLblVccvCV    OBJECT-TYPE
    SYNTAX      BITS {
        icmpPing                 (0),
        lspPing                  (1),
        bfdFaultDetect           (2),
        bfdFaultDetectSignalling (3)
    }
    MAX-ACCESS  read-only
    STATUS      current
    DESCRIPTION
        "The value of vLdpNgFec129OutLblVccvCV indicates the CV (Connectivity
         Verification) types supported by remote LSR if it supports VCCV on
         pseudowire. If VCCV is not supported, vLdpNgFec129OutLblVccvCV 
         will be set to 0."
    ::= { vLdpNgSvcFec129OutLblEntry 14 }

vLdpNgFec129OutLblVccvCC    OBJECT-TYPE
    SYNTAX      BITS {
        pwe3ControlWord   (0),
        routerAlertLabel  (1),
        mplsDemuxLabelTL1 (2)
    }
    MAX-ACCESS  read-only
    STATUS      current
    DESCRIPTION
        "The value of vLdpNgFec129OutLblVccvCC indicates the CC (Control
         Channel) types supported by remote LSR if it supports VCCV on
         pseudowire. If VCCV is not supported, vLdpNgFec129OutLblVccvCC 
         will be set to 0."
    ::= { vLdpNgSvcFec129OutLblEntry 15 }

vLdpNgFec129OutLblPwStatus   OBJECT-TYPE
    SYNTAX      TruthValue
    MAX-ACCESS  read-only
    STATUS      current
    DESCRIPTION
        "The value of vLdpNgFec129OutLblPwStatus indicates whether the remote
         LSR supports pseudowire status signaling."
    ::= { vLdpNgSvcFec129OutLblEntry 16 }

--
--  Alcatel-Lucent SROS series LDP CEP/TDM FEC In Label Table
--

vLdpNgCepTdmFec128InLblTable    OBJECT-TYPE
    SYNTAX      SEQUENCE OF VLdpNgCepTdmFec128InLblEntry
    MAX-ACCESS  not-accessible
    STATUS      current
    DESCRIPTION
        "The vLdpNgCepTdmFec128InLblTable is a read-only table that represents all 
         CEP/TDM FECs received from an LDP peer known to the Virtual Router.
         The CEP/TDM Sub-TLVs are defined in RFC 4446:

         Parameter Id    Description
         0x04            CEP/TDM Payload Bytes
         0x07            CEP/TDM bit-rate
         0x0B            TDM Options."   
    ::= { tmnxLdpNgObjs 29 }

vLdpNgCepTdmFec128InLblEntry    OBJECT-TYPE
    SYNTAX      VLdpNgCepTdmFec128InLblEntry
    MAX-ACCESS  not-accessible
    STATUS      current
    DESCRIPTION
        "Each row entry represents an instance of a service FEC 128 sent to 
         or received from an LDP peer.
         
         Use of AUGMENTS clause implies a one-to-one dependent relationship
         between the base table, vLdpNgSvcFec128InLblTable, and the augmenting
         table, vLdpNgCepTdmFec128InLblTable.  This in effect extends the
         vLdpNgSvcFec128InLblTable with additional columns.
         
          Creation or deletion of a row in the vLdpNgSvcFec128InLblTable results
          in the same fate for the row in the vLdpNgCepTdmFec128InLblEntry."
    AUGMENTS  { vLdpNgSvcFec128InLblEntry }
    ::= { vLdpNgCepTdmFec128InLblTable 1 }

VLdpNgCepTdmFec128InLblEntry ::= SEQUENCE {
    vLdpNgCepTdmFec128InLblPayldSize         Unsigned32,
    vLdpNgCepTdmFec128InLblBitrate          Unsigned32,
    vLdpNgCepTdmFec128InLblRtpHeader           TruthValue,
    vLdpNgCepTdmFec128InLblDiffTStmp         TruthValue,
    vLdpNgCepTdmFec128InLblSigPkts          TdmOptionsSigPkts,
    vLdpNgCepTdmFec128InLblCasTrunk         TdmOptionsCasTrunkFraming,
    vLdpNgCepTdmFec128InLblTStmpFreq         Unsigned32,
    vLdpNgCepTdmFec128InLblPayldType         Unsigned32,
    vLdpNgCepTdmFec128InLblSsrcId           Unsigned32
}

vLdpNgCepTdmFec128InLblPayldSize  OBJECT-TYPE
    SYNTAX      Unsigned32
    UNITS       "bytes"
    MAX-ACCESS  read-only
    STATUS      current
    DESCRIPTION
        "The value of vLdpNgCepTdmFec128InLblPayldSize indicates the local
         payload size."
    ::= { vLdpNgCepTdmFec128InLblEntry 1 }

vLdpNgCepTdmFec128InLblBitrate  OBJECT-TYPE
    SYNTAX      Unsigned32
    UNITS       "64 Kbits/s"
    MAX-ACCESS  read-only
    STATUS      current
    DESCRIPTION
        "The value of vLdpNgCepTdmFec128InLblBitrate indicates the local
         bitrate."
    ::= { vLdpNgCepTdmFec128InLblEntry 2 }

vLdpNgCepTdmFec128InLblRtpHeader OBJECT-TYPE
    SYNTAX      TruthValue
    MAX-ACCESS  read-only
    STATUS      current
    DESCRIPTION
        "The value of vLdpNgCepTdmFec128InLblRtpHeader indicates the local
         RTP header usage bit."
    ::= { vLdpNgCepTdmFec128InLblEntry 3 }

vLdpNgCepTdmFec128InLblDiffTStmp OBJECT-TYPE
    SYNTAX      TruthValue
    MAX-ACCESS  read-only
    STATUS      current
    DESCRIPTION
        "The value of vLdpNgCepTdmFec128InLblDiffTStmp indicates the local
         differential (or dynamic) timestamping mode bit."
    ::= { vLdpNgCepTdmFec128InLblEntry 4 }

vLdpNgCepTdmFec128InLblSigPkts OBJECT-TYPE
    SYNTAX      TdmOptionsSigPkts
    MAX-ACCESS  read-only
    STATUS      current
    DESCRIPTION
        "The value of vLdpNgCepTdmFec128InLblSigPkts indicates the local
         CE application signalling packets mode."
    ::= { vLdpNgCepTdmFec128InLblEntry 5 }
    
vLdpNgCepTdmFec128InLblCasTrunk OBJECT-TYPE
    SYNTAX      TdmOptionsCasTrunkFraming
    MAX-ACCESS  read-only
    STATUS      current
    DESCRIPTION
        "The value of vLdpNgCepTdmFec128InLblCasTrunk indicates the local
         CE application signalling packets mode."
    ::= { vLdpNgCepTdmFec128InLblEntry 6 }

vLdpNgCepTdmFec128InLblTStmpFreq OBJECT-TYPE
    SYNTAX      Unsigned32
    UNITS       "8 KHz"
    MAX-ACCESS  read-only
    STATUS      current
    DESCRIPTION
        "The value of vLdpNgCepTdmFec128InLblTStmpFreq indicates the local
         CE application signalling packets mode."
    ::= { vLdpNgCepTdmFec128InLblEntry 7 }

vLdpNgCepTdmFec128InLblPayldType OBJECT-TYPE
    SYNTAX      Unsigned32
    MAX-ACCESS  read-only
    STATUS      current
    DESCRIPTION
        "The value of vLdpNgCepTdmFec128InLblPayldType indicates the local
         payload type."
    ::= { vLdpNgCepTdmFec128InLblEntry 8 }

vLdpNgCepTdmFec128InLblSsrcId OBJECT-TYPE
    SYNTAX      Unsigned32
    MAX-ACCESS  read-only
    STATUS      current
    DESCRIPTION
        "The value of vLdpNgCepTdmFec128InLblSsrcId indicates the local
         value of SSRC ID."
    ::= { vLdpNgCepTdmFec128InLblEntry 9 }

--
--  Alcatel-Lucent SROS series LDP CEP/TDM FEC Out Label Table
--

vLdpNgCepTdmFec128OutLblTable    OBJECT-TYPE
    SYNTAX      SEQUENCE OF VLdpNgCepTdmFec128OutLblEntry
    MAX-ACCESS  not-accessible
    STATUS      current
    DESCRIPTION
        "The vLdpNgCepTdmFec128OutLblTable is a read-only table that represents all 
         CEP/TDM FECs sent to an LDP peer known to the Virtual Router.
         The CEP/TDM Sub-TLVs are defined in RFC 4446:

         Parameter Id    Description
         0x04            CEP/TDM Payload Bytes
         0x07            CEP/TDM bit-rate
         0x0B            TDM Options."   
    ::= { tmnxLdpNgObjs 30 }

vLdpNgCepTdmFec128OutLblEntry    OBJECT-TYPE
    SYNTAX      VLdpNgCepTdmFec128OutLblEntry
    MAX-ACCESS  not-accessible
    STATUS      current
    DESCRIPTION
        "Each row entry represents an instance of a service FEC sent to 
         or received from an LDP peer.
         
         Use of AUGMENTS clause implies a one-to-one dependent relationship
         between the base table, vLdpNgSvcFec128OutLblTable, and the augmenting
         table, vLdpNgCepTdmFec128OutLblTable.  This in effect extends the
         vLdpNgSvcFec128OutLblTable with additional columns.
         
          Creation or deletion of a row in the vLdpNgSvcFec128OutLblTable results
          in the same fate for the row in the vLdpNgCepTdmFec128OutLblEntry."
    AUGMENTS  { vLdpNgSvcFec128OutLblEntry }
    ::= { vLdpNgCepTdmFec128OutLblTable 1 }

VLdpNgCepTdmFec128OutLblEntry ::= SEQUENCE {
    vLdpNgCepTdmFec128OutLblPyldSze         Unsigned32,
    vLdpNgCepTdmFec128OutLblBitrate         Unsigned32,
    vLdpNgCepTdmFec128OutLblRtpHdr          TruthValue,
    vLdpNgCepTdmFec128OutLblDfTstmp         TruthValue,
    vLdpNgCepTdmFec128OutLblSigPkts         TdmOptionsSigPkts,
    vLdpNgCepTdmFec128OutLblCasTrnk         TdmOptionsCasTrunkFraming,
    vLdpNgCepTdmFec128OutLblTstmpFq         Unsigned32,
    vLdpNgCepTdmFec128OutLblPyldTyp         Unsigned32,
    vLdpNgCepTdmFec128OutLblSsrcId          Unsigned32
}

vLdpNgCepTdmFec128OutLblPyldSze  OBJECT-TYPE
    SYNTAX      Unsigned32
    UNITS       "bytes"
    MAX-ACCESS  read-only
    STATUS      current
    DESCRIPTION
        "The value of vLdpNgCepTdmFec128OutLblPyldSze indicates the remote
         payload size."
    ::= { vLdpNgCepTdmFec128OutLblEntry 1 }

vLdpNgCepTdmFec128OutLblBitrate  OBJECT-TYPE
    SYNTAX      Unsigned32
    UNITS       "64 Kbits/s"
    MAX-ACCESS  read-only
    STATUS      current
    DESCRIPTION
        "The value of vLdpNgCepTdmFec128OutLblBitrate indicates the remote
         bitrate."
    ::= { vLdpNgCepTdmFec128OutLblEntry 2 }

vLdpNgCepTdmFec128OutLblRtpHdr OBJECT-TYPE
    SYNTAX      TruthValue
    MAX-ACCESS  read-only
    STATUS      current
    DESCRIPTION
        "The value of vLdpNgCepTdmFec128OutLblRtpHdr indicates the remote
         RTP header usage bit."
    ::= { vLdpNgCepTdmFec128OutLblEntry 3 }

vLdpNgCepTdmFec128OutLblDfTstmp OBJECT-TYPE
    SYNTAX      TruthValue
    MAX-ACCESS  read-only
    STATUS      current
    DESCRIPTION
        "The value of vLdpNgCepTdmFec128OutLblDfTstmp indicates the remote
         differential (or dynamic) timestamping mode bit."
    ::= { vLdpNgCepTdmFec128OutLblEntry 4 }

vLdpNgCepTdmFec128OutLblSigPkts OBJECT-TYPE
    SYNTAX      TdmOptionsSigPkts
    MAX-ACCESS  read-only
    STATUS      current
    DESCRIPTION
        "The value of vLdpNgCepTdmFec128OutLblSigPkts indicates the remote
         CE application signalling packets mode."
    ::= { vLdpNgCepTdmFec128OutLblEntry 5 }
    
vLdpNgCepTdmFec128OutLblCasTrnk OBJECT-TYPE
    SYNTAX      TdmOptionsCasTrunkFraming
    MAX-ACCESS  read-only
    STATUS      current
    DESCRIPTION
        "The value of vLdpNgCepTdmFec128OutLblCasTrnk indicates the remote
         CE application signalling packets mode."
    ::= { vLdpNgCepTdmFec128OutLblEntry 6 }

vLdpNgCepTdmFec128OutLblTstmpFq OBJECT-TYPE
    SYNTAX      Unsigned32
    UNITS       "8 KHz"
    MAX-ACCESS  read-only
    STATUS      current
    DESCRIPTION
        "The value of vLdpNgCepTdmFec128OutLblTstmpFq indicates the remote
         CE application signalling packets mode."
    ::= { vLdpNgCepTdmFec128OutLblEntry 7 }

vLdpNgCepTdmFec128OutLblPyldTyp OBJECT-TYPE
    SYNTAX      Unsigned32
    MAX-ACCESS  read-only
    STATUS      current
    DESCRIPTION
        "The value of vLdpNgCepTdmFec128OutLblPyldTyp indicates the remote
         payload type."
    ::= { vLdpNgCepTdmFec128OutLblEntry 8 }

vLdpNgCepTdmFec128OutLblSsrcId OBJECT-TYPE
    SYNTAX      Unsigned32
    MAX-ACCESS  read-only
    STATUS      current
    DESCRIPTION
        "The value of vLdpNgCepTdmFec128OutLblSsrcId indicates the remote
         value of SSRC ID."
    ::= { vLdpNgCepTdmFec128OutLblEntry 9 }

--
--  Alcatel-Lucent SROS series LDP CEP/TDM FEC In Label Table
--

vLdpNgCepTdmFec129InLblTable    OBJECT-TYPE
    SYNTAX      SEQUENCE OF VLdpNgCepTdmFec129InLblEntry
    MAX-ACCESS  not-accessible
    STATUS      current
    DESCRIPTION
        "THe vLdpNgCepTdmFec129InLblTable is a read-only table that represents all 
         CEP/TDM FECs received from an LDP peer known to the Virtual Router.
         The CEP/TDM Sub-TLVs are defined in RFC 4446:

         Parameter Id    Description
         0x04            CEP/TDM Payload Bytes
         0x07            CEP/TDM bit-rate
         0x0B            TDM Options."   
    ::= { tmnxLdpNgObjs 31 }

vLdpNgCepTdmFec129InLblEntry    OBJECT-TYPE
    SYNTAX      VLdpNgCepTdmFec129InLblEntry
    MAX-ACCESS  not-accessible
    STATUS      current
    DESCRIPTION
        "Each row entry represents an instance of a service FEC received from an
         LDP peer.
         
         Use of AUGMENTS clause implies a one-to-one dependent relationship
         between the base table, vLdpNgSvcFec129InLblTable, and the augmenting
         table, vLdpNgCepTdmFec129InLblTable.  This in effect extends the
         vLdpNgSvcFec129InLblTable with additional columns.
         
          Creation or deletion of a row in the vLdpNgSvcFec129InLblTable results
          in the same fate for the row in the VLdpNgCepTdmFec129InLblEntry."
    AUGMENTS  { vLdpNgSvcFec129InLblEntry }
    ::= { vLdpNgCepTdmFec129InLblTable 1 }

VLdpNgCepTdmFec129InLblEntry ::= SEQUENCE {
    vLdpNgCepTdmFec129InLblPayldSize         Unsigned32,
    vLdpNgCepTdmFec129InLblBitrate           Unsigned32,
    vLdpNgCepTdmFec129InLblRtpHeader            TruthValue,
    vLdpNgCepTdmFec129InLblDiffTStmp         TruthValue,
    vLdpNgCepTdmFec129InLblSigPkts           TdmOptionsSigPkts,
    vLdpNgCepTdmFec129InLblCasTrunk          TdmOptionsCasTrunkFraming,
    vLdpNgCepTdmFec129InLblTStmpFreq         Unsigned32,
    vLdpNgCepTdmFec129InLblPayldType         Unsigned32,
    vLdpNgCepTdmFec129InLblSsrcId            Unsigned32
}

vLdpNgCepTdmFec129InLblPayldSize  OBJECT-TYPE
    SYNTAX      Unsigned32
    UNITS       "bytes"
    MAX-ACCESS  read-only
    STATUS      current
    DESCRIPTION
        "The value of vLdpNgCepTdmFec129InLblPayldSize indicates the local
         payload size."
    ::= { vLdpNgCepTdmFec129InLblEntry 1 }

vLdpNgCepTdmFec129InLblBitrate  OBJECT-TYPE
    SYNTAX      Unsigned32
    UNITS       "64 Kbits/s"
    MAX-ACCESS  read-only
    STATUS      current
    DESCRIPTION
        "The value of vLdpNgCepTdmFec129InLblBitrate indicates the local
         bitrate."
    ::= { vLdpNgCepTdmFec129InLblEntry 2 }

vLdpNgCepTdmFec129InLblRtpHeader OBJECT-TYPE
    SYNTAX      TruthValue
    MAX-ACCESS  read-only
    STATUS      current
    DESCRIPTION
        "The value of vLdpNgCepTdmFec129InLblRtpHeader indicates the local
         RTP header usage bit."
    ::= { vLdpNgCepTdmFec129InLblEntry 3 }

vLdpNgCepTdmFec129InLblDiffTStmp OBJECT-TYPE
    SYNTAX      TruthValue
    MAX-ACCESS  read-only
    STATUS      current
    DESCRIPTION
        "The value of vLdpNgCepTdmFec129InLblDiffTStmp indicates the local
         differential (or dynamic) timestamping mode bit."
    ::= { vLdpNgCepTdmFec129InLblEntry 4 }

vLdpNgCepTdmFec129InLblSigPkts OBJECT-TYPE
    SYNTAX      TdmOptionsSigPkts
    MAX-ACCESS  read-only
    STATUS      current
    DESCRIPTION
        "The value of vLdpNgCepTdmFec129InLblSigPkts indicates the local
         CE application signalling packets mode."
    ::= { vLdpNgCepTdmFec129InLblEntry 5 }
         
vLdpNgCepTdmFec129InLblCasTrunk OBJECT-TYPE
    SYNTAX      TdmOptionsCasTrunkFraming
    MAX-ACCESS  read-only
    STATUS      current
    DESCRIPTION
        "The value of vLdpNgCepTdmFec129InLblCasTrunk indicates the local
         CE application signalling packets mode."
    ::= { vLdpNgCepTdmFec129InLblEntry 6 }

vLdpNgCepTdmFec129InLblTStmpFreq OBJECT-TYPE
    SYNTAX      Unsigned32
    UNITS       "8 KHz"
    MAX-ACCESS  read-only
    STATUS      current
    DESCRIPTION
        "The value of vLdpNgCepTdmFec129InLblTStmpFreq indicates the local
         CE application signalling packets mode."
    ::= { vLdpNgCepTdmFec129InLblEntry 7 }

vLdpNgCepTdmFec129InLblPayldType OBJECT-TYPE
    SYNTAX      Unsigned32
    MAX-ACCESS  read-only
    STATUS      current
    DESCRIPTION
        "The value of vLdpNgCepTdmFec129InLblPayldType indicates the local
         payload type."
    ::= { vLdpNgCepTdmFec129InLblEntry 8 }

vLdpNgCepTdmFec129InLblSsrcId OBJECT-TYPE
    SYNTAX      Unsigned32
    MAX-ACCESS  read-only
    STATUS      current
    DESCRIPTION
        "The value of vLdpNgCepTdmFec129InLblSsrcId indicates the local
         value of SSRC ID."
    ::= { vLdpNgCepTdmFec129InLblEntry 9 }

--
--  Alcatel-Lucent SROS series LDP CEP/TDM FEC Out Label Table
--

vLdpNgCepTdmFec129OutLblTable    OBJECT-TYPE
    SYNTAX      SEQUENCE OF VLdpNgCepTdmFec129OutLblEntry
    MAX-ACCESS  not-accessible
    STATUS      current
    DESCRIPTION
        "THe vLdpNgCepTdmFec129OutLblTable is a read-only table that represents 
         all CEP/TDM FECs sent to an LDP peer known to the Virtual Router.
         The CEP/TDM Sub-TLVs are defined in RFC 4446:

         Parameter Id    Description
         0x04            CEP/TDM Payload Bytes
         0x07            CEP/TDM bit-rate
         0x0B            TDM Options."   
    ::= { tmnxLdpNgObjs 32 }

vLdpNgCepTdmFec129OutLblEntry    OBJECT-TYPE
    SYNTAX      VLdpNgCepTdmFec129OutLblEntry
    MAX-ACCESS  not-accessible
    STATUS      current
    DESCRIPTION
        "Each row entry represents an instance of a service FEC sent to an LDP peer.
         
         Use of AUGMENTS clause implies a one-to-one dependent relationship
         between the base table, vLdpNgSvcFec129OutLblTable, and the augmenting
         table, vLdpNgCepTdmFec129OutLblTable.  This in effect extends the
         vLdpNgSvcFec129OutLblTable with additional columns.
         
         Creation or deletion of a row in the vLdpNgSvcFec129OutLblTable results
         in the same fate for the row in the VLdpNgCepTdmFec129OutLblEntry."
    AUGMENTS  { vLdpNgSvcFec129OutLblEntry }
    ::= { vLdpNgCepTdmFec129OutLblTable 1 }

VLdpNgCepTdmFec129OutLblEntry ::= SEQUENCE {
    vLdpNgCepTdmFec129OutLblPyldSize         Unsigned32,
    vLdpNgCepTdmFec129OutLblBitrate          Unsigned32,
    vLdpNgCepTdmFec129OutLblRtpHdr           TruthValue,
    vLdpNgCepTdmFec129OutLblDifTStmp         TruthValue,
    vLdpNgCepTdmFec129OutLblSigPkts          TdmOptionsSigPkts,
    vLdpNgCepTdmFec129OutLblCasTrnk          TdmOptionsCasTrunkFraming,
    vLdpNgCepTdmFec129OutLblTStmpFrq         Unsigned32,
    vLdpNgCepTdmFec129OutLblPyldType         Unsigned32,
    vLdpNgCepTdmFec129OutLblSsrcId           Unsigned32
}

vLdpNgCepTdmFec129OutLblPyldSize  OBJECT-TYPE
    SYNTAX      Unsigned32
    UNITS       "bytes"
    MAX-ACCESS  read-only
    STATUS      current
    DESCRIPTION
        "The value of vLdpNgCepTdmFec129OutLblPyldSize indicates the remote
         payload size."
    ::= { vLdpNgCepTdmFec129OutLblEntry 1 }

vLdpNgCepTdmFec129OutLblBitrate  OBJECT-TYPE
    SYNTAX      Unsigned32
    UNITS       "64 Kbits/s"
    MAX-ACCESS  read-only
    STATUS      current
    DESCRIPTION
        "The value of vLdpNgCepTdmFec129OutLblBitrate indicates the remote
         bitrate."
    ::= { vLdpNgCepTdmFec129OutLblEntry 2 }

vLdpNgCepTdmFec129OutLblRtpHdr OBJECT-TYPE
    SYNTAX      TruthValue
    MAX-ACCESS  read-only
    STATUS      current
    DESCRIPTION
        "The value of vLdpNgCepTdmFec129OutLblRtpHdr indicates the remote
         RTP header usage bit."
    ::= { vLdpNgCepTdmFec129OutLblEntry 3 }

vLdpNgCepTdmFec129OutLblDifTStmp OBJECT-TYPE
    SYNTAX      TruthValue
    MAX-ACCESS  read-only
    STATUS      current
    DESCRIPTION
        "The value of vLdpNgCepTdmFec129OutLblDifTStmp indicates the remote
         differential (or dynamic) timestamping mode bit."
    ::= { vLdpNgCepTdmFec129OutLblEntry 4 }

vLdpNgCepTdmFec129OutLblSigPkts OBJECT-TYPE
    SYNTAX      TdmOptionsSigPkts
    MAX-ACCESS  read-only
    STATUS      current
    DESCRIPTION
        "The value of vLdpNgCepTdmFec129OutLblSigPkts indicates the remote
         CE application signalling packets mode."
    ::= { vLdpNgCepTdmFec129OutLblEntry 5 }

vLdpNgCepTdmFec129OutLblCasTrnk OBJECT-TYPE
    SYNTAX      TdmOptionsCasTrunkFraming
    MAX-ACCESS  read-only
    STATUS      current
    DESCRIPTION
        "The value of vLdpNgCepTdmFec129OutLblCasTrnk indicates the remote
         CE application signalling packets mode."
    ::= { vLdpNgCepTdmFec129OutLblEntry 6 }

vLdpNgCepTdmFec129OutLblTStmpFrq OBJECT-TYPE
    SYNTAX      Unsigned32
    UNITS       "8 KHz"
    MAX-ACCESS  read-only
    STATUS      current
    DESCRIPTION
        "The value of vLdpNgCepTdmFec129OutLblTStmpFrq indicates the remote
         CE application signalling packets mode."
    ::= { vLdpNgCepTdmFec129OutLblEntry 7 }

vLdpNgCepTdmFec129OutLblPyldType OBJECT-TYPE
    SYNTAX      Unsigned32
    MAX-ACCESS  read-only
    STATUS      current
    DESCRIPTION
        "The value of vLdpNgCepTdmFec129OutLblPyldType indicates the remote
         payload type."
    ::= { vLdpNgCepTdmFec129OutLblEntry 8 }

vLdpNgCepTdmFec129OutLblSsrcId OBJECT-TYPE
    SYNTAX      Unsigned32
    MAX-ACCESS  read-only
    STATUS      current
    DESCRIPTION
        "The value of vLdpNgCepTdmFec129OutLblSsrcId indicates the remote
         value of SSRC ID."
    ::= { vLdpNgCepTdmFec129OutLblEntry 9 }

--
--  Alcatel-Lucent SROS series LDP Static Prefix FEC Table
--

vRtrLdpNgStaticFecTableLstCh OBJECT-TYPE
    SYNTAX     TimeStamp
    MAX-ACCESS read-only
    STATUS     current
    DESCRIPTION
        "The value of vRtrLdpNgStaticFecTableLstCh indicates the last
         timestamp when an entry in the vRtrLdpNgStaticFecTable was last changed."
    ::= { tmnxLdpNgObjs 33 }

vRtrLdpNgStaticFecTable    OBJECT-TYPE
    SYNTAX      SEQUENCE OF VRtrLdpNgStaticFecEntry
    MAX-ACCESS  not-accessible
    STATUS      current
    DESCRIPTION
        "The vRtrLdpNgStaticFecTable has an entry for each static prefix FEC
         configured on the virtual router."
    ::= { tmnxLdpNgObjs 34 }

vRtrLdpNgStaticFecEntry    OBJECT-TYPE
    SYNTAX      VRtrLdpNgStaticFecEntry
    MAX-ACCESS  not-accessible
    STATUS      current
    DESCRIPTION
        "Each row entry represents a static prefix FEC configured 
         on the virtual router. 
         
         Entries can be created and deleted via SNMP SET operations
         to vRtrLdpNgStaticFecRowStatus. 

         An entry is created by setting vRtrLdpNgStaticFecRowStatus 
         to 'createAndGo'.

         An entry is deleted by setting vRtrLdpNgStaticFecRowStatus 
         to 'destroy'."
    INDEX  { vRtrID,
             vRtrLdpNgStaticFecIpPrefixType,
             vRtrLdpNgStaticFecIpPrefix,
             vRtrLdpNgStaticFecIpPrefixLen 
    }
    ::= { vRtrLdpNgStaticFecTable 1 }

VRtrLdpNgStaticFecEntry ::= SEQUENCE {
    vRtrLdpNgStaticFecIpPrefixType        InetAddressType,
    vRtrLdpNgStaticFecIpPrefix            InetAddress,
    vRtrLdpNgStaticFecIpPrefixLen         InetAddressPrefixLength,
    vRtrLdpNgStaticFecRowStatus           RowStatus,
    vRtrLdpNgStaticFecNumInLabel          Unsigned32,
    vRtrLdpNgStaticFecNumOutLabel         Unsigned32
}

vRtrLdpNgStaticFecIpPrefixType    OBJECT-TYPE 
    SYNTAX      InetAddressType
    MAX-ACCESS  not-accessible
    STATUS      current
    DESCRIPTION
        "The value of vRtrLdpNgStaticFecIpPrefixType specifies the IP Address  
         Prefix type for the static FEC indicated by vRtrLdpNgStaticFecIpPrefix."
    ::= { vRtrLdpNgStaticFecEntry 1 }

vRtrLdpNgStaticFecIpPrefix    OBJECT-TYPE 
    SYNTAX      InetAddress (SIZE (0|4|16))
    MAX-ACCESS  not-accessible
    STATUS      current
    DESCRIPTION
        "The value of vRtrLdpNgStaticFecIpPrefix specifies the IP Address  
         Prefix for this static FEC."
    ::= { vRtrLdpNgStaticFecEntry 2 }

vRtrLdpNgStaticFecIpPrefixLen    OBJECT-TYPE 
    SYNTAX      InetAddressPrefixLength (0..128) 
    MAX-ACCESS  not-accessible
    STATUS      current
    DESCRIPTION
        "The value of vRtrLdpNgStaticFecIpPrefixLen specifies the IP Address 
         Mask length for this static FEC."
    ::= { vRtrLdpNgStaticFecEntry 3 }

vRtrLdpNgStaticFecRowStatus    OBJECT-TYPE 
    SYNTAX      RowStatus
    MAX-ACCESS  read-create
    STATUS      current
    DESCRIPTION
        "vRtrLdpNgStaticFecRowStatus is used to create, delete or 
         control entries in the vRtrLdpNgStaticFecTable.

         An entry is created by setting vRtrLdpNgStaticFecRowStatus 
         'createAndGo'.

         An entry is deleted by setting vRtrLdpNgStaticFecRowStatus 
         to 'destroy'."
    ::= { vRtrLdpNgStaticFecEntry 4 }

vRtrLdpNgStaticFecNumInLabel    OBJECT-TYPE 
    SYNTAX      Unsigned32
    MAX-ACCESS  read-only
    STATUS      current
    DESCRIPTION
        "The value of vRtrLdpNgStaticFecNumInLabel indicates the number 
         of in labels that are associated with the static prefix 
         FEC represented by this row entry. This is also the number 
         of row entries configured in the vRtrLdpNgStaticFecInLabelTable 
         for this static prefix FEC.

         If the static FEC has no in labels associated with it, 
         this value will be 0."
    ::= { vRtrLdpNgStaticFecEntry 5 }

vRtrLdpNgStaticFecNumOutLabel    OBJECT-TYPE 
    SYNTAX      Unsigned32
    MAX-ACCESS  read-only
    STATUS      current
    DESCRIPTION
        "The value of vRtrLdpNgStaticFecNumOutLabel indicates the number 
         of out labels that are associated with the static prefix 
         FEC represented by this row entry. This is also the number 
         of row entries configured in the vRtrLdpNgStaticFecOutLabelTable 
         for this static prefix FEC.

         If the static FEC has no out labels associated with it, 
         this value will be 0."
    ::= { vRtrLdpNgStaticFecEntry 6 }

--
--  Alcatel-Lucent SROS series LDP Static Prefix FEC In Label Table
--

vRtrLdpNgStaticFecInLabelTable    OBJECT-TYPE
    SYNTAX      SEQUENCE OF VRtrLdpNgStaticFecInLabelEntry
    MAX-ACCESS  not-accessible
    STATUS      current
    DESCRIPTION
        "vRtrLdpNgStaticFecInLabelTable has an entry for each static prefix FEC
         in label configured on the virtual router."
    ::= { tmnxLdpNgObjs 35 }

vRtrLdpNgStaticFecInLabelEntry    OBJECT-TYPE
    SYNTAX      VRtrLdpNgStaticFecInLabelEntry
    MAX-ACCESS  not-accessible
    STATUS      current
    DESCRIPTION
        "Each row entry represents a static prefix FEC in label configured on
         the virtual router. The static prefix FEC corresponding to a in label
         entry must exist as a row entry in the vRtrLdpNgStaticFecTable.
         
         Entries can be created and deleted via SNMP SET operations
         to vRtrLdpNgSFecInLabelRowStatus. 

         An entry is created by setting vRtrLdpNgSFecInLabelRowStatus 
         to 'createAndGo'.

         An entry is deleted by setting vRtrLdpNgSFecInLabelRowStatus 
         to 'destroy'."
    INDEX  { vRtrID, 
             vRtrLdpNgStaticFecIpPrefixType,
             vRtrLdpNgStaticFecIpPrefix,
             vRtrLdpNgStaticFecIpPrefixLen,
             vRtrLdpNgSFecInLabel
           }
    ::= {vRtrLdpNgStaticFecInLabelTable 1 }

VRtrLdpNgStaticFecInLabelEntry ::= SEQUENCE {
    vRtrLdpNgSFecInLabel                  Unsigned32,
    vRtrLdpNgSFecInLabelRowStatus         RowStatus,
    vRtrLdpNgSFecOperInLabel              Unsigned32
}

vRtrLdpNgSFecInLabel    OBJECT-TYPE 
    SYNTAX      Unsigned32 (32..262112 | 4294967295)
    MAX-ACCESS  not-accessible
    STATUS      current
    DESCRIPTION
        "The value of vRtrLdpNgSFecInLabel indicates the label
         that is advertised to the upstream peer. 
        
         The range of vRtrLdpNgSFecInLabel is dynamic and
         depends on the value of vRtrMplsLabelMaxStaticLspLabels.

         If the value of vRtrMplsLabelMaxStaticLspLabels is 0 then 
         vRtrLdpNgSFecInLabel cannot be configured.

         If the value of vRtrMplsLabelMaxStaticLspLabels is 1 then
         vRtrLdpNgSFecInLabel can only be set to 32. 

         The normal range of vRtrLdpNgSFecInLabel starts at 32 and ends at 
         the value of vRtrMplsLabelMaxStaticLspLabels.
         
         If this variable is set to the value of 4294967295, the ingress label 
         will be dynamically assigned by the label manager."
    ::= { vRtrLdpNgStaticFecInLabelEntry 1 }

vRtrLdpNgSFecInLabelRowStatus    OBJECT-TYPE 
    SYNTAX      RowStatus
    MAX-ACCESS  read-create
    STATUS      current
    DESCRIPTION
        "vRtrLdpNgSFecInLabelRowStatus is used to create, delete or 
         control entries in the vRtrLdpNgStaticFecInLabelTable.

         An entry is created by setting vRtrLdpNgSFecInLabelRowStatus 
         to 'createAndGo'.

         An entry is deleted by setting vRtrLdpNgSFecInLabelRowStatus 
         to 'destroy'."
    ::= { vRtrLdpNgStaticFecInLabelEntry 2 }

vRtrLdpNgSFecOperInLabel    OBJECT-TYPE 
    SYNTAX      Unsigned32
    MAX-ACCESS  read-only
    STATUS      current
    DESCRIPTION
        "The value of vRtrLdpNgSFecOperInLabel indicates the 
         actual or operational value of the label that was advertised
         to the upstream peer."
    ::= { vRtrLdpNgStaticFecInLabelEntry 3 }

--
--  Alcatel-Lucent SROS series LDP Static Prefix FEC Out Label Table
--

vRtrLdpNgStaticFecOutLabelTable    OBJECT-TYPE
    SYNTAX      SEQUENCE OF VRtrLdpNgStaticFecOutLabelEntry
    MAX-ACCESS  not-accessible
    STATUS      current
    DESCRIPTION
        "vRtrLdpNgStaticFecOutLabelTable has an entry for each static prefix FEC
         out label configured on the virtual router."
    ::= { tmnxLdpNgObjs 36 }

vRtrLdpNgStaticFecOutLabelEntry    OBJECT-TYPE
    SYNTAX      VRtrLdpNgStaticFecOutLabelEntry
    MAX-ACCESS  not-accessible
    STATUS      current
    DESCRIPTION
        "Each row entry represents a static prefix FEC out label configured on
         the virtual router. The static prefix FEC corresponding to a in label
         entry must exist as a row entry in the vRtrLdpNgStaticFecTable. For
         vRtrLdpNgSFecOutLabelType 'pop' or 'swap' corresponding static FEC
         Prefix row entry must exist in vRtrLdpNgStaticFecInLabelTable
         
         Entries can be created and deleted via SNMP SET operations
         to vRtrLdpNgSFecOutLabelRowStatus. 

         An entry is created by setting vRtrLdpNgSFecOutLabelRowStatus 
         to 'createAndGo'.

         An entry is deleted by setting vRtrLdpNgSFecOutLabelRowStatus 
         to 'destroy'."
    INDEX  { vRtrID, 
             vRtrLdpNgStaticFecIpPrefixType,
             vRtrLdpNgStaticFecIpPrefix,
             vRtrLdpNgStaticFecIpPrefixLen,
             vRtrLdpNgSFecOutLabelType,
             vRtrLdpNgSFecOutLabelIfName,
             vRtrLdpNgSFecOutLabelIpAddrType,
             vRtrLdpNgSFecOutLabelIpAddr
           }
    ::= { vRtrLdpNgStaticFecOutLabelTable 1 }

VRtrLdpNgStaticFecOutLabelEntry ::= SEQUENCE {
    vRtrLdpNgSFecOutLabelType              INTEGER,
    vRtrLdpNgSFecOutLabelIfName            DisplayString,
    vRtrLdpNgSFecOutLabelIpAddrType        InetAddressType,
    vRtrLdpNgSFecOutLabelIpAddr            InetAddress,
    vRtrLdpNgSFecOutLabelRowStatus         RowStatus,
    vRtrLdpNgSFecOutLabel                  Unsigned32
}

vRtrLdpNgSFecOutLabelType    OBJECT-TYPE 
    SYNTAX      INTEGER {
                 unknown (0),
                     pop (1),
                    push (2),
                    swap (3)
                }
    MAX-ACCESS  not-accessible
    STATUS      current
    DESCRIPTION
        "The value of vRtrLdpNgSFecOutLabelType indicates operation type 
         of this FEC."
    ::= { vRtrLdpNgStaticFecOutLabelEntry 1 }

vRtrLdpNgSFecOutLabelIfName    OBJECT-TYPE 
    SYNTAX      DisplayString (SIZE(0..32))
    MAX-ACCESS  not-accessible
    STATUS      current
    DESCRIPTION
        "If vRtrLdpNgSFecOutLabelType is set to 'swap' or 'push', the value 
         of vRtrLdpNgSFecOutLabelIfName indicates the interface name 
         to use for this static fec prefix.

         If vRtrLdpNgSFecOutLabelType is set to 'pop', the value of 
         vRtrLdpNgSFecOutLabelIfName will be a null string."
    ::= { vRtrLdpNgStaticFecOutLabelEntry 2 }

vRtrLdpNgSFecOutLabelIpAddrType    OBJECT-TYPE 
    SYNTAX      InetAddressType
    MAX-ACCESS  not-accessible
    STATUS      current
    DESCRIPTION
        "The value of vRtrLdpNgSFecOutLabelIpAddrType indicates the IP 
         address type for vRtrLdpNgSFecOutLabelIpAddr."
    ::= { vRtrLdpNgStaticFecOutLabelEntry 3 }

vRtrLdpNgSFecOutLabelIpAddr    OBJECT-TYPE 
    SYNTAX      InetAddress (SIZE (0|4|16))
    MAX-ACCESS  not-accessible
    STATUS      current
    DESCRIPTION
         "If vRtrLdpNgSFecOutLabelType is set to 'swap' or 'push', 
          the value of vRtrLdpNgSFecOutLabelIpAddr indicates the IP address 
          of the next-hop.

          If vRtrLdpNgSFecOutLabelType is set to 'pop', the value of 
          vRtrLdpNgSFecOutLabelIpAddr will be 0.0.0.0"
    ::= { vRtrLdpNgStaticFecOutLabelEntry 4 }

vRtrLdpNgSFecOutLabelRowStatus    OBJECT-TYPE 
    SYNTAX      RowStatus
    MAX-ACCESS  read-create
    STATUS      current
    DESCRIPTION
        "vRtrLdpNgSFecOutLabelRowStatus is used to create, delete or 
         control entries in the vRtrLdpNgStaticFecOutLabelTable.

         An entry is created by setting vRtrLdpNgSFecOutLabelRowStatus 
         to 'createAndGo'.  

         An entry is deleted by setting vRtrLdpNgSFecOutLabelRowStatus 
         to 'destroy'."
    ::= { vRtrLdpNgStaticFecOutLabelEntry 5 }

vRtrLdpNgSFecOutLabel   OBJECT-TYPE 
    SYNTAX      Unsigned32 (16..1048575|4294967295)
    MAX-ACCESS  read-create
    STATUS      current
    DESCRIPTION
        "The value of vRtrLdpNgSFecOutLabel specifies the egress
         label associated with this next-hop entry. The LSR will swap
         the incoming label with the configured egress label.

         If the value of vRtrLdpNgSFecOutLabel is set to 4294967295, 
         the LSR will pop the incoming label."
    DEFVAL { 4294967295 }
    ::= { vRtrLdpNgStaticFecOutLabelEntry 6 }

--
--  Alcatel-Lucent SROS series LDP Targetted Peer Table
--

vRtrLdpNgTargPeerTableLstCh OBJECT-TYPE
    SYNTAX     TimeStamp
    MAX-ACCESS read-only
    STATUS     current
    DESCRIPTION
        "The value of vRtrLdpNgTargPeerTableLstCh indicates the last
         timestamp when an entry in the vRtrLdpNgTargPeerTable was last changed."
    ::= { tmnxLdpNgObjs 37 }

vRtrLdpNgTargPeerTable    OBJECT-TYPE
    SYNTAX      SEQUENCE OF VRtrLdpTargPeerEntry
    MAX-ACCESS  not-accessible
    STATUS      current
    DESCRIPTION
        "vRtrLdpNgTargPeerTable provides an entry for each virtual router
         targeted peer configured to be used with the Label Distribution
         Protocol (LDP)."
    ::= { tmnxLdpNgObjs 38 }

vRtrLdpNgTargPeerEntry    OBJECT-TYPE
    SYNTAX      VRtrLdpTargPeerEntry
    MAX-ACCESS  not-accessible
    STATUS      current
    DESCRIPTION
        "Each row entry represents a targeted peer on this virtual router that
         participates in the LDP protocol.

         Row entries can be created or deleted via SNMP SET requests. A row with
         default attribute values is created by setting
         vRtrLdpNgTargPeerRowStatus to 'createAndGo'. A row entry can be
         destroyed by setting vRtrLdpNgTargPeerRowStatus to 'destroy'."

   INDEX  { vRtrID,
            vRtrLdpNgPeerAddressType,
            vRtrLdpNgPeerAddress }
    ::= { vRtrLdpNgTargPeerTable 1 }

VRtrLdpTargPeerEntry ::= SEQUENCE {
    vRtrLdpNgPeerAddressType                InetAddressType,
    vRtrLdpNgPeerAddress                    InetAddress,
    vRtrLdpNgTargPeerRowStatus              RowStatus,
    vRtrLdpNgTargPeerLastChange             TimeStamp,
    vRtrLdpNgTargPeerAdminState             TmnxAdminState,
    vRtrLdpNgTargPeerOperState              TmnxOperState,
    vRtrLdpNgTargPeerUpTime                 TimeInterval,
    vRtrLdpNgTargPeerOperDownReason         TmnxLdpIntTargOperDownReasonCode,
    vRtrLdpNgTargPeerInheritance            Unsigned32,
    vRtrLdpNgTargPeerKAFactor               TmnxLdpKeepAliveFactor,
    vRtrLdpNgTargPeerKATimeout              TmnxLdpNewKeepAliveTimeout,
    vRtrLdpNgTargPeerHelloFactor            TmnxLdpHelloFactor,
    vRtrLdpNgTargPeerHelloTimeout           TmnxLdpNewHelloTimeout,
    vRtrLdpNgTargPeerOprHelloTimeout        TmnxLdpNewHelloTimeout,
    vRtrLdpNgTargPeerHelloReduction         TruthValue,
    vRtrLdpNgTargPeerHelloRdctnFctr         Unsigned32,
    vRtrLdpNgTargPeerBackoffTime            TmnxLdpBackoffTime,
    vRtrLdpNgTargPeerMaxBackoffTime         TmnxLdpBackoffTime,
    vRtrLdpNgTargPeerTunneling              TruthValue,
    vRtrLdpNgTargPeerBfdEnabled             TruthValue,
    vRtrLdpNgTargPeerLsrIfIndex             InterfaceIndexOrZero, 
    vRtrLdpNgTargPeerAutoCreate             TruthValue,
    vRtrLdpNgTargPeerCreator                INTEGER,
    vRtrLdpNgTargPeerTemplName              TNamedItemOrEmpty
}

vRtrLdpNgPeerAddressType    OBJECT-TYPE
    SYNTAX      InetAddressType
    MAX-ACCESS  not-accessible
    STATUS      current
    DESCRIPTION
        "The value of vRtrLdpNgPeerAddressType specifies the address family type
         for vRtrLdpNgPeerAddress."
    ::= { vRtrLdpNgTargPeerEntry 1 }

vRtrLdpNgPeerAddress    OBJECT-TYPE
    SYNTAX      InetAddress (SIZE (0|4|16))
    MAX-ACCESS  not-accessible
    STATUS      current
    DESCRIPTION
        "vRtrLdpNgPeerAddress specifies the targeted peer IP address."
    ::= { vRtrLdpNgTargPeerEntry 2 }

vRtrLdpNgTargPeerRowStatus    OBJECT-TYPE
    SYNTAX      RowStatus
    MAX-ACCESS  read-create
    STATUS      current
    DESCRIPTION
        "vRtrLdpNgTargPeerRowStatus is used to control the creation and deletion
         of rows in the vRtrLdpNgTargPeerTable.

         A row can be created by setting vRtrLdpNgTargPeerRowStatus to
         'createAndGo'.  The agent should assign the default attribute values
         and change the row status to 'active'.

         A row entry can be destroyed by setting vRtrLdpNgTargPeerRowStatus to
         'destroy'."
    ::= { vRtrLdpNgTargPeerEntry 3 }

vRtrLdpNgTargPeerLastChange    OBJECT-TYPE
    SYNTAX      TimeStamp
    MAX-ACCESS  read-only
    STATUS      current
    DESCRIPTION
        "The value of vRtrLdpNgTargPeerLastChange specifies the sysUpTime when
         this row was last modified."
    ::= { vRtrLdpNgTargPeerEntry 4 }
    
vRtrLdpNgTargPeerAdminState    OBJECT-TYPE
    SYNTAX      TmnxAdminState
    MAX-ACCESS  read-create
    STATUS      current
    DESCRIPTION
        "The value of vRtrLdpNgTargPeerAdminState indicates the desired
         administrative state for this LDP targeted peer."
    DEFVAL { inService }
    ::= { vRtrLdpNgTargPeerEntry 5 }

vRtrLdpNgTargPeerOperState    OBJECT-TYPE
    SYNTAX      TmnxOperState
    MAX-ACCESS  read-only
    STATUS      current
    DESCRIPTION
        "The value of vRtrLdpNgTargPeerOperState specifies the current
         operational state of LDP targeted peer."
    ::= { vRtrLdpNgTargPeerEntry 6 }

vRtrLdpNgTargPeerUpTime    OBJECT-TYPE
    SYNTAX       TimeInterval
    MAX-ACCESS   read-only
    STATUS       current
    DESCRIPTION
        "The value of vRtrLdpNgTargPeerUpTime indicates the time, in hundreds of
         seconds, that the targeted peer has been in current operational state
         vRtrLdpNgTargPeerOperState.

         If the value of vRtrLdpNgTargPeerOperState is 'inService (2)', then
         vRtrLdpNgTargPeerUpTime specifies the time that the targeted peer has
         been operationally up.

         If the value of vRtrLdpNgTargPeerOperState is 'outOfService (3)', then
         vRtrLdpNgTargPeerUpTime specifies the time that the targeted peer has
         been operationally down.

         If the value of vRtrLdpNgTargPeerOperState is 'transition (4)', then
         vRtrLdpNgTargPeerUpTime specifies the time that the targeted peer has
         been operationally in transition."
    ::= { vRtrLdpNgTargPeerEntry 7 }

vRtrLdpNgTargPeerOperDownReason    OBJECT-TYPE
    SYNTAX      TmnxLdpIntTargOperDownReasonCode
    MAX-ACCESS  read-only
    STATUS      current
    DESCRIPTION
        "The value of vRtrLdpNgTargPeerOperDownReason specifies the operational
         down reason for targeted peer."
    ::= { vRtrLdpNgTargPeerEntry 8 }

vRtrLdpNgTargPeerInheritance    OBJECT-TYPE
    SYNTAX      Unsigned32 
    MAX-ACCESS  read-create
    STATUS      current
    DESCRIPTION
        "Some writable object in this row that can be configured to inherit its
         value from its corresponding object in the vRtrLdpNgGeneralTable.
         vRtrLdpNgTargPeerInheritance controls whether to inherit the
         operational value of that object, or to use the administratively set
         value.

         Non mask bits will always have value of zero, and any attempt to change
         the value will be silently discarded.

         When the bit for an object has value of one, then the object's
         administrative and operational value are whatever the DEFVAL or most
         recently SET value. The mask bit(s) will be set to one when SET is
         performed on the inherited object(s). Any attempt to set the mask bit
         to one will be silently discarded.

         When the bit for an object is set to zero, then the object's
         administrative and operational value are inherited from the
         corresponding object in vRtrLdpNgGeneralTable.
         
         This object is a bit-mask, with the following positions:
         vRtrLdpNgTargPeerKAFactor         0x1
         vRtrLdpNgTargPeerKATimeout        0x2
         vRtrLdpNgTargPeerHelloFactor      0x4
         vRtrLdpNgTargPeerHelloTimeout     0x8
         vRtrLdpNgTargPeerHelloReduction   0x10
         vRtrLdpNgTargPeerHelloRdctnFctr   0x20"
    DEFVAL { 0 } -- by default inherit everything
    ::= { vRtrLdpNgTargPeerEntry 9 }

vRtrLdpNgTargPeerKAFactor    OBJECT-TYPE
    SYNTAX      TmnxLdpKeepAliveFactor
    MAX-ACCESS  read-create
    STATUS      current
    DESCRIPTION
        "The value of vRtrLdpNgTargPeerKAFactor specifies the value by which the
         keepalive timeout (vRtrLdpNgTargPeerKATimeout) should be divided to
         give the keepalive time i.e. the time interval, in seconds, between LDP
         keepalive messages. LDP keepalive messages are sent to keep the LDP
         session from timing out when no other LDP traffic is being sent between
         the neighbors."
    DEFVAL { 4 }
    ::= { vRtrLdpNgTargPeerEntry 10 }

vRtrLdpNgTargPeerKATimeout    OBJECT-TYPE
    SYNTAX      TmnxLdpNewKeepAliveTimeout
    UNITS       "seconds"
    MAX-ACCESS  read-create
    STATUS      current
    DESCRIPTION
        "The value of vRtrLdpNgTargPeerKATimeout specifies the time
         interval, in seconds, that LDP waits before tearing down a session. If
         no LDP messages are exchanged during this time interval, the LDP
         session is torn down. Generally the value of vRtrLdpNgTargPeerKATimeout 
         is configured to be 3 times the keepalive time (the time interval 
         between successive LDP keepalive messages)."
    DEFVAL { 40 }
    ::= { vRtrLdpNgTargPeerEntry 11 }

vRtrLdpNgTargPeerHelloFactor    OBJECT-TYPE
    SYNTAX      TmnxLdpHelloFactor
    MAX-ACCESS  read-create
    STATUS      current
    DESCRIPTION
        "The value of vRtrLdpNgTargPeerHelloFactor specifies the value by which
         the hello timeout (vRtrLdpNgTargPeerHelloTimeout) should be divided to
         give the hello time i.e. the time interval, in seconds, between LDP
         Hello messages. LDP uses hello messages to discover neighbors and to
         detect loss of connectivity with its neighbors."
    DEFVAL { 3 }
    ::= { vRtrLdpNgTargPeerEntry 12 }

vRtrLdpNgTargPeerHelloTimeout    OBJECT-TYPE
    SYNTAX      TmnxLdpNewHelloTimeout
    UNITS       "seconds"
    MAX-ACCESS  read-create
    STATUS      current
    DESCRIPTION
        "The value of vRtrLdpNgTargPeerHelloTimeout specifies the hello time also
         known as hold time. It is the time interval, in seconds, that LDP waits
         before declaring a neighbor to be down. Hello timeout is local to the
         system and is sent in the hello messages to a neighbor.  Hello timeout
         cannot be set to a value that is less than 3 times the hello time."
    DEFVAL { 45 }
    ::= { vRtrLdpNgTargPeerEntry 13 }

vRtrLdpNgTargPeerOprHelloTimeout  OBJECT-TYPE
    SYNTAX      TmnxLdpNewHelloTimeout (3..65535)
    UNITS       "seconds"
    MAX-ACCESS  read-only
    STATUS      current
    DESCRIPTION
        "The value of vRtrLdpNgTargPeerOprHelloTimeout indicates the operational
         hello time also known as hold time used by the operational targeted
         peer. It is the time interval that LDP waits before declaring a
         neighbor to be down."
    ::= { vRtrLdpNgTargPeerEntry 14 }
    
vRtrLdpNgTargPeerHelloReduction  OBJECT-TYPE
    SYNTAX      TruthValue
    MAX-ACCESS  read-create
    STATUS      current
    DESCRIPTION
        "The value of vRtrLdpNgTargPeerHelloReduction specifies whether hello
         reduction to this targeted peer is enabled or not. If enabled, the
         sender advertises the dampened vRtrLdpNgTargPeerHelloTimeout, to the
         targeted peer after LDP session is established."
    DEFVAL { false }
    ::= { vRtrLdpNgTargPeerEntry 15 }

vRtrLdpNgTargPeerHelloRdctnFctr  OBJECT-TYPE
    SYNTAX      Unsigned32 (3..20)
    MAX-ACCESS  read-create
    STATUS      current
    DESCRIPTION
        "The value of vRtrLdpNgTargPeerHelloRdctnFctr specifies the number of
         hello messages that are sent at consistent
         vRtrLdpNgTargPeerHelloTimeout value before advertising further dampened
         vRtrLdpNgTargPeerHelloTimeout.

         An 'inconsistentValue' error is returned if this object is set when
         vRtrLdpNgTargPeerHelloReduction is disabled."
    DEFVAL { 3 }
    ::= { vRtrLdpNgTargPeerEntry 16 }

vRtrLdpNgTargPeerBackoffTime    OBJECT-TYPE
    SYNTAX      TmnxLdpBackoffTime (1..2592000)
    UNITS       "seconds"
    MAX-ACCESS  read-only
    STATUS      current
    DESCRIPTION
        "The value of vRtrLdpNgTargPeerBackoffTime specifies the initial value
         for the backoff interval.

         The backoff interval is the time, in seconds, that LDP waits after an
         LDP session setup has failed before it attempts to setup the session
         again. After the LDP session startup fails the first time, the backoff
         interval is set to the value of vRtrLdpNgTargPeerBackoffTime.
         Thereafter, if session startup fails again the backoff interval
         increases exponentially."
    ::= { vRtrLdpNgTargPeerEntry 17 }

vRtrLdpNgTargPeerMaxBackoffTime    OBJECT-TYPE
    SYNTAX      TmnxLdpBackoffTime
    UNITS       "seconds"
    MAX-ACCESS  read-only
    STATUS      current
    DESCRIPTION
        "The value of vRtrLdpNgTargPeerMaxBackoffTime specifies the maximum
         value for the backoff interval.

         For each successive failure of the LDP session startup, the backoff
         interval (the time for which the router waits before retrying)
         increases exponentially. If the backoff interval exceeds
         vRtrLdpNgTargPeerMaxBackoffTime, the router will give up trying to
         establish the LDP session. 

         If vRtrLdpNgTargPeerMaxBackoffTime has value of zero (0), then the
         backoff interval does not increase exponentially after the first
         session startup attempt fails. Instead it remains constant and LDP will
         keep retrying to establish a session until it succeeds."
    ::= { vRtrLdpNgTargPeerEntry 18 }

vRtrLdpNgTargPeerTunneling  OBJECT-TYPE
     SYNTAX      TruthValue
     MAX-ACCESS  read-create
     STATUS      current
     DESCRIPTION
         "The value of vRtrLdpNgTargPeerTunneling specifies whether tunneling
          of LDP over tunnels is enabled.  When this object has a value of
          'true', tunneling is enabled.  When its value is 'false', tunneling is
          disabled."
     DEFVAL { false }
    ::= { vRtrLdpNgTargPeerEntry 19 }

vRtrLdpNgTargPeerBfdEnabled  OBJECT-TYPE
     SYNTAX      TruthValue
     MAX-ACCESS  read-create
     STATUS      current
     DESCRIPTION
         "The value of vRtrLdpNgTargPeerBfdEnabled specifies whether BFD
          tracking is enabled to the transport address of this peering session.
          When this object has a value of 'true', BFD tracking is enabled. 
          When its value is 'false', BFD tracking is disabled."
     DEFVAL { false }
    ::= { vRtrLdpNgTargPeerEntry 20 }

vRtrLdpNgTargPeerLsrIfIndex  OBJECT-TYPE
     SYNTAX      InterfaceIndexOrZero 
     MAX-ACCESS  read-create
     STATUS      current
     DESCRIPTION
         "The value of vRtrLdpNgTargPeerLsrIfIndex specifies the local
          interface index that is to be used as source LSR-ID to establish
          targeted hello  adjacency with a LDP peer."
     DEFVAL { 0 }
    ::= { vRtrLdpNgTargPeerEntry 21 }

vRtrLdpNgTargPeerAutoCreate    OBJECT-TYPE
    SYNTAX      TruthValue
    MAX-ACCESS  read-only
    STATUS      current
    DESCRIPTION
        "The value of vRtrLdpNgTargPeerAutoCreate specifies whether or not the
         row entry was automatically created."
    ::= { vRtrLdpNgTargPeerEntry 22 }

vRtrLdpNgTargPeerCreator    OBJECT-TYPE
    SYNTAX      INTEGER {
        manual   (1),
        template (2),
        sdp      (3)
    }
    MAX-ACCESS  read-only
    STATUS      current
    DESCRIPTION
        "The value of vRtrLdpNgTargPeerCreator indicates the creator of this
         row.

         A value of 'manual(1)' indicates the entry is created manually by the
         user.

         A value of 'template(2)' indicates the entry is auto created by
         template configuration.

         A value of 'sdp(3)' indicates the entry is auto created by service
         manager."
    ::= { vRtrLdpNgTargPeerEntry 23 }

vRtrLdpNgTargPeerTemplName    OBJECT-TYPE
    SYNTAX      TNamedItemOrEmpty
    MAX-ACCESS  read-only
    STATUS      current
    DESCRIPTION
        "The value of vRtrLdpNgTargPeerTemplName specifies the template name
         that created this row. This object has valid value when
         vRtrLdpNgTargPeerCreator has value of template."
    ::= { vRtrLdpNgTargPeerEntry 24 }

--
--  Alcatel-Lucent SROS series LDP Targeted Peer Statistics Table
--

vRtrLdpNgTargPeerStatsTable    OBJECT-TYPE
    SYNTAX      SEQUENCE OF VRtrLdpNgTargPeerStatsEntry
    MAX-ACCESS  not-accessible
    STATUS      current
    DESCRIPTION
        "The vRtrLdpNgTargPeerStatsTable is a read-only table. The purpose of this 
         table is to keep statistical information about the Targeted peers on
         the LSR.

         Use of AUGMENTS clause implies a one-to-one dependent relationship
         between the base table, vRtrLdpNgTargPeerTable, and the augmenting
         table, vRtrLdpNgTargPeerStatsTable. This in effect extends the
         vRtrLdpNgTargPeerTable with additional columns. Creation or deletion of
         a row in the vRtrLdpNgTargPeerTable results in the same fate for the
         row in the vRtrLdpNgTargPeerTable."
    ::= { tmnxLdpNgObjs 39 }

vRtrLdpNgTargPeerStatsEntry OBJECT-TYPE
    SYNTAX      VRtrLdpNgTargPeerStatsEntry
    MAX-ACCESS  not-accessible
    STATUS      current
    DESCRIPTION
        "A row in this table contains statistical information about an LDP
        Targeted peer. 

        Some counters contained in a row are for fatal errors received 
        during a former LDP Session associated with this entry. For example,
        an LDP Pdu received on a TCP connection during an LDP Session 
        contains a fatal error.  That error is counted here, because the
        session is terminated.

        If the error is NOT fatal (i.e. and the Session remains), then the
        error is counted in the vRtrLdpNgSessionStatsEntry."
    AUGMENTS  { vRtrLdpNgTargPeerEntry }
    ::= { vRtrLdpNgTargPeerStatsTable 1 }

VRtrLdpNgTargPeerStatsEntry ::= SEQUENCE {
    vRtrLdpNgTargPeerStatExistingAdj                Gauge32
}

vRtrLdpNgTargPeerStatExistingAdj    OBJECT-TYPE
    SYNTAX      Gauge32
    MAX-ACCESS  read-only
    STATUS      current
    DESCRIPTION
        "The value of vRtrLdpNgTargPeerStatExistingAdj indicates a count of the
         total active adjacencies with this targeted peer."
    ::= { vRtrLdpNgTargPeerStatsEntry 1 }

--
--  Alcatel-Lucent SROS series LDP Inet Address Family Interface Table
--

vRtrLdpNgInetIfTableLstCh OBJECT-TYPE
    SYNTAX     TimeStamp
    MAX-ACCESS read-only
    STATUS     current
    DESCRIPTION
        "The value of vRtrLdpNgInetIfTableLstCh indicates the last
         timestamp when an entry in the vRtrLdpNgInetIfTable was last changed."
    ::= { tmnxLdpNgObjs 40 }

vRtrLdpNgInetIfTable    OBJECT-TYPE
    SYNTAX      SEQUENCE OF VRtrLdpInetIfEntry
    MAX-ACCESS  not-accessible
    STATUS      current
    DESCRIPTION
        "vRtrLdpNgInetIfTable provides an entry for each virtual router
         interface configuration to be used with the Label Distribution 
         Protocol (LDP) for a given Inet address family."
    ::= { tmnxLdpNgObjs 41 }

vRtrLdpNgInetIfEntry    OBJECT-TYPE
    SYNTAX      VRtrLdpInetIfEntry
    MAX-ACCESS  not-accessible
    STATUS      current
    DESCRIPTION
        "Each row entry represents an interface on this virtual router 
         that participates in the LDP protocol for a given Inet address 
         family.

         Corresponding interface entry must exist in vRtrLdpNgIfTable before
         creating an entry in this table.

         Row entries can be created or deleted via SNMP SET requests.  A row
         with default attribute values is created by setting
         vRtrLdpNgInetIfRowStatus to 'createAndGo'. A row entry can be destroyed
         by setting vRtrLdpNgInetIfRowStatus to 'destroy'."
   INDEX  { vRtrID,
            vRtrLdpNgIfIndex,
            vRtrLdpNgIfAddrType }
    ::= { vRtrLdpNgInetIfTable 1 }            

VRtrLdpInetIfEntry ::= SEQUENCE {
    vRtrLdpNgIfAddrType               InetAddressType,
    vRtrLdpNgInetIfRowStatus          RowStatus,
    vRtrLdpNgInetIfUpTime             TimeInterval,
    vRtrLdpNgInetIfLastChange         TimeStamp,
    vRtrLdpNgInetIfAdminState         TmnxAdminState,
    vRtrLdpNgInetIfOperState          TmnxOperState,
    vRtrLdpNgInetIfOperDownReason     TmnxLdpIntTargOperDownReasonCode,
    vRtrLdpNgInetIfInheritance        INTEGER, 
    vRtrLdpNgInetIfKAFactor           TmnxLdpKeepAliveFactor,
    vRtrLdpNgInetIfKATimeout          TmnxLdpNewKeepAliveTimeout,
    vRtrLdpNgInetIfHelloFactor        TmnxLdpHelloFactor,
    vRtrLdpNgInetIfHelloTimeout       TmnxLdpNewHelloTimeout,
    vRtrLdpNgInetIfOperHelloTimeout   TmnxLdpNewHelloTimeout,
    vRtrLdpNgInetIfBackoffTime        TmnxLdpBackoffTime,
    vRtrLdpNgInetIfMaxBackoffTime     TmnxLdpBackoffTime,
    vRtrLdpNgInetIfTransAddrType      INTEGER,
    vRtrLdpNgInetIfLsrIfType          INTEGER,
    vRtrLdpNgInetIfLsrIfIndex         InterfaceIndexOrZero,
    vRtrLdpNgInetIfIPv4P2MPFecCap     TmnxEnabledDisabled,
    vRtrLdpNgInetIfIPv6P2MPFecCap     TmnxEnabledDisabled,
    vRtrLdpNgInetIfIPv4PfxFecCap      TmnxEnabledDisabled,
    vRtrLdpNgInetIfIPv6PfxFecCap      TmnxEnabledDisabled
    }

vRtrLdpNgIfAddrType    OBJECT-TYPE
    SYNTAX      InetAddressType
    MAX-ACCESS  not-accessible
    STATUS      current
    DESCRIPTION
        "vRtrLdpNgIfAddrType indicates the Inet address family of this
         interface."
    ::= { vRtrLdpNgInetIfEntry 1 }
    
vRtrLdpNgInetIfRowStatus    OBJECT-TYPE
    SYNTAX      RowStatus
    MAX-ACCESS  read-create
    STATUS      current
    DESCRIPTION
        "vRtrLdpNgInetIfRowStatus is used to control the creation and deletion
         of rows in the vRtrLdpNgInetIfTable.

         A row can be created by setting vRtrLdpNgIfRowStatus to 'createAndGo'.
         The agent should assign the default attribute values and change the row
         status to 'active'. Corresponding interface entry must exit in
         vRtrLdpNgIfTable before creating an entry in this table.

         A row entry can be destroyed by setting vRtrLdpNgInetIfRowStatus to
         'destroy'."
    ::= { vRtrLdpNgInetIfEntry 2 }

vRtrLdpNgInetIfUpTime    OBJECT-TYPE
    SYNTAX       TimeInterval
    MAX-ACCESS   read-only
    STATUS       current
    DESCRIPTION
        "The value of vRtrLdpNgInetIfUpTime indicates the time, in hundreds of
         seconds, that the LDP interface has been in current operational state
         vRtrLdpNgIfOperState.

         If the value of vRtrLdpNgIfOperState is 'inService (2)', then
         vRtrLdpNgInetIfUpTime specifies the time that the LDP interface has
         been operationally up.

         If the value of vRtrLdpNgIfOperState is 'outOfService (3)', then
         vRtrLdpNgInetIfUpTime specifies the time that the LDP interface has
         been operationally down.

         If the value of vRtrLdpNgIfOperState is 'transition (4)', then
         vRtrLdpNgInetIfUpTime specifies the time that the LDP interface has
         been operationally in transition."
    ::= { vRtrLdpNgInetIfEntry 3 }

vRtrLdpNgInetIfLastChange    OBJECT-TYPE
    SYNTAX      TimeStamp
    MAX-ACCESS  read-only
    STATUS      current
    DESCRIPTION
        "The value of vRtrLdpNgInetIfLastChange specifies the sysUpTime when
         this row was last modified."
    ::= { vRtrLdpNgInetIfEntry 4 }
    
vRtrLdpNgInetIfAdminState    OBJECT-TYPE
    SYNTAX      TmnxAdminState
    MAX-ACCESS  read-create
    STATUS      current
    DESCRIPTION
        "The value of vRtrLdpNgInetIfAdminState indicates the desired
         administrative state for this interface."
    DEFVAL { inService }
    ::= { vRtrLdpNgInetIfEntry 5 }

vRtrLdpNgInetIfOperState    OBJECT-TYPE
    SYNTAX      TmnxOperState
    MAX-ACCESS  read-only
    STATUS      current
    DESCRIPTION
        "The value of vRtrLdpNgInetIfOperState specifies the current operational
         state of this interface."
    ::= { vRtrLdpNgInetIfEntry 6 }

vRtrLdpNgInetIfOperDownReason    OBJECT-TYPE
    SYNTAX      TmnxLdpIntTargOperDownReasonCode
    MAX-ACCESS  read-only
    STATUS      current
    DESCRIPTION
        "The value of vRtrLdpNgInetIfOperDownReason specifies the reason that the
         LDP interface is operationally down."
    ::= { vRtrLdpNgInetIfEntry 7 }

vRtrLdpNgInetIfInheritance    OBJECT-TYPE
    SYNTAX      INTEGER  
    MAX-ACCESS  read-create
    STATUS      current
    DESCRIPTION
        "Some writable object in this row that can be configured to inherit its
         value from its corresponding object in the vRtrLdpNgGeneralTable.
         vRtrLdpIfInheritance controls whether to inherit the operational value
         of that object, or use the administratively set value.

         Non mask bits will always have value of zero, and any attempt to change
         the value will be silently discarded.

         When the bit for an object has value of one, then the object's
         administrative and operational value are whatever the DEFVAL or most
         recently SET value. The mask bit(s) will be set to one when set is
         performed on the inherited object(s). Any attempt to set the mask bit
         to one will be silently discarded.

         When the bit for an object is set to zero, then the object's
         administrative and operational value are inherited from the
         corresponding object in vRtrLdpNgGeneralTable.
         
         This object is a bit-mask, with the following positions:
         vRtrLdpNgInetIfKAFactor        0x1
         vRtrLdpNgInetIfKATimeout       0x2
         vRtrLdpNgInetIfHelloFactor     0x4
         vRtrLdpNgInetIfHelloTimeout    0x8
         vRtrLdpNgInetIfTransAddrType   0x10"
    DEFVAL { 0 } -- by default inherit everything
    ::= { vRtrLdpNgInetIfEntry 8 }

vRtrLdpNgInetIfKAFactor    OBJECT-TYPE
    SYNTAX      TmnxLdpKeepAliveFactor
    MAX-ACCESS  read-create
    STATUS      current
    DESCRIPTION
        "The value of vRtrLdpNgInetIfKAFactor specifies the value by which the
         keepalive timeout (vRtrLdpNgInetIfKATimeout) should be divided to give
         the keepalive time i.e. the time interval, in seconds, between LDP
         keepalive messages. LDP keepalive messages are sent to keep the LDP
         session from timing out when no other LDP traffic is being sent between
         the neighbors."
    DEFVAL { 3 }
    ::= { vRtrLdpNgInetIfEntry 9 }

vRtrLdpNgInetIfKATimeout    OBJECT-TYPE
    SYNTAX      TmnxLdpNewKeepAliveTimeout
    UNITS       "seconds"
    MAX-ACCESS  read-create
    STATUS      current
    DESCRIPTION
        "The value of vRtrLdpNgInetIfKATimeout specifies the time interval, in
         seconds, that LDP waits before tearing down a session. If no LDP
         messages are exchanged during this time interval, the LDP session is
         torn down. Generally the value of vRtrLdpNgInetIfKATimeout is
         configured to be 3 times the keepalive time (the time interval between
         successive LDP keepalive messages)."
    DEFVAL { 30 }
    ::= { vRtrLdpNgInetIfEntry 10 }

vRtrLdpNgInetIfHelloFactor    OBJECT-TYPE
    SYNTAX      TmnxLdpHelloFactor
    MAX-ACCESS  read-create
    STATUS      current
    DESCRIPTION
        "The value of vRtrLdpNgInetIfHelloFactor specifies the value by which
         the hello timeout (vRtrLdpNgInetIfHelloTimeout) should be divided to
         give the hello time i.e. the time interval, in seconds, between LDP
         Hello messages. LDP uses hello messages to discover neighbors and to
         detect loss of connectivity with its neighbors."
    DEFVAL { 3 }
    ::= { vRtrLdpNgInetIfEntry 11 }

vRtrLdpNgInetIfHelloTimeout    OBJECT-TYPE
    SYNTAX      TmnxLdpNewHelloTimeout
    UNITS       "seconds"
    MAX-ACCESS  read-create
    STATUS      current
    DESCRIPTION
        "The value of vRtrLdpNgInetIfHelloTimeout specifies the hello time also
         known as hold time. It is the time interval, in seconds, that LDP waits
         before declaring a neighbor to be down. Hello timeout is local to the
         system and is sent in the hello messages to a neighbor. Hello timeout
         cannot be set to a value that is less than 3 times the hello time."
    DEFVAL { 15 }
    ::= { vRtrLdpNgInetIfEntry 12 }

vRtrLdpNgInetIfOperHelloTimeout  OBJECT-TYPE
    SYNTAX      TmnxLdpNewHelloTimeout (3..65535)
    UNITS       "seconds"
    MAX-ACCESS  read-only
    STATUS      current
    DESCRIPTION
        "The value of vRtrLdpNgInetIfOperHelloTimeout indicates the operational
         hello time also known as hold time used by the operational LDP
         interface. It is the time interval that LDP waits before declaring a
         neighbor to be down."
    ::= { vRtrLdpNgInetIfEntry 13 }

vRtrLdpNgInetIfBackoffTime    OBJECT-TYPE
    SYNTAX      TmnxLdpBackoffTime (1..2592000)
    UNITS       "seconds"
    MAX-ACCESS  read-only
    STATUS      current
    DESCRIPTION
        "The value of vRtrLdpNgInetIfBackoffTime indicates the initial value for
         the backoff interval.

         The backoff interval is the time, in seconds, that LDP waits after an
         LDP session setup has failed before it attempts to setup the session
         again. After the LDP session startup fails the first time, the backoff
         interval is set to the value of vRtrLdpNgInetIfBackoffTime. Thereafter, if
         session startup fails again the backoff interval increases exponentially."
    ::= { vRtrLdpNgInetIfEntry 14 }

vRtrLdpNgInetIfMaxBackoffTime    OBJECT-TYPE
    SYNTAX      TmnxLdpBackoffTime
    UNITS       "seconds"
    MAX-ACCESS  read-only
    STATUS      current
    DESCRIPTION
        "The value of vRtrLdpNgInetIfMaxBackoffTime specifies the maximum value
         for the backoff interval.

         For each successive failure of the LDP session startup, the backoff
         interval (the time for which the router waits before retrying)
         increases exponentially. If the backoff interval exceeds
         vRtrLdpNgInetIfMaxBackoffTime, the router will give up trying to establish
         the LDP session."
    ::= { vRtrLdpNgInetIfEntry 15 }

vRtrLdpNgInetIfTransAddrType    OBJECT-TYPE
    SYNTAX      INTEGER {
                    interface (1),
                    system    (2)
                }
    MAX-ACCESS  read-create
    STATUS      current
    DESCRIPTION
       "The value of vRtrLdpNgInetIfTransAddrType specifies the source of
        the transport address to be used when setting up the LDP TCP sessions.

        The interface's IP address is used to setup the LDP session between
        neighbors. If multiple interfaces exist between two neighbors, the
        'interface' mode cannot be used since only one LDP session is actually
        set up between the two neighbors.

        When the value of this object is 'system', the system's IP address is
        used to set up the LDP session between neighbors."
    DEFVAL { system }
    ::= { vRtrLdpNgInetIfEntry 16 }

vRtrLdpNgInetIfLsrIfType  OBJECT-TYPE
     SYNTAX      INTEGER {
                     system(1),
                     interface(2)
                 }

     MAX-ACCESS  read-create
     STATUS      current
     DESCRIPTION
         "The value of vRtrLdpNgInetIfLsrIfType specifies whether the local
          interface address or the system interface address should be used as
          source Label Switch Router identifier (LSR-ID) to establish a link LDP
          adjacency with a LDP peer"
     DEFVAL { system }
    ::= { vRtrLdpNgInetIfEntry 17 }

vRtrLdpNgInetIfLsrIfIndex  OBJECT-TYPE
     SYNTAX      InterfaceIndexOrZero 
     MAX-ACCESS  read-create
     STATUS      current
     DESCRIPTION
         "The value of vRtrLdpNgInetIfLsrIfIndex specifies the local interface
          index that is to be used as source LSR-ID to establish link hello
          adjacency with a LDP peer."
     DEFVAL { 0 }
    ::= { vRtrLdpNgInetIfEntry 18 }

vRtrLdpNgInetIfIPv4P2MPFecCap  OBJECT-TYPE
     SYNTAX      TmnxEnabledDisabled 
     MAX-ACCESS  read-create
     STATUS      current
     DESCRIPTION
         "The value of vRtrLdpNgInetIfIPv4P2MPFecCap specifies whether traffic 
         exchange for IPv4 P2MP FECs is enabled or disabled on this interface."
     DEFVAL { enabled } 
    ::= { vRtrLdpNgInetIfEntry 19 }

vRtrLdpNgInetIfIPv6P2MPFecCap  OBJECT-TYPE
     SYNTAX      TmnxEnabledDisabled 
     MAX-ACCESS  read-create
     STATUS      current
     DESCRIPTION
         "The value of vRtrLdpNgInetIfIPv6P2MPFecCap specifies whether traffic 
         exchange for IPv6 P2MP FECs is enabled or disabled on this interface."
     DEFVAL { enabled } 
    ::= { vRtrLdpNgInetIfEntry 20 }

vRtrLdpNgInetIfIPv4PfxFecCap  OBJECT-TYPE
     SYNTAX      TmnxEnabledDisabled
     MAX-ACCESS  read-create
     STATUS      current
     DESCRIPTION
         "The value of vRtrLdpNgInetIfIPv4PfxFecCap specifies whether traffic 
         exchange for IPv4 prefix FECs is enabled or disabled on this interface."
     DEFVAL { enabled } 
    ::= { vRtrLdpNgInetIfEntry 21 }

vRtrLdpNgInetIfIPv6PfxFecCap  OBJECT-TYPE
     SYNTAX      TmnxEnabledDisabled 
     MAX-ACCESS  read-create
     STATUS      current
     DESCRIPTION
         "The value of vRtrLdpNgInetIfIPv6PfxFecCap specifies whether traffic 
         exchange for IPv6 prefix FECs is enabled or disabled this interface."
     DEFVAL { enabled }
    ::= { vRtrLdpNgInetIfEntry 22 }

-- 
--  LDP Statistics table
--

vLdpNgStatsTable    OBJECT-TYPE
    SYNTAX      SEQUENCE OF VLdpNgStatsEntry
    MAX-ACCESS  not-accessible
    STATUS      current
    DESCRIPTION
        "vLdpNgStatsTable is a read-only table. The purpose of this table
         is to keep statistical information about an LDP Instance.

         Use of AUGMENTS clause implies a one-to-one dependent
         relationship between the base table, vRtrLdpNgGeneralTable,
         and the augmenting table, vLdpNgStatsTable. This in
         effect extends the vRtrLdpNgGeneralTable with additional
         columns.  Creation or deletion of a row in the 
         vRtrLdpNgGeneralTable results in the same fate for the row 
         in the vLdpNgStatsTable."
    ::= { tmnxLdpNgObjs 42 }

vLdpNgStatsEntry OBJECT-TYPE
    SYNTAX      VLdpNgStatsEntry
    MAX-ACCESS  not-accessible
    STATUS      current
    DESCRIPTION
        "A row in this table represents statistical information about
         an LDP instance."
    AUGMENTS  { vRtrLdpNgGeneralEntry }
    ::= { vLdpNgStatsTable 1 }

VLdpNgStatsEntry ::= SEQUENCE {
    vLdpNgStatsOperDownEvents                  Counter32,  
    vLdpNgStatsIPv4ActiveSess                  Gauge32,
    vLdpNgStatsIPv6ActiveSess                  Gauge32,
    vLdpNgStatsIPv4ActiveLinkAdj               Gauge32,
    vLdpNgStatsIPv6ActiveLinkAdj               Gauge32,
    vLdpNgStatsIPv4ActiveTargAdj               Gauge32,
    vLdpNgStatsIPv6ActiveTargAdj               Gauge32,
    vLdpNgStatsIPv4ActiveIf                    Gauge32,
    vLdpNgStatsIPv6ActiveIf                    Gauge32,
    vLdpNgStatsIPv4InactiveIf                  Gauge32,
    vLdpNgStatsIPv6InactiveIf                  Gauge32,
    vLdpNgStatsIPv4ActiveTargPeers             Gauge32,
    vLdpNgStatsIPv6ActiveTargPeers             Gauge32,
    vLdpNgStatsIPv4InactiveTargPeers           Gauge32,
    vLdpNgStatsIPv6InactiveTargPeers           Gauge32,
    vLdpNgStatsIPv4PfxFecRecv                  Gauge32,
    vLdpNgStatsIPv6PfxFecRecv                  Gauge32,  
    vLdpNgStatsIPv4PfxFecSent                  Gauge32,
    vLdpNgStatsIPv6PfxFecSent                  Gauge32,
    vLdpNgStatsFec128FecSent                   Gauge32,
    vLdpNgStatsFec128FecRecv                   Gauge32,  
    vLdpNgStatsFec129FecSent                   Gauge32,
    vLdpNgStatsFec129FecRecv                   Gauge32,
    vLdpNgStatsIPv4AttemptedSessions           Counter32,
    vLdpNgStatsIPv6AttemptedSessions           Counter32,
    vLdpNgStatsSessRejNoHelloErrs              Counter32,
    vLdpNgStatsSessRejAdvErrors                Counter32,
    vLdpNgStatsSessRejMaxPduErrs               Counter32,
    vLdpNgStatsSessRejLblRngeErrs              Counter32,
    vLdpNgStatsBadLdpIdErrors                  Counter32,
    vLdpNgStatsBadPduLengthErrors              Counter32,
    vLdpNgStatsBadMsgLengthErrors              Counter32,
    vLdpNgStatsBadTlvLengthErrors              Counter32,
    vLdpNgStatsMalformedTlvErrors              Counter32,
    vLdpNgStatsKeepAliveExpErrors              Counter32,
    vLdpNgStatsShutdownNotifRecv               Counter32,
    vLdpNgStatsShutdownNotifSent               Counter32,
    vLdpNgStatsIPv4EgrFecPfxCount              Counter32,
    vLdpNgStatsIPv6EgrFecPfxCount              Counter32,
    vLdpNgStatsUnknownTlvErrors                Counter32, 
    vLdpNgStatsIPv4P2MPFecSent                 Gauge32,
    vLdpNgStatsIPv6P2MPFecSent                 Gauge32,  
    vLdpNgStatsIPv4P2MPFecRecv                 Gauge32,
    vLdpNgStatsIPv6P2MPFecRecv                 Gauge32,
    vLdpNgStatsIPv4PfxFecOLSessSent            Gauge32,
    vLdpNgStatsIPv6PfxFecOLSessSent            Gauge32,
    vLdpNgStatsIPv4PfxFecOLSessRecv            Gauge32,
    vLdpNgStatsIPv6PfxFecOLSessRecv            Gauge32,
    vLdpNgStatsIPv4P2MPFecOLSessSent           Gauge32,
    vLdpNgStatsIPv6P2MPFecOLSessSent           Gauge32,
    vLdpNgStatsIPv4P2MPFecOLSessRecv           Gauge32,
    vLdpNgStatsIPv6P2MPFecOLSessRecv           Gauge32,
    vLdpNgStatsFec128FecOLSessSent             Gauge32,
    vLdpNgStatsFec128FecOLSessRecv             Gauge32,
    vLdpNgStatsFec129FecOLSessSent             Gauge32,
    vLdpNgStatsFec129FecOLSessRecv             Gauge32,
    vLdpNgStatsIPv4OLoadInterfaces             Gauge32,
    vLdpNgStatsIPv6OLoadInterfaces             Gauge32,
    vLdpNgStatsIPv4OLoadTargPeers              Gauge32,
    vLdpNgStatsIPv6OLoadTargPeers              Gauge32,
    vLdpNgStatsIPv4PfxFecInOLoad               Gauge32,
    vLdpNgStatsIPv6PfxFecInOLoad               Gauge32,
    vLdpNgStatsIPv4P2MPFecInOLoad              Gauge32,
    vLdpNgStatsIPv6P2MPFecInOLoad              Gauge32,
    vLdpNgStatsFec128FecInOLoad                Gauge32,
    vLdpNgStatsFec129FecInOLoad                Gauge32
}

vLdpNgStatsOperDownEvents    OBJECT-TYPE
    SYNTAX      Counter32
    MAX-ACCESS  read-only
    STATUS      current
    DESCRIPTION
        "The value of vLdpNgStatsOperDownEvents specifies the number 
         of times the LDP instance has gone operationally down since
         the instance was created."
    ::= { vLdpNgStatsEntry 1 }

vLdpNgStatsIPv4ActiveSess    OBJECT-TYPE
    SYNTAX      Gauge32
    MAX-ACCESS  read-only
    STATUS      current
    DESCRIPTION
        "The value of vLdpNgStatsIPv4ActiveSess specifies the number
         of active IPv4 sessions (i.e. session in some form of creation) 
         associated with the LDP instance."
    ::= { vLdpNgStatsEntry 2 }

vLdpNgStatsIPv6ActiveSess    OBJECT-TYPE
    SYNTAX      Gauge32
    MAX-ACCESS  read-only
    STATUS      current
    DESCRIPTION
        "The value of vLdpNgStatsIPv6ActiveSess specifies the number
         of active IPv6 sessions (i.e. session in some form of creation) 
         associated with the LDP instance."
    ::= { vLdpNgStatsEntry 3 }

vLdpNgStatsIPv4ActiveLinkAdj    OBJECT-TYPE
    SYNTAX      Gauge32
    MAX-ACCESS  read-only
    STATUS      current
    DESCRIPTION
        "The value of vLdpNgStatsIPv4ActiveLinkAdj specifies the 
         number of active IPv4 link adjacencies (i.e. established adjacencies)
         associated with the LDP instance."
    ::= { vLdpNgStatsEntry 4 }

vLdpNgStatsIPv6ActiveLinkAdj    OBJECT-TYPE
    SYNTAX      Gauge32
    MAX-ACCESS  read-only
    STATUS      current
    DESCRIPTION
        "The value of vLdpNgStatsIPv6ActiveLinkAdj specifies the 
         number of active IPv6 link adjacencies (i.e. established adjacencies)
         associated with the LDP instance."
    ::= { vLdpNgStatsEntry 5 }
    
vLdpNgStatsIPv4ActiveTargAdj    OBJECT-TYPE
    SYNTAX      Gauge32
    MAX-ACCESS  read-only
    STATUS      current
    DESCRIPTION
        "The value of vLdpNgStatsIPv4ActiveTargAdj specifies the 
         number of active IPv4 target adjacencies (i.e. established sessions)
         associated with the LDP instance."
    ::= { vLdpNgStatsEntry 6 }

vLdpNgStatsIPv6ActiveTargAdj    OBJECT-TYPE
    SYNTAX      Gauge32
    MAX-ACCESS  read-only
    STATUS      current
    DESCRIPTION
        "The value of vLdpNgStatsIPv6ActiveTargAdj specifies the 
         number of active IPv6 target adjacencies (i.e. established sessions)
         associated with the LDP instance."
    ::= { vLdpNgStatsEntry 7 } 

vLdpNgStatsIPv4ActiveIf    OBJECT-TYPE
    SYNTAX      Gauge32
    MAX-ACCESS  read-only
    STATUS      current
    DESCRIPTION
        "The value of vLdpNgStatsIPv4ActiveIf specifies the 
         number of active (i.e. operationally up) IPv4 interfaces
         associated with the LDP instance."
    ::= { vLdpNgStatsEntry 8 }

vLdpNgStatsIPv6ActiveIf    OBJECT-TYPE
    SYNTAX      Gauge32
    MAX-ACCESS  read-only
    STATUS      current
    DESCRIPTION
        "The value of vLdpNgStatsIPv6ActiveIf specifies the 
         number of active (i.e. operationally up) IPv6 interfaces
         associated with the LDP instance."
    ::= { vLdpNgStatsEntry 9 }

vLdpNgStatsIPv4InactiveIf    OBJECT-TYPE
    SYNTAX      Gauge32
    MAX-ACCESS  read-only
    STATUS      current
    DESCRIPTION
        "The value of vLdpNgStatsIPv4InactiveIf specifies the
         number of inactive (i.e. operationally down) IPv4 interfaces
         associated with the LDP instance."
    ::= { vLdpNgStatsEntry 10 }

vLdpNgStatsIPv6InactiveIf    OBJECT-TYPE
    SYNTAX      Gauge32
    MAX-ACCESS  read-only
    STATUS      current
    DESCRIPTION
        "The value of vLdpNgStatsIPv6InactiveIf specifies the
         number of inactive (i.e. operationally down) IPv6 interfaces
         associated with the LDP instance."
    ::= { vLdpNgStatsEntry 11 }

vLdpNgStatsIPv4ActiveTargPeers    OBJECT-TYPE
    SYNTAX      Gauge32
    MAX-ACCESS  read-only
    STATUS      current
    DESCRIPTION
        "The value of vLdpNgStatsIPv4ActiveTargPeers specifies 
         the number of configured IPv4 targeted peers that are 
         administratively up in an LDP instance."
    ::= { vLdpNgStatsEntry 12 }

vLdpNgStatsIPv6ActiveTargPeers    OBJECT-TYPE
    SYNTAX      Gauge32
    MAX-ACCESS  read-only
    STATUS      current
    DESCRIPTION
        "The value of vLdpNgStatsIPv6ActiveTargPeers specifies 
         the number of configured IPv6 targeted peers that are 
         administratively up in an LDP instance."
    ::= { vLdpNgStatsEntry 13 }

vLdpNgStatsIPv4InactiveTargPeers    OBJECT-TYPE
    SYNTAX      Gauge32
    MAX-ACCESS  read-only
    STATUS      current
    DESCRIPTION
        "The value of vLdpNgStatsIPv4InactiveTargPeers specifies the
         number of inactive (i.e. operationally down) IPv4 targeted 
         sessions associated with the LDP instance."
    ::= { vLdpNgStatsEntry 14 }

vLdpNgStatsIPv6InactiveTargPeers    OBJECT-TYPE
    SYNTAX      Gauge32
    MAX-ACCESS  read-only
    STATUS      current
    DESCRIPTION
        "The value of vLdpNgStatsIPv6InactiveTargPeers specifies the
         number of inactive (i.e. operationally down) IPv6 targeted 
         sessions associated with the LDP instance."
    ::= { vLdpNgStatsEntry 15 }

vLdpNgStatsIPv4PfxFecRecv    OBJECT-TYPE
    SYNTAX      Gauge32
    MAX-ACCESS  read-only
    STATUS      current
    DESCRIPTION
        "The value of vLdpNgStatsIPv4PfxFecRecv specifies the number of
         IPv4 Address FECs received by the LDP instance from its neighbors."
    ::= { vLdpNgStatsEntry 16 }

vLdpNgStatsIPv6PfxFecRecv    OBJECT-TYPE
    SYNTAX      Gauge32
    MAX-ACCESS  read-only
    STATUS      current
    DESCRIPTION
        "The value of vLdpNgStatsIPv6PfxFecRecv specifies the number of
         IPv6 Address FECs received by the LDP instance from its neighbors."
    ::= { vLdpNgStatsEntry 17 }

vLdpNgStatsIPv4PfxFecSent    OBJECT-TYPE
    SYNTAX      Gauge32
    MAX-ACCESS  read-only
    STATUS      current
    DESCRIPTION
        "The value of vLdpNgStatsIPv4PfxFecSent specifies the number of
         IPv4 Address FECs sent by the LDP instance to its neighbors."
    ::= { vLdpNgStatsEntry 18 }
    
vLdpNgStatsIPv6PfxFecSent    OBJECT-TYPE
    SYNTAX      Gauge32
    MAX-ACCESS  read-only
    STATUS      current
    DESCRIPTION
        "The value of vLdpNgStatsIPv6PfxFecSent specifies the number of
         IPv6 Address FECs sent by the LDP instance to its neighbors."
    ::= { vLdpNgStatsEntry 19 }

vLdpNgStatsFec128FecSent    OBJECT-TYPE
    SYNTAX      Gauge32
    MAX-ACCESS  read-only
    STATUS      current
    DESCRIPTION
        "The value of vLdpNgStatsFec128FecSent specifies the number of
         Pseudo wire ID FECs sent by the LDP instance to its neighbors."
    ::= { vLdpNgStatsEntry 20 }

vLdpNgStatsFec128FecRecv    OBJECT-TYPE
    SYNTAX      Gauge32
    MAX-ACCESS  read-only
    STATUS      current
    DESCRIPTION
        "The value of vLdpNgStatsFec128FecRecv specifies the number of
         Pseudo wire ID FECs received by the LDP instance from its neighbors."
    ::= { vLdpNgStatsEntry 21 }

vLdpNgStatsFec129FecSent    OBJECT-TYPE
    SYNTAX      Gauge32
    MAX-ACCESS  read-only
    STATUS      current
    DESCRIPTION
        "The value of vLdpNgStatsFec129FecSent specifies the number of
         General Pseudo wire ID FECs sent by the LDP instance to its neighbors."
    ::= { vLdpNgStatsEntry 22 }

vLdpNgStatsFec129FecRecv    OBJECT-TYPE
    SYNTAX      Gauge32
    MAX-ACCESS  read-only
    STATUS      current
    DESCRIPTION
        "The value of vLdpNgStatsFec129FecRecv specifies the number of
         General Pseudo wire ID FECs received by the LDP instance from its 
         neighbors."
    ::= { vLdpNgStatsEntry 23 }

vLdpNgStatsIPv4AttemptedSessions    OBJECT-TYPE
    SYNTAX      Counter32
    MAX-ACCESS  read-only
    STATUS      current
    DESCRIPTION
        "The value of vLdpNgStatsIPv4AttemptedSessions specifies the total number 
         of attempted IPv4 sessions for this LDP instance."
    ::= { vLdpNgStatsEntry 24 }
    
vLdpNgStatsIPv6AttemptedSessions    OBJECT-TYPE
    SYNTAX      Counter32
    MAX-ACCESS  read-only
    STATUS      current
    DESCRIPTION
        "The value of vLdpNgStatsIPv6AttemptedSessions specifies the total number 
         of attempted IPv6 sessions for this LDP instance."
    ::= { vLdpNgStatsEntry 25 }

vLdpNgStatsSessRejNoHelloErrs    OBJECT-TYPE
    SYNTAX      Counter32
    MAX-ACCESS  read-only
    STATUS      current
    DESCRIPTION
        "The value of vLdpNgStatsSessRejNoHelloErrs gives the total
         number of Session Rejected/No Hello Error Notification Messages
         sent or received by this LDP instance."
    ::= { vLdpNgStatsEntry 26 }

vLdpNgStatsSessRejAdvErrors    OBJECT-TYPE
    SYNTAX      Counter32
    MAX-ACCESS  read-only
    STATUS      current
    DESCRIPTION
        "The value of vLdpNgStatsSessRejAdvErrors gives the total
         number of Session Rejected/Parameters Advertisement Mode Error
         Notification Messages sent or received by this LDP instance."
    ::= { vLdpNgStatsEntry 27 }

vLdpNgStatsSessRejMaxPduErrs    OBJECT-TYPE
    SYNTAX      Counter32
    MAX-ACCESS  read-only
    STATUS      current
    DESCRIPTION
        "The value of vLdpNgStatsSessRejMaxPduErrs gives the total
         number of Session Rejected/Parameters Max Pdu Length Error 
         Notification Messages sent or received by this LDP instance."
    ::= { vLdpNgStatsEntry 28 }

vLdpNgStatsSessRejLblRngeErrs    OBJECT-TYPE
    SYNTAX      Counter32
    MAX-ACCESS  read-only
    STATUS      current
    DESCRIPTION
        "The value of vLdpNgStatsSessRejLblRngeErrs gives the total
         number of Session Rejected/Parameters Label Range Error 
         Notification Messages sent or received by this LDP instance."
    ::= { vLdpNgStatsEntry 29 }

vLdpNgStatsBadLdpIdErrors    OBJECT-TYPE
    SYNTAX      Counter32
    MAX-ACCESS  read-only
    STATUS      current
    DESCRIPTION
        "The value of vLdpNgStatsBadLdpIdErrors gives the number of
         Bad LDP Identifier Fatal Errors detected for sessions associated
         with this LDP instance."
    REFERENCE
       "LDP Specification, Section 3.5.1.2."
    ::= { vLdpNgStatsEntry 30}

vLdpNgStatsBadPduLengthErrors    OBJECT-TYPE
    SYNTAX      Counter32
    MAX-ACCESS  read-only
    STATUS      current
    DESCRIPTION
        "The value of vLdpNgStatsBadPduLengthErrors gives the number of 
         Bad Pdu Length Fatal Errors detected for sessions associated  
         with this LDP instance."
    REFERENCE
       "LDP Specification, Section 3.5.1.2."
    ::= { vLdpNgStatsEntry 31 }

vLdpNgStatsBadMsgLengthErrors    OBJECT-TYPE
    SYNTAX      Counter32
    MAX-ACCESS  read-only
    STATUS      current
    DESCRIPTION
        "The value of vLdpNgStatsBadMsgLengthErrors gives the number of
         Bad Message Length Fatal Errors detected for sessions associated 
         with this LDP instance."
    REFERENCE
       "LDP Specification, Section 3.5.1.2."
    ::= { vLdpNgStatsEntry 32 }

vLdpNgStatsBadTlvLengthErrors    OBJECT-TYPE
    SYNTAX      Counter32
    MAX-ACCESS  read-only
    STATUS      current
    DESCRIPTION
        "The value of vLdpNgStatsBadTlvLengthErrors gives the number of
         Bad TLV Length Fatal Errors detected for sessions associated  
         with this LDP instance."
    REFERENCE
       "LDP Specification, Section 3.5.1.2."
    ::= { vLdpNgStatsEntry 33 }

vLdpNgStatsMalformedTlvErrors    OBJECT-TYPE
    SYNTAX      Counter32
    MAX-ACCESS  read-only
    STATUS      current
    DESCRIPTION
        "The value of vLdpNgStatsMalformedTlvErrors gives the number of
         Malformed TLV Value Fatal Errors detected for sessions associated
         with this LDP instance."
    REFERENCE
       "LDP Specification, Section 3.5.1.2."
    ::= { vLdpNgStatsEntry 34 }

vLdpNgStatsKeepAliveExpErrors    OBJECT-TYPE
    SYNTAX      Counter32
    MAX-ACCESS  read-only
    STATUS      current
    DESCRIPTION
       "The value of vLdpNgStatsKeepAliveExpErrors gives the number of
        Session Keep Alive Timer Expired Errors detected for sessions 
        associated with this LDP instance."
    REFERENCE
       "LDP Specification, Section 3.5.1.2."
    ::= { vLdpNgStatsEntry 35 }

vLdpNgStatsShutdownNotifRecv    OBJECT-TYPE
    SYNTAX      Counter32
    MAX-ACCESS  read-only
    STATUS      current
    DESCRIPTION
       "The value of vLdpNgStatsShutdownNotifRecv gives the number of
        Shutdown Notifications received related to sessions associated 
        with this LDP instance."
    ::= { vLdpNgStatsEntry 36 }

vLdpNgStatsShutdownNotifSent    OBJECT-TYPE
    SYNTAX      Counter32
    MAX-ACCESS  read-only
    STATUS      current
    DESCRIPTION
       "The value of vLdpNgStatsShutdownNotifSent gives the number of
        Shutdown Notifications sent related to sessions associated with 
        this LDP instance."
    ::= { vLdpNgStatsEntry 37 }

vLdpNgStatsIPv4EgrFecPfxCount    OBJECT-TYPE
    SYNTAX      Counter32
    MAX-ACCESS  read-only
    STATUS      current
    DESCRIPTION
       "The value of vLdpNgStatsIPv4EgrFecPfxCount indicates the number of
        IPv4 egress FEC prefix statistics configured for this LDP instance."  
    ::= { vLdpNgStatsEntry 38 }

vLdpNgStatsIPv6EgrFecPfxCount    OBJECT-TYPE
    SYNTAX      Counter32
    MAX-ACCESS  read-only
    STATUS      current
    DESCRIPTION
       "The value of vLdpNgStatsIPv6EgrFecPfxCount indicates the number of
        IPv6 egress FEC prefix statistics configured for this LDP instance."  
    ::= { vLdpNgStatsEntry 39 }
    
vLdpNgStatsUnknownTlvErrors    OBJECT-TYPE
    SYNTAX      Counter32
    MAX-ACCESS  read-only
    STATUS      current
    DESCRIPTION
        "The value of vLdpNgStatsUnknownTlvErrors indicates the number of
         Unknown TLV Fatal Errors detected for sessions associated
         with this LDP instance."
    REFERENCE
       "LDP Specification, Section 3.5.1.2."
    ::= { vLdpNgStatsEntry 40 }

vLdpNgStatsIPv4P2MPFecSent    OBJECT-TYPE
    SYNTAX      Gauge32
    MAX-ACCESS  read-only
    STATUS      current
    DESCRIPTION
        "The value of vLdpNgStatsIPv4P2MPFecSent specifies the number of IPv4 
         P2MP FECs sent by the LDP instance to its neighbors."
    ::= { vLdpNgStatsEntry 41 }

vLdpNgStatsIPv6P2MPFecSent    OBJECT-TYPE
    SYNTAX      Gauge32
    MAX-ACCESS  read-only
    STATUS      current
    DESCRIPTION
        "The value of vLdpNgStatsIPv6P2MPFecSent specifies the number of IPv6 
         P2MP FECs sent by the LDP instance to its neighbors."
    ::= { vLdpNgStatsEntry 42 }

vLdpNgStatsIPv4P2MPFecRecv    OBJECT-TYPE
    SYNTAX      Gauge32
    MAX-ACCESS  read-only
    STATUS      current
    DESCRIPTION
        "The value of vLdpNgStatsIPv4P2MPFecRecv specifies the number of IPv4 
         P2MP FECs received by the LDP instance from its neighbors."
    ::= { vLdpNgStatsEntry 43 }

vLdpNgStatsIPv6P2MPFecRecv    OBJECT-TYPE
    SYNTAX      Gauge32
    MAX-ACCESS  read-only
    STATUS      current
    DESCRIPTION
        "The value of vLdpNgStatsIPv6P2MPFecRecv specifies the number of IPv6 
         P2MP FECs received by the LDP instance from its neighbors."
    ::= { vLdpNgStatsEntry 44 }

vLdpNgStatsIPv4PfxFecOLSessSent    OBJECT-TYPE   
    SYNTAX      Gauge32
    MAX-ACCESS  read-only
    STATUS      current
    DESCRIPTION
        "The value of vLdpNgStatsIPv4PfxFecOLSessSent indicates the number
         of Overload Notifications sent for IPv4 address FEC over
         sessions in LDP instance."
    ::= { vLdpNgStatsEntry 45 }

vLdpNgStatsIPv6PfxFecOLSessSent    OBJECT-TYPE
    SYNTAX      Gauge32
    MAX-ACCESS  read-only
    STATUS      current
    DESCRIPTION
        "The value of vLdpNgStatsIPv6PfxFecOLSessSent indicates the number
         of Overload Notifications sent for IPv6 address FEC over
         sessions in LDP instance."
    ::= { vLdpNgStatsEntry 46 }

vLdpNgStatsIPv4PfxFecOLSessRecv    OBJECT-TYPE
    SYNTAX      Gauge32
    MAX-ACCESS  read-only
    STATUS      current
    DESCRIPTION
        "The value of vLdpNgStatsIPv4PfxFecOLSessRecv indicates the number
         of Overload Notifications received for IPv4 address FEC over
         sessions in LDP instance."
    ::= { vLdpNgStatsEntry 47 }

vLdpNgStatsIPv6PfxFecOLSessRecv    OBJECT-TYPE
    SYNTAX      Gauge32
    MAX-ACCESS  read-only
    STATUS      current
    DESCRIPTION
        "The value of vLdpNgStatsIPv6PfxFecOLSessRecv indicates the number
         of Overload Notifications received for IPv6 address FEC over
         sessions in LDP instance."
    ::= { vLdpNgStatsEntry 48 }

vLdpNgStatsIPv4P2MPFecOLSessSent    OBJECT-TYPE
    SYNTAX      Gauge32
    MAX-ACCESS  read-only
    STATUS      current
    DESCRIPTION
        "The value of vLdpNgStatsIPv4P2MPFecOLSessSent indicates the number
         of Overload Notifications sent for IPv4 P2MP FEC over 
         sessions in LDP instance."
    ::= { vLdpNgStatsEntry 49 }

vLdpNgStatsIPv6P2MPFecOLSessSent    OBJECT-TYPE
    SYNTAX      Gauge32
    MAX-ACCESS  read-only
    STATUS      current
    DESCRIPTION
        "The value of vLdpNgStatsIPv6P2MPFecOLSessSent indicates the number
         of Overload Notifications sent for IPv6 P2MP FEC over 
         sessions in LDP instance."
    ::= { vLdpNgStatsEntry 50 }

vLdpNgStatsIPv4P2MPFecOLSessRecv    OBJECT-TYPE
    SYNTAX      Gauge32
    MAX-ACCESS  read-only
    STATUS      current
    DESCRIPTION
        "The value of vLdpNgStatsIPv4P2MPFecOLSessRecv indicates the number
         of Overload Notifications received for IPv4 P2MP FEC over
         sessions in LDP instance."
    ::= { vLdpNgStatsEntry 51 }

vLdpNgStatsIPv6P2MPFecOLSessRecv    OBJECT-TYPE
    SYNTAX      Gauge32
    MAX-ACCESS  read-only
    STATUS      current
    DESCRIPTION
        "The value of vLdpNgStatsIPv6P2MPFecOLSessRecv indicates the number
         of Overload Notifications received for IPv6 P2MP FEC over sessions in 
         LDP instance."
    ::= { vLdpNgStatsEntry 52 }

vLdpNgStatsFec128FecOLSessSent    OBJECT-TYPE
    SYNTAX      Gauge32
    MAX-ACCESS  read-only
    STATUS      current
    DESCRIPTION
        "The value of vLdpNgStatsFec128FecOLSessSent indicates the number
         of Overload Notifications sent for PW ID FEC over sessions in LDP 
         instance."
    ::= { vLdpNgStatsEntry 53 }

vLdpNgStatsFec128FecOLSessRecv    OBJECT-TYPE
    SYNTAX      Gauge32
    MAX-ACCESS  read-only
    STATUS      current
    DESCRIPTION
        "The value of vLdpNgStatsFec128FecOLSessRecv indicates the number
         of Overload Notifications received for PW ID FEC over sessions in LDP 
         instance."
    ::= { vLdpNgStatsEntry 54 }

vLdpNgStatsFec129FecOLSessSent    OBJECT-TYPE
    SYNTAX      Gauge32
    MAX-ACCESS  read-only
    STATUS      current
    DESCRIPTION
        "The value of vLdpNgStatsFec129FecOLSessSent indicates the number
         of Overload Notifications sent for General PW ID FEC over sessions in 
         LDP instance."
    ::= { vLdpNgStatsEntry 55 }

vLdpNgStatsFec129FecOLSessRecv    OBJECT-TYPE
    SYNTAX      Gauge32
    MAX-ACCESS  read-only
    STATUS      current
    DESCRIPTION
        "The value of vLdpNgStatsFec129FecOLSessRecv indicates the number
         of Overload Notifications received for General PW ID FEC over sessions 
         in LDP instance."
    ::= { vLdpNgStatsEntry 56 }

vLdpNgStatsIPv4OLoadInterfaces    OBJECT-TYPE
    SYNTAX      Gauge32
    MAX-ACCESS  read-only
    STATUS      current
    DESCRIPTION
        "The value of vLdpNgStatsIPv4OLoadInterfaces indicates the
         number of overloaded IPv4 interfaces in LDP instance."
    ::= { vLdpNgStatsEntry 57 }

vLdpNgStatsIPv6OLoadInterfaces    OBJECT-TYPE
    SYNTAX      Gauge32
    MAX-ACCESS  read-only
    STATUS      current
    DESCRIPTION
        "The value of vLdpNgStatsIPv6OLoadInterfaces indicates the
         number of overloaded IPv6 interfaces in LDP instance."
    ::= { vLdpNgStatsEntry 58 }

vLdpNgStatsIPv4OLoadTargPeers    OBJECT-TYPE 
    SYNTAX      Gauge32
    MAX-ACCESS  read-only
    STATUS      current
    DESCRIPTION
        "The value of vLdpNgStatsIPv4OLoadTargPeers indicates the
         number of overloaded IPv4 targeted peers in LDP instance."
    ::= { vLdpNgStatsEntry 59 }

vLdpNgStatsIPv6OLoadTargPeers    OBJECT-TYPE 
    SYNTAX      Gauge32
    MAX-ACCESS  read-only
    STATUS      current
    DESCRIPTION
        "The value of vLdpNgStatsIPv6OLoadTargPeers indicates the
         number of overloaded IPv6 targeted peers in LDP instance."
    ::= { vLdpNgStatsEntry 60 }

vLdpNgStatsIPv4PfxFecInOLoad    OBJECT-TYPE
    SYNTAX      Gauge32
    MAX-ACCESS  read-only
    STATUS      current
    DESCRIPTION
        "The value of vLdpNgStatsIPv4PfxFecInOLoad indicates the number
         IPv4 Address FEC in overload state in LDP instance."
    ::= { vLdpNgStatsEntry 61 }

vLdpNgStatsIPv6PfxFecInOLoad    OBJECT-TYPE
    SYNTAX      Gauge32
    MAX-ACCESS  read-only
    STATUS      current
    DESCRIPTION
        "The value of vLdpNgStatsIPv6PfxFecInOLoad indicates the number
         IPv6 Address FEC in overload state in LDP instance."
    ::= { vLdpNgStatsEntry 62 }

vLdpNgStatsIPv4P2MPFecInOLoad    OBJECT-TYPE
    SYNTAX      Gauge32
    MAX-ACCESS  read-only
    STATUS      current
    DESCRIPTION
        "The value of vLdpNgStatsIPv4P2MPFecInOLoad indicates the number
         IPv4 P2MP FEC in overload state in LDP instance."
    ::= { vLdpNgStatsEntry 63 }

vLdpNgStatsIPv6P2MPFecInOLoad    OBJECT-TYPE
    SYNTAX      Gauge32
    MAX-ACCESS  read-only
    STATUS      current
    DESCRIPTION
        "The value of vLdpNgStatsIPv6P2MPFecInOLoad indicates the number
         IPv4 P2MP FEC in overload state in LDP instance."
    ::= { vLdpNgStatsEntry 64 }

vLdpNgStatsFec128FecInOLoad    OBJECT-TYPE
    SYNTAX      Gauge32
    MAX-ACCESS  read-only
    STATUS      current
    DESCRIPTION
        "The value of vLdpNgStatsFec128FecInOLoad indicates the number
         PW ID FEC in overload state in LDP instance."
    ::= { vLdpNgStatsEntry 65 }

vLdpNgStatsFec129FecInOLoad    OBJECT-TYPE
    SYNTAX      Gauge32
    MAX-ACCESS  read-only
    STATUS      current
    DESCRIPTION
        "The value of vLdpNgStatsFec129FecInOLoad indicates the number
         General PW ID FEC in overload state in LDP instance."
    ::= { vLdpNgStatsEntry 66 }
    
--
--  The Virtual Router Label Distribution Protocol (LDP) General Table
--

vRtrLdpNgCapabilityTable    OBJECT-TYPE
    SYNTAX      SEQUENCE OF VRtrLdpNgCapabilityEntry
    MAX-ACCESS  not-accessible
    STATUS      current
    DESCRIPTION
        "vRtrLdpNgCapabilityTable is a read-only table. The purpose of this table
         is to keep capability information about an LDP Instance.
         
         Use of AUGMENTS clause implies a one-to-one dependent
         relationship between the base table, vRtrLdpNgGeneralTable,
         and the augmenting table, vRtrLdpNgCapabilityTable. This in
         effect extends the vRtrLdpNgGeneralTable with additional
         columns.  Creation or deletion of a row in the 
         vRtrLdpNgGeneralTable results in the same fate for the row 
         in the vRtrLdpNgCapabilityTable."
    ::= { tmnxLdpNgObjs 43 }

vRtrLdpNgCapabilityEntry    OBJECT-TYPE
    SYNTAX      VRtrLdpNgCapabilityEntry
    MAX-ACCESS  not-accessible
    STATUS      current
    DESCRIPTION
        "An row in this table contains capability information about an 
         LDP instance."
    AUGMENTS  { vRtrLdpNgGeneralEntry }
    ::= { vRtrLdpNgCapabilityTable 1 }

VRtrLdpNgCapabilityEntry ::= SEQUENCE {
    vRtrLdpNgGenP2MPCapability            TruthValue,
    vRtrLdpNgGenMPMBBCapability           TruthValue,
    vRtrLdpNgGenDynamicCapability         TruthValue,
    vRtrLdpNgGenOverloadCapability        TruthValue,
    vRtrLdpNgGenFec128Capability          TruthValue,
    vRtrLdpNgGenFec129Capability          TruthValue,
    vRtrLdpNgGenIPv4PfxFecCapability      TruthValue,
    vRtrLdpNgGenIPv6PfxFecCapability      TruthValue
}
    
vRtrLdpNgGenP2MPCapability  OBJECT-TYPE
    SYNTAX      TruthValue
    MAX-ACCESS  read-only
    STATUS      current
    DESCRIPTION
        "The value of vRtrLdpNgGenP2MPCapability specifies whether 
         Point-to-Multipoint (P2MP) FEC capability is supported in the 
         LDP instance or not. When the value is 'true', the LDP 
         instance is P2MP capable."
    ::= { vRtrLdpNgCapabilityEntry 1 }

vRtrLdpNgGenMPMBBCapability  OBJECT-TYPE
    SYNTAX      TruthValue
    MAX-ACCESS  read-only
    STATUS      current
    DESCRIPTION
        "The value of vRtrLdpNgGenMPMBBCapability specifies whether 
         Multipoint(MP) Make-Before-Break (MBB) capability is supported 
         in the LDP instance or not.  When the value is 'true', the LDP
         instance is MP MBB capable."
    ::= { vRtrLdpNgCapabilityEntry 2 }

vRtrLdpNgGenDynamicCapability  OBJECT-TYPE
    SYNTAX      TruthValue
    MAX-ACCESS  read-only
    STATUS      current
    DESCRIPTION
        "The value of vRtrLdpNgGenDynamicCapability specifies whether dynamic 
         capability negotiation is supported or not in LDP sessions associated 
         with the LDP instance.  When 'true', the LDP instance supports dynamic
         capability negotiation."
    ::= { vRtrLdpNgCapabilityEntry 3 }

vRtrLdpNgGenOverloadCapability  OBJECT-TYPE
    SYNTAX      TruthValue
    MAX-ACCESS  read-only
    STATUS      current
    DESCRIPTION
        "The value of vRtrLdpNgGenOverloadCapability indicates whether 
         LSR Overload is supported or not in LDP sessions associated 
         with the LDP instance. When 'true', the LDP instance is LSR
         overload capable."
    ::= { vRtrLdpNgCapabilityEntry 4 }

vRtrLdpNgGenFec128Capability    OBJECT-TYPE
    SYNTAX      TruthValue
    MAX-ACCESS  read-only
    STATUS      current
    DESCRIPTION
        "The value of vRtrLdpNgGenFec128Capability specifies whether or not PW 
         (Pseudowire) ID FEC capability is supported in LDP instance."
    ::= { vRtrLdpNgCapabilityEntry 5 }

vRtrLdpNgGenFec129Capability    OBJECT-TYPE
    SYNTAX      TruthValue
    MAX-ACCESS  read-only
    STATUS      current
    DESCRIPTION
        "The value of vRtrLdpNgGenFec129Capability specifies whether or not 
          General PW ID FEC capability is supported in LDP instance."
    ::= { vRtrLdpNgCapabilityEntry 6 }

vRtrLdpNgGenIPv4PfxFecCapability    OBJECT-TYPE
    SYNTAX      TruthValue
    MAX-ACCESS  read-only
    STATUS      current
    DESCRIPTION
        "The value of vRtrLdpNgGenIPv4PfxFecCapability indicates whether or not
         IPv4 Prefix FEC capability is supported in LDP instance."
    ::= { vRtrLdpNgCapabilityEntry 7 }

vRtrLdpNgGenIPv6PfxFecCapability    OBJECT-TYPE
    SYNTAX      TruthValue
    MAX-ACCESS  read-only
    STATUS      current
    DESCRIPTION
        "The value of vRtrLdpNgGenIPv6PfxFecCapability specifies whether or not 
         IPv6 Prefix FEC capability is supported in LDP instance."
    ::= { vRtrLdpNgCapabilityEntry 8 }

--
--  The Virtual Router Label Distribution Protocol (LDP) TCP Session Params Table
--

vRtrLdpNgTcpSessParamsTableLstCh OBJECT-TYPE
    SYNTAX     TimeStamp
    MAX-ACCESS read-only
    STATUS     current
    DESCRIPTION
        "The value of vRtrLdpNgTcpSessParamsTableLstCh indicates the last
         timestamp when an entry in the vRtrLdpNgTcpSessParamsTable was last 
         changed."
    ::= { tmnxLdpNgObjs 44 }

vRtrLdpNgTcpSessParamsTable    OBJECT-TYPE
    SYNTAX      SEQUENCE OF VRtrLdpNgTcpSessParamsEntry
    MAX-ACCESS  not-accessible
    STATUS      current
    DESCRIPTION
        "vRtrLdpNgTcpSessParamsTable is used to configure parameters applicable
         to TCP transport session of an LDP session to remote peer."
    ::= { tmnxLdpNgObjs 45 }

vRtrLdpNgTcpSessParamsEntry    OBJECT-TYPE
    SYNTAX      VRtrLdpNgTcpSessParamsEntry
    MAX-ACCESS  not-accessible
    STATUS      current
    DESCRIPTION
        "Each row entry represents information applicable to TCP session to far
         end peer.

         Row entries can be created or deleted via SNMP SET requests.
         A row with default attribute values is created by setting
         vRtrLdpNgTcpSessRowStatus to 'createAndGo'. A row entry can be
         destroyed by setting vRtrLdpNgTcpSessRowStatus to 'destroy'."

   INDEX  { vRtrID,
            vRtrLdpNgTcpSessPeerAddrType,
            vRtrLdpNgTcpSessPeerAddr }
    ::= { vRtrLdpNgTcpSessParamsTable 1 }

VRtrLdpNgTcpSessParamsEntry ::= SEQUENCE {
    vRtrLdpNgTcpSessPeerAddrType             InetAddressType,
    vRtrLdpNgTcpSessPeerAddr                 InetAddress,
    vRtrLdpNgTcpSessRowStatus                RowStatus,
    vRtrLdpNgTcpSessAuth                     TruthValue,
    vRtrLdpNgTcpSessAuthKey                  OCTET STRING,
    vRtrLdpNgTcpSessAuthKeyChain             TNamedItemOrEmpty,
    vRtrLdpNgTcpSessPMTUDiscovery            TruthValue
}

vRtrLdpNgTcpSessPeerAddrType    OBJECT-TYPE
    SYNTAX      InetAddressType
    MAX-ACCESS  not-accessible
    STATUS      current
    DESCRIPTION
        "The value of vRtrLdpNgTcpSessPeerAddrType specifies the IP address type
         for vRtrLdpNgTcpSessPeerAddr."
    ::= { vRtrLdpNgTcpSessParamsEntry 1 }

vRtrLdpNgTcpSessPeerAddr    OBJECT-TYPE
    SYNTAX      InetAddress (SIZE (0|4|16))
    MAX-ACCESS  not-accessible
    STATUS      current
    DESCRIPTION
        "The value of vRtrLdpNgTcpSessPeerAddr specifies the remote TCP
         transport address to use for an LDP session to a peer. This value
         corresponds to peer address (vRtrLdpNgSessPeerAddress) of LDP session."
    ::= { vRtrLdpNgTcpSessParamsEntry 2 }

vRtrLdpNgTcpSessRowStatus    OBJECT-TYPE
    SYNTAX      RowStatus
    MAX-ACCESS  read-create
    STATUS      current
    DESCRIPTION
        "vRtrLdpNgTcpSessRowStatus is used to control the creation and deletion
         of rows in the vRtrLdpNgTcpSessParamsTable.

         A row can be created by setting vRtrLdpNgTcpSessRowStatus to
         'createAndGo'.  The agent should assign the default attribute values
         and change the row status to 'active'.

         A row entry can be destroyed by setting vRtrLdpNgTcpSessRowStatus to
         'destroy'."
    ::= { vRtrLdpNgTcpSessParamsEntry 3 }

vRtrLdpNgTcpSessAuth    OBJECT-TYPE
    SYNTAX      TruthValue
    MAX-ACCESS  read-create
    STATUS      current
    DESCRIPTION
        "When the value of vRtrLdpNgTcpSessAuth is 'true', authentication
         using MD5 message based digest protocol is enabled.  When 'false',
         no authentication is used."
    DEFVAL { false }
    ::= { vRtrLdpNgTcpSessParamsEntry 4 }

vRtrLdpNgTcpSessAuthKey    OBJECT-TYPE
    SYNTAX      OCTET STRING (SIZE(0..16))
    MAX-ACCESS  read-create
    STATUS      current
    DESCRIPTION
        "The string specified in vRtrLdpNgTcpSessAuthKey is the authentication
         key to be used between two LDP neighbors before establishing TCP
         transport session of the LDP protocol stream.  Authentication is done
         using the MD-5 message based digest protocol.  The authentication key
         can be any combination of letters or numbers.  Note that the string may
         contain embedded nulls.

         An SNMP Get request on this object should return an OCTET STRING of
         length 0."
    DEFVAL { ''H }   -- the empty string
    ::= { vRtrLdpNgTcpSessParamsEntry 5 }

vRtrLdpNgTcpSessAuthKeyChain  OBJECT-TYPE
    SYNTAX      TNamedItemOrEmpty
    MAX-ACCESS  read-create
    STATUS      current
    DESCRIPTION
        "The value of vRtrLdpNgTcpSessAuthKeyChain specifies the keychain which
         will be used to sign and/or authenticate TCP transport session of the
         LDP protocol stream.

         The keychain name is defined by tmnxKeyChainName and is the index for
         TIMETRA-SECURITY-MIB::tmnxKeyChainTable"
    DEFVAL { ''H }
    ::= { vRtrLdpNgTcpSessParamsEntry 6 }

vRtrLdpNgTcpSessPMTUDiscovery  OBJECT-TYPE
    SYNTAX      TruthValue
    MAX-ACCESS  read-create
    STATUS      current
    DESCRIPTION
        "The value of vRtrLdpNgTcpSessPMTUDiscovery specifies whether path MTU 
         discovery is enabled for this TCP transport session.

         When the value is set to 'true', path MTU discovery is enabled for 
         this TCP transport session. When the value is set to 'false', path MTU
         discovery is disabled."
    DEFVAL { false }
    ::= { vRtrLdpNgTcpSessParamsEntry 7 }

--
--  The Virtual Router Label Distribution Protocol (LDP) General Table
--

vRtrLdpNgGeneralTableLstCh OBJECT-TYPE
    SYNTAX     TimeStamp
    MAX-ACCESS read-only
    STATUS     current
    DESCRIPTION
        "The value of vRtrLdpNgGeneralTableLstCh indicates the last
         timestamp when an entry in the vRtrLdpNgGeneralTable was last 
         changed."
    ::= { tmnxLdpNgObjs 46 }

vRtrLdpNgGeneralTable    OBJECT-TYPE
    SYNTAX      SEQUENCE OF VRtrLdpNgGeneralEntry
    MAX-ACCESS  not-accessible
    STATUS      current
    DESCRIPTION
        "vRtrLdpNgGeneralTable has an entry for each virtual router 
         in the system capable of supporting an instance of the
         Label Distribution Protocol (LDP)."
    ::= { tmnxLdpNgObjs 47 }

vRtrLdpNgGeneralEntry    OBJECT-TYPE
    SYNTAX      VRtrLdpNgGeneralEntry
    MAX-ACCESS  not-accessible
    STATUS      current
    DESCRIPTION
        "Each row entry represents an instance of the Label Distribution
         Protocol (LDP) for a virtual router in the system. 

         An entry in this table is created by the agent when vRtrLdpStatus
         in the vRtrConfTable is set to 'create'. 
         The entry is destroyed when vRtrLdpStatus is set to 'delete' but
         only if vRtrLdpNgGenAdminState has a value of 'outOfService'."
    INDEX { vRtrID }
    ::= { vRtrLdpNgGeneralTable 1 }

VRtrLdpNgGeneralEntry ::= SEQUENCE {
    vRtrLdpNgGenCreateTime                TimeStamp,
    vRtrLdpNgGenUpTime                    TimeInterval,
    vRtrLdpNgGenRowLastCh                 TimeStamp,
    vRtrLdpNgGenLastChange                TimeStamp,
    vRtrLdpNgGenAdminState                TmnxAdminState,
    vRtrLdpNgGenOperState                 TmnxOperState,
    vRtrLdpNgGenOperDownReason            TmnxLdpGenOperDownReasonCode,
    vRtrLdpNgGenLdpIPv4LsrId              MplsLsrIdentifier,
    vRtrLdpNgGenLdpIPv6LsrId              TmnxMplsLsrNgIdentifier,
    vRtrLdpNgGenProtocolVersion           Unsigned32,
    vRtrLdpNgGenBackoffTime               TmnxLdpBackoffTime,
    vRtrLdpNgGenMaxBackoffTime            TmnxLdpBackoffTime,
    vRtrLdpNgGenTunnelDownDampTime        Unsigned32,
    vRtrLdpNgGenGracefulRestart           TruthValue,
    vRtrLdpNgGenGRNbrLiveTime             Unsigned32,
    vRtrLdpNgGenGRMaxRecoveryTime         Unsigned32,
    vRtrLdpNgGenLabelWithdrawalDelay      Unsigned32,
    vRtrLdpNgGenImplicitNull              TruthValue,
    vRtrLdpNgGenShortTTLPropLocal         TruthValue,
    vRtrLdpNgGenShortTTLPropTransit       TruthValue,
    vRtrLdpNgGenMPMBBTime                 Unsigned32,
    vRtrLdpNgGenLdpFrr                    TruthValue,
    vRtrLdpNgGenMcastUpstreamFrr          TruthValue,
    vRtrLdpNgGenDeaggregateFec            TruthValue,
    vRtrLdpNgGenControlMode               INTEGER,
    vRtrLdpNgGenDistMethod                TmnxLdpLabelDistMethod,
    vRtrLdpNgGenRetentionMode             INTEGER,
    vRtrLdpNgGenPropagatePolicy           TmnxLdpFECPolicy,
    vRtrLdpNgGenLoopDetectCap             INTEGER,
    vRtrLdpNgGenHopLimit                  Unsigned32,
    vRtrLdpNgGenPathVectorLimit           Unsigned32,
    vRtrLdpNgGenRoutePreference           Unsigned32
}

vRtrLdpNgGenCreateTime OBJECT-TYPE
    SYNTAX       TimeStamp
    MAX-ACCESS   read-only
    STATUS       current
    DESCRIPTION
        "The value of vRtrLdpNgGenCreateTime specifies the sysUpTime
         when this LDP instance was created."
    ::= { vRtrLdpNgGeneralEntry 1 }

vRtrLdpNgGenUpTime OBJECT-TYPE
    SYNTAX       TimeInterval
    MAX-ACCESS   read-only
    STATUS       current
    DESCRIPTION
        "The value of vRtrLdpNgGenUpTime specifies the time, in hundreds of 
         seconds, that the LDP instance has been in current operational state 
         (vRtrLdpNgGenOperState).

         If the value of vRtrLdpNgGenOperState is 'inService (2)', then 
         vRtrLdpNgGenUpTime specifies the time that the LDP instance has been 
         operationally up.

         If the value of vRtrLdpNgGenOperState is 'outOfService (3)', then 
         vRtrLdpNgGenUpTime specifies the time that the LDP instance has been 
         operationally down.

         If the value of vRtrLdpNgGenOperState is 'transition (4)', then 
         vRtrLdpNgGenUpTime specifies the time that the LDP instance has been 
         operationally in transition."
    ::= { vRtrLdpNgGeneralEntry 2 }

vRtrLdpNgGenRowLastCh OBJECT-TYPE
    SYNTAX     TimeStamp
    MAX-ACCESS read-only
    STATUS     current
    DESCRIPTION
        "The value of vRtrLdpNgGenRowLastCh indicates the timestamp when this 
         row was last modified."
    ::= { vRtrLdpNgGeneralEntry 3 }

vRtrLdpNgGenLastChange    OBJECT-TYPE
    SYNTAX      TimeStamp
    MAX-ACCESS  read-only
    STATUS      current
    DESCRIPTION
        "The value of vRtrLdpNgGenLastChange specifies the sysUpTime
         when this row was last modified."
    ::= { vRtrLdpNgGeneralEntry 4 }

vRtrLdpNgGenAdminState    OBJECT-TYPE
    SYNTAX      TmnxAdminState
    MAX-ACCESS  read-write
    STATUS      current
    DESCRIPTION
        "The value of vRtrLdpNgGenAdminState specifies the desired 
         administrative state for this LDP instance."
    DEFVAL { inService }
    ::= { vRtrLdpNgGeneralEntry 5 }

vRtrLdpNgGenOperState    OBJECT-TYPE
    SYNTAX      TmnxOperState
    MAX-ACCESS  read-only
    STATUS      current
    DESCRIPTION
        "The value of vRtrLdpNgGenOperState specifies the current 
         operational state of this LDP instance."
    ::= { vRtrLdpNgGeneralEntry 6 }

vRtrLdpNgGenOperDownReason  OBJECT-TYPE
    SYNTAX       TmnxLdpGenOperDownReasonCode
    MAX-ACCESS   read-only
    STATUS       current
    DESCRIPTION
        "The value of vRtrLdpNgGenOperDownReason specifies the reason
         that the LDP instance is operationally down."
    ::= { vRtrLdpNgGeneralEntry 7 }

vRtrLdpNgGenLdpIPv4LsrId    OBJECT-TYPE
    SYNTAX      MplsLsrIdentifier
    MAX-ACCESS  read-only
    STATUS      current
    DESCRIPTION
        "The value of vRtrLdpNgGenLdpIPv4LsrId is the IPv4 Label Switch Router
         (LSR) identifier which is used as the first 4 bytes or the 
         Router Id component of the Label Distribution Protocol (LDP) 
         identifier."
    ::= { vRtrLdpNgGeneralEntry 8 }

vRtrLdpNgGenLdpIPv6LsrId    OBJECT-TYPE
    SYNTAX      TmnxMplsLsrNgIdentifier
    MAX-ACCESS  read-only
    STATUS      current
    DESCRIPTION
        "The value of vRtrLdpNgGenLdpIPv6LsrId is the IPv6 Label Switch Router
         (LSR) identifier which is used as the first 16 bytes or the 
         Router Id component of the Label Distribution Protocol (LDP) 
         identifier."
    ::= { vRtrLdpNgGeneralEntry 9 }

vRtrLdpNgGenProtocolVersion    OBJECT-TYPE
    SYNTAX      Unsigned32
    MAX-ACCESS  read-only
    STATUS      current
    DESCRIPTION
        "The value of  vRtrLdpNgGenProtocolVersion specifies the 
         version of the LDP protocol instance. A value of zero (0) 
         indicates that the version of the protocol is unknown."
    ::= { vRtrLdpNgGeneralEntry 10 }

vRtrLdpNgGenBackoffTime    OBJECT-TYPE
    SYNTAX      TmnxLdpBackoffTime (1..2592000)
    UNITS       "seconds"
    MAX-ACCESS  read-only
    STATUS      current
    DESCRIPTION
        "The value of vRtrLdpNgGenBackoffTime specifies the initial 
         value for the backoff interval. 

         The backoff interval is the time, in seconds, that LDP waits 
         after an LDP session setup has failed before it attempts to 
         setup the session again. After the LDP session startup fails 
         the first time, the backoff interval is set to the value of 
         vRtrLdpNgGenBackoffTime. Thereafter, if session startup 
         fails again the backoff interval increases exponentially."
    ::= { vRtrLdpNgGeneralEntry 11 }

vRtrLdpNgGenMaxBackoffTime    OBJECT-TYPE
    SYNTAX      TmnxLdpBackoffTime
    UNITS       "seconds"
    MAX-ACCESS  read-only
    STATUS      current
    DESCRIPTION
        "The value of vRtrLdpNgGenMaxBackoffTime specifies the maximum
         value for the backoff interval.

         For each successive failure of the LDP session startup, the 
         backoff interval (the time for which the router waits before 
         retrying) increases exponentially. If the backoff interval 
         exceeds vRtrLdpNgGenMaxBackoffTime, the router will give 
         up trying to establish the LDP session. 

         If vRtrLdpNgGenMaxBackoffTime is set to zero (0), then the 
         backoff interval does not increase exponentially after the 
         first session startup attempt fails. Instead it remains
         constant and LDP will keep retrying to establish a session 
         until it succeeds."
    ::= { vRtrLdpNgGeneralEntry 12 }

vRtrLdpNgGenTunnelDownDampTime  OBJECT-TYPE
    SYNTAX       Unsigned32 (0..20)
    UNITS        "seconds"
    MAX-ACCESS   read-write
    STATUS       current
    DESCRIPTION
        "The value of vRtrLdpNgGenTunnelDownDampTime specifies the time 
         interval, in seconds, that LDP waits before posting a 
         tunnel down event to the Route Table Manager. If a tunnel
         up event is generated before the damping interval has 
         elapsed, a tunnel modify event will be posted to the Route 
         Table Manager (RTM). If this value is set to 0, then tunnel
         down events are not damped."
    DEFVAL { 3 }
    ::= { vRtrLdpNgGeneralEntry 13 }

vRtrLdpNgGenGracefulRestart  OBJECT-TYPE
    SYNTAX      TruthValue
    MAX-ACCESS  read-write
    STATUS      current
    DESCRIPTION
        "The value of vRtrLdpNgGenGracefulRestart specifies whether graceful 
         restart helper is allowed.  When this object has a value of 'true', 
         graceful restart helper is enabled.  When its value is 'false', 
         graceful restart helper is disabled."
    DEFVAL { false }
    ::= { vRtrLdpNgGeneralEntry 14 }

vRtrLdpNgGenGRNbrLiveTime  OBJECT-TYPE
    SYNTAX       Unsigned32 (5..300)
    UNITS        "seconds"
    MAX-ACCESS   read-write
    STATUS       current
    DESCRIPTION
        "The value of vRtrLdpNgGenGRNbrLiveTime specifies the value for neighbor
         liveness timer.  The amount of time the Label Switching Router (LSR) 
         keeps its stale label-FEC bindings is set to the lesser of the FT 
         Reconnect Timeout, as was advertised by the  neighbor, and this local 
         timer, called the Neighbor Liveness Timer.  

         The LSR waits for the specified time till a LDP session re-establishes 
         itself.  If within that time the LSR still does not establish an LDP 
         session with the neighbor, all the stale bindings are deleted.  This 
         object has meaning only when vRtrLdpNgGenGracefulRestart is 'true'."
    DEFVAL { 120 }
    ::= { vRtrLdpNgGeneralEntry 15 }

vRtrLdpNgGenGRMaxRecoveryTime OBJECT-TYPE
    SYNTAX       Unsigned32 (15..1800)
    UNITS        "seconds"
    MAX-ACCESS   read-write
    STATUS       current
    DESCRIPTION
        "The value of vRtrLdpNgGenGRMaxRecoveryTime specifies the local maximum
         recovery time. 
         
         If the Label Switching Router (LSR)  determines that the neighbor was 
         able to preserve its MPLS forwarding state (as was indicated by the 
         non-zero Recovery Time advertised by the neighbor), the LSR should 
         further keep the stale label-FEC  bindings, received from the 
         neighbor, for as long as the lesser of the Recovery Time advertised 
         by the neighbor, and a local configurable value, called Maximum 
         Recovery Time, allows.  This object has meaning only when 
         vRtrLdpNgGenGracefulRestart is 'true'."
    DEFVAL { 120 }
    ::= { vRtrLdpNgGeneralEntry 16 }

vRtrLdpNgGenLabelWithdrawalDelay  OBJECT-TYPE
    SYNTAX       Unsigned32 (0|3..120)
    UNITS        "seconds"
    MAX-ACCESS   read-write
    STATUS       current
    DESCRIPTION
        "The value of vRtrLdpNgGenLabelWithdrawalDelay specifies the time
         interval, in seconds, LDP will delay for the withdrawal of FEC-label 
         binding it distributed to its neighbours when FEC is de-activated. 
         When the timer expires, LDP then sends a label withdrawal for the FEC 
         to all its neighbours. This is applicable only to LDP transport 
         tunnels (ipv4 prefix FECs) and is not applicable to Pseudowires 
         (service FECs).
         
         A value of 0 indicates that vRtrLdpNgGenLabelWithdrawalDelay is 
         disabled." 
    DEFVAL { 0 }
    ::= { vRtrLdpNgGeneralEntry 17 }

vRtrLdpNgGenImplicitNull  OBJECT-TYPE
    SYNTAX       TruthValue
    MAX-ACCESS   read-write
    STATUS       current
    DESCRIPTION
        "The value of vRtrLdpNgGenImplicitNull specifies whether or not to 
         signal implicit null values for all LDP FECs for which this node is 
         an egress Label Edge Router (LER). When the value is true implicit 
         null values are signaled."
    DEFVAL { false }
    ::= { vRtrLdpNgGeneralEntry 18 }

vRtrLdpNgGenShortTTLPropLocal   OBJECT-TYPE
    SYNTAX      TruthValue
    MAX-ACCESS  read-write
    STATUS      current
    DESCRIPTION
        "The value of vRtrLdpNgGenShortTTLPropLocal specifies whether or not
         to enable the propagation of time to live (TTL) from the header of 
         IP packet into the header of resulting MPLS packet for all local 
         packets forwarded over a LDP shortcut.  When the value is set to 
         'true' TTL is propagated from the header of IP packet into the 
         header of the resulting MPLS packet for all local packets."
    DEFVAL { true }    
    ::= { vRtrLdpNgGeneralEntry 19 }

vRtrLdpNgGenShortTTLPropTransit   OBJECT-TYPE
    SYNTAX      TruthValue 
    MAX-ACCESS  read-write
    STATUS      current
    DESCRIPTION
        "The value of vRtrLdpNgGenShortTTLPropTransit specifies whether or not
         to enable the propagation of time to live (TTL) from the header of 
         IP packet into the header of resulting MPLS packet for all transit 
         packets forwarded over a LDP shortcut.  When the value is set to 
         'true' TTL is propagated from the header of IP packet into the 
         header of the resulting MPLS packet for all transit packets."
    DEFVAL { true }    
    ::= { vRtrLdpNgGeneralEntry 20 }

vRtrLdpNgGenMPMBBTime    OBJECT-TYPE
    SYNTAX      Unsigned32 (0..10)
    UNITS       "seconds"
    MAX-ACCESS  read-write
    STATUS      current
    DESCRIPTION
        "The value of vRtrLdpNgGenMPMBBTime specifies the maximum
         time a Multi Point (MP) transit node must wait before 
         switching over to a new path if the new node does not send
         Make Before Break (MBB) Tag Length Value (TLV) to inform of 
         the availability of the data plane."
    DEFVAL { 3 }    
    ::= { vRtrLdpNgGeneralEntry 21 }

vRtrLdpNgGenLdpFrr  OBJECT-TYPE
    SYNTAX      TruthValue
    MAX-ACCESS  read-write
    STATUS      current
    DESCRIPTION
        "The value of vRtrLdpNgGenLdpFrr specifies whether fast re-route of 
         LDP tunnel is enabled or disabled.

         When the value of vRtrLdpNgGenLdpFrr is set to 'true' fast re-route 
         of LDP tunnel is enabled and when vRtrLdpNgGenLdpFrr is set to 
         'false' fast re-route of LDP tunnel is disabled."
    DEFVAL { false }
    ::= { vRtrLdpNgGeneralEntry 22 }

vRtrLdpNgGenMcastUpstreamFrr  OBJECT-TYPE
    SYNTAX      TruthValue
    MAX-ACCESS  read-write
    STATUS      current
    DESCRIPTION
        "The value of vRtrLdpNgGenMcastUpstreamFrr specifies whether mLDP fast
         upstream switchover feature is enabled or not for the LDP instance.
         When 'true', the LDP instance supports mLDP fast upstream switchover."
    DEFVAL { false }
    ::= { vRtrLdpNgGeneralEntry 23 }

vRtrLdpNgGenDeaggregateFec    OBJECT-TYPE
    SYNTAX      TruthValue
    MAX-ACCESS  read-only
    STATUS      current
    DESCRIPTION
        "When vRtrLdpNgGenDeaggregateFec has a value of 'false', LDP
         aggregates multiple prefixes into a single Forwarding Equivalence
         Class (FEC) and advertises a single label for the FEC. When the 
         value is 'true', LDP deaggregates prefixes into multiple
         FECs."
    ::= { vRtrLdpNgGeneralEntry 24 }

vRtrLdpNgGenControlMode    OBJECT-TYPE
    SYNTAX      INTEGER {
                    ordered (1),
                    independent (2)
                }
    MAX-ACCESS  read-only 
    STATUS      current
    DESCRIPTION
        "The value of vRtrLdpNgGenControlMode specifies the mode used  
         for distributing labels in response to label binding requests.
             
         When vRtrLdpNgGenControlMode has a value of 'ordered', label 
         bindings are not distributed in response to a label request until 
         a label binding has been received from the next hop for the 
         destination.
                           
         When vRtrLdpNgGenControlMode has a value of 'independent', label 
         bindings are distributed immediately in response to a label 
         request even if a label binding has not yet been received from 
         the next hop for the destination."
    ::= { vRtrLdpNgGeneralEntry 25 }

vRtrLdpNgGenDistMethod    OBJECT-TYPE
    SYNTAX      TmnxLdpLabelDistMethod
    MAX-ACCESS  read-only
    STATUS      current
    DESCRIPTION
        "The value of vRtrLdpNgGenDistMethod specifies the label
         distribution method used.
             
         When vRtrLdpNgGenDistMethod has a value of 'downstreamOnDemand',
         label bindings are distributed to the upstream LSR, for each FEC, 
         without requiring a request message for the FEC from the upstream 
         LSR.

         When vRtrLdpNgGenDistMethod has a value of 'downstreamUnsolicited',
         label bindings are distributed to the upstream LSR only when a 
         label request message is received."
    ::= { vRtrLdpNgGeneralEntry 26 }
        
vRtrLdpNgGenRetentionMode    OBJECT-TYPE
    SYNTAX      INTEGER {
                    conservative (1),
                    liberal (2)
                }
    MAX-ACCESS  read-only
    STATUS      current
    DESCRIPTION
        "The value of vRtrLdpNgGenRetentionMode specifies the label
         retention mode used.
             
         If the value of this object is 'conservative', then advertised 
         label mappings are retained only if they will be used to forward 
         packets, i.e. if the label came from a valid next hop.  Label
         bindings received from non-nexthops for each FEC are discarded.

         If the value of this object is 'liberal', then all advertised 
         label mappings are retained whether they are from a valid next 
         hop or not.  When vRtrLdpNgGenDistMethod has a value of
         'downstreamUnsolicited', a LSR may receive label bindings for
         the same destination for all its neighbors.  Labels for the
         non-nexthops for the FECs are retained in the software but not
         used.  When a network topology change occurs where a non-nexthop
         becomes a true next hop, the label received earlier is then used."
    ::= { vRtrLdpNgGeneralEntry 27 }

vRtrLdpNgGenPropagatePolicy    OBJECT-TYPE
    SYNTAX      TmnxLdpFECPolicy
    MAX-ACCESS  read-only
    STATUS      current
    DESCRIPTION
        "The value of vRtrLdpNgGenPropagatePolicy determines whether the 
         LSR should generate FECs and which FECs it should generate.
         
         When the value of this object is 'system', LDP will distribute 
         label bindings only for the router's system IP address

         When the value of this object is 'interface', LDP will distribute
         label bindings for all LDP interfaces

         When the value of this object is 'all', LDP will distribute label
         bindings for all prefixes in the routing table
         
         When the value of this object is 'none', LDP will not distribute
         any label bindings."
    ::= { vRtrLdpNgGeneralEntry 28 }

vRtrLdpNgGenLoopDetectCap    OBJECT-TYPE
    SYNTAX      INTEGER {
                    none (1),
                    other (2),
                    hopCount (3),
                    pathVector (4),
                    hopCountAndPathVector (5)
                }
    MAX-ACCESS  read-only
    STATUS      current
    DESCRIPTION
        "The value of vRtrLdpNgGenLoopDetectCap indicate whether 
         this LSR supports loop detection and if so, what type of loop
         detection is supported.

         When the value is 'none' loop detection is not supported on this 
         LSR.

         When the value is 'other' Loop Detection is supported but by a 
         method other than those listed below.
         
         When the value is 'hopCount' Loop Detection is supported by Hop 
         Count only.

         When the value is 'pathVector' Loop Detection is supported by
         Path Vector only.

         When the value is 'hopCountAndPathVector' Loop Detection is
         supported by both Hop Count and Path Vector.

         Since Loop Detection is determined during Session Initialization, 
         an individual session may not be running with loop detection.  
         This object simply gives an indication of whether or not the
         LSR has the ability to support Loop Detection and which types."
    ::= { vRtrLdpNgGeneralEntry 29 }

vRtrLdpNgGenHopLimit    OBJECT-TYPE
    SYNTAX       Unsigned32 (0..255)
    MAX-ACCESS   read-only
    STATUS       current
    DESCRIPTION
        "The value of vRtrLdpNgGenHopLimit specifies the maximum
         allowable value for the hop count.  The value of this object
         is valid and used only if vRtrLdpNgGenLoopDetectCap has
         a value of either 'hopCount' or 'hopCountAndPathVector'."
    ::= { vRtrLdpNgGeneralEntry 30 }

vRtrLdpNgGenPathVectorLimit  OBJECT-TYPE
    SYNTAX      Unsigned32 (0..255)
    MAX-ACCESS  read-only
    STATUS      current
    DESCRIPTION
        "The value of vRtrLdpNgGenPathVectorLimit specifies the maximum
         allowable value for the path vector count.  The value of this
         object is valid and used only if vRtrLdpNgGenLoopDetectCap
         has a value of either 'pathVector' or 'hopCountAndPathVector'."
    ::= { vRtrLdpNgGeneralEntry 31 }    

vRtrLdpNgGenRoutePreference    OBJECT-TYPE
    SYNTAX      Unsigned32 (1..255)
    MAX-ACCESS  read-only
    STATUS      current
    DESCRIPTION
        "The value of vRtrLdpNgGenRoutePreference specifies the route 
         preference assigned to LDP routes. When multiple routes are 
         available to a destination, the route with the lowest preference 
         will be used."
    ::= { vRtrLdpNgGeneralEntry 32 }

--
--  The Virtual Router Label Distribution Protocol (LDP) Policy Table
--

vRtrLdpNgPolicyTableLstCh OBJECT-TYPE
    SYNTAX     TimeStamp
    MAX-ACCESS read-only
    STATUS     current
    DESCRIPTION
        "The value of vRtrLdpNgPolicyTableLstCh indicates the last
         timestamp when an entry in the vRtrLdpNgPolicyTable was last 
         changed."
    ::= { tmnxLdpNgObjs 48 }

vRtrLdpNgPolicyTable    OBJECT-TYPE
    SYNTAX      SEQUENCE OF VRtrLdpNgPolicyEntry
    MAX-ACCESS  not-accessible
    STATUS      current
    DESCRIPTION
        "vRtrLdpNgGeneralTable keeps information about LDP policies.

         Use of AUGMENTS clause implies a one-to-one dependent relationship
         between the base table, vRtrLdpNgGeneralTable, and the augmenting table,
         vRtrLdpTargTable. This in effect extends the vRtrLdpNgGeneralTable with
         additional columns.  Creation or deletion of a row in the
         vRtrLdpNgGeneralTable results in the same fate for the row in the
         vRtrLdpTargTable."
    ::= { tmnxLdpNgObjs 49 }

vRtrLdpNgPolicyEntry    OBJECT-TYPE
    SYNTAX      VRtrLdpNgPolicyEntry
    MAX-ACCESS  not-accessible
    STATUS      current
    DESCRIPTION
        "A row in this table represents information about the policy
         configuration in LDP"
    AUGMENTS  { vRtrLdpNgGeneralEntry }
    ::= { vRtrLdpNgPolicyTable 1 }

VRtrLdpNgPolicyEntry ::= SEQUENCE {
    vRtrLdpNgPolRowLastCh                 TimeStamp,
    vRtrLdpNgPolImportPolicy1             TPolicyStatementNameOrEmpty,
    vRtrLdpNgPolImportPolicy2             TPolicyStatementNameOrEmpty,
    vRtrLdpNgPolImportPolicy3             TPolicyStatementNameOrEmpty,
    vRtrLdpNgPolImportPolicy4             TPolicyStatementNameOrEmpty,
    vRtrLdpNgPolImportPolicy5             TPolicyStatementNameOrEmpty,
    vRtrLdpNgPolExportPolicy1             TPolicyStatementNameOrEmpty,
    vRtrLdpNgPolExportPolicy2             TPolicyStatementNameOrEmpty,
    vRtrLdpNgPolExportPolicy3             TPolicyStatementNameOrEmpty,
    vRtrLdpNgPolExportPolicy4             TPolicyStatementNameOrEmpty,
    vRtrLdpNgPolExportPolicy5             TPolicyStatementNameOrEmpty,
    vRtrLdpNgPolTunlTblExportPolicy1      TPolicyStatementNameOrEmpty,
    vRtrLdpNgPolTunlTblExportPolicy2      TPolicyStatementNameOrEmpty,
    vRtrLdpNgPolTunlTblExportPolicy3      TPolicyStatementNameOrEmpty,
    vRtrLdpNgPolTunlTblExportPolicy4      TPolicyStatementNameOrEmpty,
    vRtrLdpNgPolTunlTblExportPolicy5      TPolicyStatementNameOrEmpty
}

vRtrLdpNgPolRowLastCh OBJECT-TYPE
    SYNTAX     TimeStamp
    MAX-ACCESS read-only
    STATUS     current
    DESCRIPTION
        "The value of vRtrLdpNgPolRowLastCh indicates the timestamp when this 
         row was last modified."
    ::= { vRtrLdpNgPolicyEntry 1 }

vRtrLdpNgPolImportPolicy1 OBJECT-TYPE
    SYNTAX       TPolicyStatementNameOrEmpty
    MAX-ACCESS   read-write
    STATUS       current
    DESCRIPTION
        "The value of vRtrLdpNgPolImportPolicy1 specifies the first 
         import policy used to filter LDP label bindings received
         from LDP peers."
    DEFVAL { ''H }
    ::= { vRtrLdpNgPolicyEntry 2 }

vRtrLdpNgPolImportPolicy2 OBJECT-TYPE
    SYNTAX       TPolicyStatementNameOrEmpty
    MAX-ACCESS   read-write
    STATUS       current
    DESCRIPTION
        "The value of vRtrLdpNgPolImportPolicy2 specifies the second 
         import policy used to filter LDP label bindings received
         from LDP peers."  
    DEFVAL { ''H }
    ::= { vRtrLdpNgPolicyEntry 3 }

vRtrLdpNgPolImportPolicy3 OBJECT-TYPE
    SYNTAX       TPolicyStatementNameOrEmpty
    MAX-ACCESS   read-write
    STATUS       current
    DESCRIPTION
        "The value of vRtrLdpNgPolImportPolicy3 specifies the third 
         import policy used to filter LDP label bindings received
         from LDP peers."  
    DEFVAL { ''H }
    ::= { vRtrLdpNgPolicyEntry 4 }

vRtrLdpNgPolImportPolicy4 OBJECT-TYPE
    SYNTAX       TPolicyStatementNameOrEmpty
    MAX-ACCESS   read-write
    STATUS       current
    DESCRIPTION
        "The value of vRtrLdpNgPolImportPolicy4 specifies the fourth 
         import policy used to filter LDP label bindings received
         from LDP peers."  
    DEFVAL { ''H }
    ::= { vRtrLdpNgPolicyEntry 5 }

vRtrLdpNgPolImportPolicy5 OBJECT-TYPE
    SYNTAX       TPolicyStatementNameOrEmpty
    MAX-ACCESS   read-write
    STATUS       current
    DESCRIPTION
        "The value of vRtrLdpNgPolImportPolicy5 specifies the fifth 
         import policy used to filter LDP label bindings received
         from LDP peers."  
    DEFVAL { ''H }
    ::= { vRtrLdpNgPolicyEntry 6 }

vRtrLdpNgPolExportPolicy1 OBJECT-TYPE
    SYNTAX       TPolicyStatementNameOrEmpty
    MAX-ACCESS   read-write
    STATUS       current
    DESCRIPTION
        "The value of vRtrLdpNgPolExportPolicy1 specifies the first 
         export policy used to filter LDP label bindings advertised
         to LDP peers."  
    DEFVAL { ''H }
    ::= { vRtrLdpNgPolicyEntry 7 }

vRtrLdpNgPolExportPolicy2 OBJECT-TYPE
    SYNTAX       TPolicyStatementNameOrEmpty
    MAX-ACCESS   read-write
    STATUS       current
    DESCRIPTION
        "The value of vRtrLdpNgPolExportPolicy2 specifies the second 
         export policy used to filter LDP label bindings advertised
         to LDP peers."  
    DEFVAL { ''H }
    ::= { vRtrLdpNgPolicyEntry 8 }

vRtrLdpNgPolExportPolicy3 OBJECT-TYPE
    SYNTAX       TPolicyStatementNameOrEmpty
    MAX-ACCESS   read-write
    STATUS       current
    DESCRIPTION
        "The value of vRtrLdpNgPolExportPolicy3 specifies the third 
         export policy used to filter LDP label bindings advertised
         to LDP peers."  
    DEFVAL { ''H }
    ::= { vRtrLdpNgPolicyEntry 9 }

vRtrLdpNgPolExportPolicy4 OBJECT-TYPE
    SYNTAX       TPolicyStatementNameOrEmpty
    MAX-ACCESS   read-write
    STATUS       current
    DESCRIPTION
        "The value of vRtrLdpNgPolExportPolicy4 specifies the fourth 
         export policy used to filter LDP label bindings advertised
         to LDP peers."  
    DEFVAL { ''H }
    ::= { vRtrLdpNgPolicyEntry 10 }

vRtrLdpNgPolExportPolicy5 OBJECT-TYPE
    SYNTAX       TPolicyStatementNameOrEmpty
    MAX-ACCESS   read-write
    STATUS       current
    DESCRIPTION
        "The value of vRtrLdpNgPolExportPolicy5 specifies the fifth
         export policy used to filter LDP label bindings advertised
         to LDP peers."  
    DEFVAL { ''H }
    ::= { vRtrLdpNgPolicyEntry 11 }

vRtrLdpNgPolTunlTblExportPolicy1 OBJECT-TYPE
    SYNTAX       TPolicyStatementNameOrEmpty
    MAX-ACCESS   read-write
    STATUS       current
    DESCRIPTION
        "The value of vRtrLdpNgPolTunlTblExportPolicy1 specifies the first tunnel
         table export policy used for exporting tunneled routes from the CPM
         tunnel table as LDP FEC."
    DEFVAL { ''H }
    ::= { vRtrLdpNgPolicyEntry 12 }

vRtrLdpNgPolTunlTblExportPolicy2 OBJECT-TYPE
    SYNTAX       TPolicyStatementNameOrEmpty
    MAX-ACCESS   read-write
    STATUS       current
    DESCRIPTION
        "The value of vRtrLdpNgPolTunlTblExportPolicy2 specifies the second tunnel
         table export policy used for exporting tunneled routes from the CPM
         tunnel table as LDP FEC."
    DEFVAL { ''H }
    ::= { vRtrLdpNgPolicyEntry 13 }

vRtrLdpNgPolTunlTblExportPolicy3 OBJECT-TYPE
    SYNTAX       TPolicyStatementNameOrEmpty
    MAX-ACCESS   read-write
    STATUS       current
    DESCRIPTION
        "The value of vRtrLdpNgPolTunlTblExportPolicy3 specifies the third tunnel
         table export policy used for exporting tunneled routes from the CPM
         tunnel table as LDP FEC."
    DEFVAL { ''H }
    ::= { vRtrLdpNgPolicyEntry 14 }

vRtrLdpNgPolTunlTblExportPolicy4 OBJECT-TYPE
    SYNTAX       TPolicyStatementNameOrEmpty
    MAX-ACCESS   read-write
    STATUS       current
    DESCRIPTION
        "The value of vRtrLdpNgPolTunlTblExportPolicy4 specifies the fourth 
         tunnel table export policy used for exporting tunneled routes from 
         the CPM tunnel table as LDP FEC."
    DEFVAL { ''H }
    ::= { vRtrLdpNgPolicyEntry 15 }

vRtrLdpNgPolTunlTblExportPolicy5 OBJECT-TYPE
    SYNTAX       TPolicyStatementNameOrEmpty
    MAX-ACCESS   read-write
    STATUS       current
    DESCRIPTION
        "The value of vRtrLdpNgPolTunlTblExportPolicy5 specifies the fifth tunnel 
         table export policy used for exporting tunneled routes from the CPM 
         tunnel table as LDP FEC."
    DEFVAL { ''H }
    ::= { vRtrLdpNgPolicyEntry 16 }

--
--  The Virtual Router Label Distribution Protocol (LDP) Interface Parameters Table
--

vRtrLdpNgIfParamsTableLstCh OBJECT-TYPE
    SYNTAX     TimeStamp
    MAX-ACCESS read-only
    STATUS     current
    DESCRIPTION
        "The value of vRtrLdpNgIfParamsTableLstCh indicates the last
         timestamp when an entry in the vRtrLdpNgIfParamsTable was last 
         changed."
    ::= { tmnxLdpNgObjs 50 }

vRtrLdpNgIfParamsTable    OBJECT-TYPE
    SYNTAX      SEQUENCE OF VRtrLdpNgIfParamsEntry
    MAX-ACCESS  not-accessible
    STATUS      current
    DESCRIPTION
         "vRtrLdpNgIfParamsTable keeps information applicable to the interfaces
          in LDP.

          Use of AUGMENTS clause implies a one-to-one dependent relationship
          between the base table, vRtrLdpNgGeneralTable, and the augmenting
          table, vRtrLdpNgIfParamsTable. This in effect extends the
          vRtrLdpNgGeneralTable with additional columns.  Creation or deletion
          of a row in the vRtrLdpNgGeneralTable results in the same fate for the
          row in the vRtrLdpNgIfParamsTable."
    ::= { tmnxLdpNgObjs 51 }

vRtrLdpNgIfParamsEntry    OBJECT-TYPE
    SYNTAX      VRtrLdpNgIfParamsEntry
    MAX-ACCESS  not-accessible
    STATUS      current
    DESCRIPTION
        "A row in this table represents information applicable to the interfaces
         in LDP."
    AUGMENTS  { vRtrLdpNgGeneralEntry }
    ::= { vRtrLdpNgIfParamsTable 1 }

VRtrLdpNgIfParamsEntry ::= SEQUENCE {
    vRtrLdpNgIfParamRowLastCh                 TimeStamp,
    vRtrLdpNgIfParamIPv4KAFactor              TmnxLdpKeepAliveFactor,
    vRtrLdpNgIfParamIPv6KAFactor              TmnxLdpKeepAliveFactor,
    vRtrLdpNgIfParamIPv4KATimeout             TmnxLdpNewKeepAliveTimeout,
    vRtrLdpNgIfParamIPv6KATimeout             TmnxLdpNewKeepAliveTimeout,
    vRtrLdpNgIfParamIPv4HelloFactor           TmnxLdpHelloFactor,
    vRtrLdpNgIfParamIPv6HelloFactor           TmnxLdpHelloFactor,
    vRtrLdpNgIfParamIPv4HelloTimeout          TmnxLdpNewHelloTimeout,
    vRtrLdpNgIfParamIPv6HelloTimeout          TmnxLdpNewHelloTimeout,
    vRtrLdpNgIfParamIPv4TransAddrTyp          INTEGER,
    vRtrLdpNgIfParamIPv6TransAddrTyp          INTEGER
}

vRtrLdpNgIfParamRowLastCh OBJECT-TYPE
    SYNTAX     TimeStamp
    MAX-ACCESS read-only
    STATUS     current
    DESCRIPTION
        "The value of vRtrLdpNgIfParamRowLastCh indicates the timestamp when 
         this row was last modified."
    ::= { vRtrLdpNgIfParamsEntry 1 }

vRtrLdpNgIfParamIPv4KAFactor    OBJECT-TYPE
    SYNTAX      TmnxLdpKeepAliveFactor
    MAX-ACCESS  read-write
    STATUS      current
    DESCRIPTION
        "The value of vRtrLdpNgIfParamIPv4KAFactor specifies the value by which
         the keepalive timeout (vRtrLdpNgIfParamKeepAliveTimeout) should be
         divided to give the keepalive time i.e. the time interval, in seconds,
         between LDP keepalive messages. LDP keepalive messages are sent to keep
         the LDP session from timing out when no other LDP traffic is being sent
         between the neighbors.

         This value is only applicable to LDP IPv4 interfaces."
    DEFVAL { 3 }
    ::= { vRtrLdpNgIfParamsEntry 2 }

vRtrLdpNgIfParamIPv6KAFactor    OBJECT-TYPE
    SYNTAX      TmnxLdpKeepAliveFactor
    MAX-ACCESS  read-write
    STATUS      current
    DESCRIPTION
        "The value of vRtrLdpNgIfParamIPv6KAFactor specifies the value by which
         the keepalive timeout (vRtrLdpNgIfParamKeepAliveTimeout) should be
         divided to give the keepalive time i.e. the time interval, in seconds,
         between LDP keepalive messages. LDP keepalive messages are sent to keep
         the LDP session from timing out when no other LDP traffic is being sent
         between the neighbors.

         This value is only applicable to LDP IPv6 interfaces."
    DEFVAL { 3 }
    ::= { vRtrLdpNgIfParamsEntry 3 }

vRtrLdpNgIfParamIPv4KATimeout    OBJECT-TYPE
    SYNTAX      TmnxLdpNewKeepAliveTimeout
    UNITS       "seconds"
    MAX-ACCESS  read-write
    STATUS      current
    DESCRIPTION
        "The value of vRtrLdpNgIfParamIPv4KATimeout specifies the time interval,
         in seconds, that LDP waits before tearing down a session. If no LDP
         messages are exchanged during this time interval, the LDP session is
         torn down. Generally the value of vRtrLdpNgIfParamIPv4KATimeout is
         configured to be 3 times the keepalive time (the time interval between
         successive LDP keepalive messages).

         This value is only applicable to LDP IPv4 interfaces."
    DEFVAL { 30 }
    ::= { vRtrLdpNgIfParamsEntry 4 }

vRtrLdpNgIfParamIPv6KATimeout    OBJECT-TYPE
    SYNTAX      TmnxLdpNewKeepAliveTimeout
    UNITS       "seconds"
    MAX-ACCESS  read-write
    STATUS      current
    DESCRIPTION
        "The value of vRtrLdpNgIfParamIPv6KATimeout specifies the time interval, in
         seconds, that LDP waits before tearing down a session. If no LDP
         messages are exchanged during this time interval, the LDP session is
         torn down. Generally the value of vRtrLdpNgIfParamIPv6KATimeout is
         configured to be 3 times the keepalive time (the time interval between
         successive LDP keepalive messages).

         This value is only applicable to LDP IPv6 interfaces."
    DEFVAL { 30 }
    ::= { vRtrLdpNgIfParamsEntry 5 }

vRtrLdpNgIfParamIPv4HelloFactor    OBJECT-TYPE
    SYNTAX      TmnxLdpHelloFactor
    MAX-ACCESS  read-write
    STATUS      current
    DESCRIPTION
        "The value of vRtrLdpNgIfParamIPv4HelloFactor specifies the value by 
         which the hello timeout (vRtrLdpNgIfParamIPv4HelloTimeout) should be
         divided to give the hello time i.e. the time interval, in seconds, 
         between LDP Hello messages. LDP uses hello messages to discover
         neighbors and to detect loss of connectivity with its neighbors.

         This value is only applicable to LDP IPv4 interfaces."
    DEFVAL { 3 }
    ::= { vRtrLdpNgIfParamsEntry 6 }

vRtrLdpNgIfParamIPv6HelloFactor    OBJECT-TYPE
    SYNTAX      TmnxLdpHelloFactor
    MAX-ACCESS  read-write
    STATUS      current
    DESCRIPTION
        "The value of vRtrLdpNgIfParamIPv6HelloFactor specifies the value by 
         which the hello timeout (vRtrLdpNgIfParamIPv6HelloTimeout) should be
         divided to give the hello time i.e. the time interval, in seconds, 
         between LDP Hello messages. LDP uses hello messages to discover
         neighbors and to detect loss of connectivity with its neighbors.

         This value is only applicable to LDP IPv6 interfaces."
    DEFVAL { 3 }
    ::= { vRtrLdpNgIfParamsEntry 7 }

vRtrLdpNgIfParamIPv4HelloTimeout    OBJECT-TYPE
    SYNTAX      TmnxLdpNewHelloTimeout
    UNITS       "seconds"
    MAX-ACCESS  read-write
    STATUS      current
    DESCRIPTION
        "The value of vRtrLdpNgIfParamIPv4HelloTimeout specifies the hello time 
         also known as hold time. It is the time interval, in seconds, that
         LDP waits before declaring a neighbor to be down. Hello timeout 
         is local to the system and is sent in the hello messages to a
         neighbor. Hello timeout cannot be set to a value that is less 
         than 3 times the hello time.

         This value is only applicable to LDP IPv4 interfaces."
    DEFVAL { 15 }
    ::= { vRtrLdpNgIfParamsEntry 8 }

vRtrLdpNgIfParamIPv6HelloTimeout    OBJECT-TYPE
    SYNTAX      TmnxLdpNewHelloTimeout
    UNITS       "seconds"
    MAX-ACCESS  read-write
    STATUS      current
    DESCRIPTION
        "The value of vRtrLdpNgIfParamIPv6HelloTimeout specifies the hello time 
         also known as hold time. It is the time interval, in seconds, that
         LDP waits before declaring a neighbor to be down. Hello timeout 
         is local to the system and is sent in the hello messages to a
         neighbor. Hello timeout cannot be set to a value that is less 
         than 3 times the hello time.

         This value is only applicable to LDP IPv6 interfaces."
    DEFVAL { 15 }
    ::= { vRtrLdpNgIfParamsEntry 9 }

vRtrLdpNgIfParamIPv4TransAddrTyp    OBJECT-TYPE
    SYNTAX      INTEGER {
                    interface (1),
                    system (2)
                }
    MAX-ACCESS  read-write
    STATUS      current
    DESCRIPTION
        "The value of vRtrLdpNgIfParamIPv4TransAddrTyp specifies the source
         of the transport address to be used when setting up the LDP TCP
         sessions.  The transport address can be configured globally
         (applied to all interfaces) or per interface.
             
         When the value of this object is 'interface', the interface's 
         IP address is used to setup the LDP session between neighbors.  
         If multiple interfaces exist between two neighbors, the 
         'interface' mode cannot be used since only one LDP session is 
         actually set up between the two neighbors.
             
         When the value of this object is 'system', the system's IP address
         is used to set up the LDP session between neighbors.

         This value is only applicable to LDP IPv4 interfaces."
    DEFVAL { system }
    ::= { vRtrLdpNgIfParamsEntry 10 }

vRtrLdpNgIfParamIPv6TransAddrTyp    OBJECT-TYPE
    SYNTAX      INTEGER {
                    interface (1),
                    system (2)
                }
    MAX-ACCESS  read-write
    STATUS      current
    DESCRIPTION
        "The value of vRtrLdpNgIfParamIPv6TransAddrTyp specifies the source
         of the transport address to be used when setting up the LDP TCP
         sessions.  The transport address can be configured globally
         (applied to all interfaces) or per interface.
             
         When the value of this object is 'interface', the interface's 
         IP address is used to setup the LDP session between neighbors.  
         If multiple interfaces exist between two neighbors, the 
         'interface' mode cannot be used since only one LDP session is 
         actually set up between the two neighbors.
             
         When the value of this object is 'system', the system's IP address
         is used to set up the LDP session between neighbors.

         This value is only applicable to LDP IPv6 interfaces."
    DEFVAL { system }
    ::= { vRtrLdpNgIfParamsEntry 11 }

--
--  The Virtual Router Label Distribution Protocol (LDP) Targeted Peer Table
--

vRtrLdpNgTargTableLstCh OBJECT-TYPE
    SYNTAX     TimeStamp
    MAX-ACCESS read-only
    STATUS     current
    DESCRIPTION
        "The value of vRtrLdpNgTargTableLstCh indicates the last
         timestamp when an entry in the vRtrLdpNgTargTable was last 
         changed."
    ::= { tmnxLdpNgObjs 52 }

vRtrLdpNgTargTable    OBJECT-TYPE
    SYNTAX      SEQUENCE OF VRtrLdpNgTargEntry
    MAX-ACCESS  not-accessible
    STATUS      current
    DESCRIPTION
         "vRtrLdpNgTargTable keeps information applicable to the LDP targeted
          peers.

          Use of AUGMENTS clause implies a one-to-one dependent relationship
          between the base table, vRtrLdpNgGeneralTable, and the augmenting
          table, vRtrLdpNgTargTable. This in effect extends the
          vRtrLdpNgGeneralTable with additional columns.  Creation or deletion
          of a row in the vRtrLdpNgGeneralTable results in the same fate for the
          row in the vRtrLdpNgTargTable."
    ::= { tmnxLdpNgObjs 53 }

vRtrLdpNgTargEntry    OBJECT-TYPE
    SYNTAX      VRtrLdpNgTargEntry
    MAX-ACCESS  not-accessible
    STATUS      current
    DESCRIPTION
        "A row in this table represents information applicable to the
         LDP targeted peers in virtual router instance."
    AUGMENTS  { vRtrLdpNgGeneralEntry }
    ::= { vRtrLdpNgTargTable 1 }

VRtrLdpNgTargEntry ::= SEQUENCE {
    vRtrLdpNgTargRowLastCh             TimeStamp,
    vRtrLdpNgTargImportPolicy1         TPolicyStatementNameOrEmpty,
    vRtrLdpNgTargImportPolicy2         TPolicyStatementNameOrEmpty,
    vRtrLdpNgTargImportPolicy3         TPolicyStatementNameOrEmpty,
    vRtrLdpNgTargImportPolicy4         TPolicyStatementNameOrEmpty,
    vRtrLdpNgTargImportPolicy5         TPolicyStatementNameOrEmpty,
    vRtrLdpNgTargExportPolicy1         TPolicyStatementNameOrEmpty,
    vRtrLdpNgTargExportPolicy2         TPolicyStatementNameOrEmpty,
    vRtrLdpNgTargExportPolicy3         TPolicyStatementNameOrEmpty,
    vRtrLdpNgTargExportPolicy4         TPolicyStatementNameOrEmpty,
    vRtrLdpNgTargExportPolicy5         TPolicyStatementNameOrEmpty,
    vRtrLdpNgTargTunnelPreference      TruthValue,
    vRtrLdpNgTargetedSessions          TruthValue,
    vRtrLdpNgTargIPv4KAFactor          TmnxLdpKeepAliveFactor,
    vRtrLdpNgTargIPv6KAFactor          TmnxLdpKeepAliveFactor,
    vRtrLdpNgTargIPv4KATimeout         TmnxLdpNewKeepAliveTimeout,
    vRtrLdpNgTargIPv6KATimeout         TmnxLdpNewKeepAliveTimeout,
    vRtrLdpNgTargIPv4HelloFactor       TmnxLdpHelloFactor,
    vRtrLdpNgTargIPv6HelloFactor       TmnxLdpHelloFactor,
    vRtrLdpNgTargIPv4HelloTimeout      TmnxLdpNewHelloTimeout,
    vRtrLdpNgTargIPv6HelloTimeout      TmnxLdpNewHelloTimeout,
    vRtrLdpNgTargIPv4HelloReduction    TruthValue,
    vRtrLdpNgTargIPv6HelloReduction    TruthValue,
    vRtrLdpNgTargIPv4HelloReduceFctr   Unsigned32,
    vRtrLdpNgTargIPv6HelloReduceFctr   Unsigned32
}

vRtrLdpNgTargRowLastCh OBJECT-TYPE
    SYNTAX     TimeStamp
    MAX-ACCESS read-only
    STATUS     current
    DESCRIPTION
        "The value of vRtrLdpNgTargRowLastCh indicates the timestamp when 
         this row was last modified."
    ::= { vRtrLdpNgTargEntry 1 }

vRtrLdpNgTargImportPolicy1 OBJECT-TYPE
    SYNTAX       TPolicyStatementNameOrEmpty
    MAX-ACCESS   read-write
    STATUS       current
    DESCRIPTION
        "The value of vRtrLdpNgTargImportPolicy1 specifies the import 
         route policy to determine which routes are accepted from targeted
         LDP neighbors.  A maximum of 5 policies can be specified.
         vRtrLdpNgTargImportPolicy1 specifies the first policy."
    DEFVAL { ''H }
    ::= { vRtrLdpNgTargEntry 2 }

vRtrLdpNgTargImportPolicy2 OBJECT-TYPE
    SYNTAX       TPolicyStatementNameOrEmpty
    MAX-ACCESS   read-write
    STATUS       current
    DESCRIPTION
        "The value of vRtrLdpNgTargImportPolicy2 specifies the second 
         import policy used to determine which routes are accepted from targeted
         LDP neighbors."  
    DEFVAL { ''H }
    ::= { vRtrLdpNgTargEntry 3 }

vRtrLdpNgTargImportPolicy3 OBJECT-TYPE
    SYNTAX       TPolicyStatementNameOrEmpty
    MAX-ACCESS   read-write
    STATUS       current
    DESCRIPTION
        "The value of vRtrLdpNgTargImportPolicy3 specifies the third 
         import policy used to determine which routes are accepted from targeted
         LDP neighbors."  
    DEFVAL { ''H }
    ::= { vRtrLdpNgTargEntry 4 }

vRtrLdpNgTargImportPolicy4 OBJECT-TYPE
    SYNTAX       TPolicyStatementNameOrEmpty
    MAX-ACCESS   read-write
    STATUS       current
    DESCRIPTION
        "The value of vRtrLdpNgTargImportPolicy4 specifies the fourth 
         import policy to determine which routes are accepted from targeted
         LDP neighbors."  
    DEFVAL { ''H }
    ::= { vRtrLdpNgTargEntry 5 }

vRtrLdpNgTargImportPolicy5 OBJECT-TYPE
    SYNTAX       TPolicyStatementNameOrEmpty
    MAX-ACCESS   read-write
    STATUS       current
    DESCRIPTION
        "The value of vRtrLdpNgTargImportPolicy5 specifies the fifth 
         import policy used to determine which routes are accepted from targeted
         LDP neighbors."  
    DEFVAL { ''H }
    ::= { vRtrLdpNgTargEntry 6 }

vRtrLdpNgTargExportPolicy1 OBJECT-TYPE
    SYNTAX       TPolicyStatementNameOrEmpty
    MAX-ACCESS   read-write
    STATUS       current
    DESCRIPTION
        "The value of vRtrLdpNgTargExportPolicy1 specifies the export 
         route policy used to determine which routes are exported to this 
         targeted LDP session.  A maximum of 5 policies can be specified.
         vRtrLdpNgTargExportPolicy1 specifies the first policy."  
    DEFVAL { ''H }
    ::= { vRtrLdpNgTargEntry 7 }

vRtrLdpNgTargExportPolicy2 OBJECT-TYPE
    SYNTAX       TPolicyStatementNameOrEmpty
    MAX-ACCESS   read-write
    STATUS       current
    DESCRIPTION
        "The value of vRtrLdpNgTargExportPolicy2 specifies the second 
         export policy used to determine which routes are exported to this 
         targeted LDP session"  
    DEFVAL { ''H }
    ::= { vRtrLdpNgTargEntry 8 }

vRtrLdpNgTargExportPolicy3 OBJECT-TYPE
    SYNTAX       TPolicyStatementNameOrEmpty
    MAX-ACCESS   read-write
    STATUS       current
    DESCRIPTION
        "The value of vRtrLdpNgTargExportPolicy3 specifies the third 
         export policy used to determine which routes are exported to this 
         targeted LDP session."
    DEFVAL { ''H }
    ::= { vRtrLdpNgTargEntry 9 }

vRtrLdpNgTargExportPolicy4 OBJECT-TYPE
    SYNTAX       TPolicyStatementNameOrEmpty
    MAX-ACCESS   read-write
    STATUS       current
    DESCRIPTION
        "The value of vRtrLdpNgTargExportPolicy4 specifies the fourth 
         export policy used to determine which routes are exported to this 
         targeted LDP session."
    DEFVAL { ''H }
    ::= { vRtrLdpNgTargEntry 10 }

vRtrLdpNgTargExportPolicy5 OBJECT-TYPE
    SYNTAX       TPolicyStatementNameOrEmpty
    MAX-ACCESS   read-write
    STATUS       current
    DESCRIPTION
        "The value of vRtrLdpNgTargExportPolicy5 specifies the fifth
         export policy used to determine which routes are exported to this 
         targeted LDP session."
    DEFVAL { ''H }
    ::= { vRtrLdpNgTargEntry 11 }

vRtrLdpNgTargTunnelPreference OBJECT-TYPE
    SYNTAX      TruthValue
    MAX-ACCESS  read-write
    STATUS      current
    DESCRIPTION
        "The value of vRtrLdpNgTargTunnelPreference indicates whether LDP 
         over tunnel is preferred when link-level LDP bindings are also 
         available. If this value is 'true', then LDP tunnels are 
         preferred and if the value is 'false' then LDP over tunnel is 
         preferred.

         By default LDP tunnels are preferred."
    DEFVAL { true }
    ::= { vRtrLdpNgTargEntry 12 }

vRtrLdpNgTargetedSessions    OBJECT-TYPE
    SYNTAX      TruthValue
    MAX-ACCESS  read-write
    STATUS      current
    DESCRIPTION
        "The value of vRtrLdpNgTargetedSessions specifies whether or
         not targeted sessions are allowed.  Targeted sessions are LDP
         sessions between indirectly connected peers.  The discovery
         messages for an indirect LDP session are addressed to the
         specified peer instead of to the multicast address.  When this
         object has a value of 'true', targeted sessions are enabled.
         When its value is 'false', targeted sessions are disabled."
    DEFVAL { true }
    ::= { vRtrLdpNgTargEntry 13 }

vRtrLdpNgTargIPv4KAFactor    OBJECT-TYPE
    SYNTAX      TmnxLdpKeepAliveFactor
    MAX-ACCESS  read-write
    STATUS      current
    DESCRIPTION
        "The value of vRtrLdpNgTargIPv4KAFactor specifies the value
         by which the keepalive timeout (vRtrLdpNgTargKATimeout)
         should be divided to give the keepalive time i.e. the time 
         interval, in seconds, between LDP keepalive messages. LDP 
         keepalive messages are sent to keep the LDP session from timing 
         out when no other LDP traffic is being sent between the neighbors.

         This value is only applicable to IPv4 targeted LDP peer."
    DEFVAL { 4 }
    ::= { vRtrLdpNgTargEntry 14 }

vRtrLdpNgTargIPv6KAFactor    OBJECT-TYPE
    SYNTAX      TmnxLdpKeepAliveFactor
    MAX-ACCESS  read-write
    STATUS      current
    DESCRIPTION
        "The value of vRtrLdpNgTargIPv6KAFactor specifies the value
         by which the keepalive timeout (vRtrLdpNgTargKATimeout)
         should be divided to give the keepalive time i.e. the time 
         interval, in seconds, between LDP keepalive messages. LDP 
         keepalive messages are sent to keep the LDP session from timing 
         out when no other LDP traffic is being sent between the neighbors.

         This value is only applicable to IPv6 targeted LDP peer."
    DEFVAL { 4 }
    ::= { vRtrLdpNgTargEntry 15 }

vRtrLdpNgTargIPv4KATimeout    OBJECT-TYPE
    SYNTAX      TmnxLdpNewKeepAliveTimeout
    UNITS       "seconds"
    MAX-ACCESS  read-write
    STATUS      current
    DESCRIPTION
        "The value of vRtrLdpNgTargIPv4KATimeout specifies the time 
         interval, in seconds, that LDP waits before tearing down a session.
         If no LDP messages are exchanged during this time interval, the LDP
         session is torn down. Generally the value of 
         vRtrLdpNgTargIPv4KATimeout is configured to be 3 times the
         keepalive time (the time interval between successive LDP keepalive
         messages).

         This value is only applicable to IPv4 LDP targeted peer."
    DEFVAL { 40 }
    ::= { vRtrLdpNgTargEntry 16 }

vRtrLdpNgTargIPv6KATimeout    OBJECT-TYPE
    SYNTAX      TmnxLdpNewKeepAliveTimeout
    UNITS       "seconds"
    MAX-ACCESS  read-write
    STATUS      current
    DESCRIPTION
        "The value of vRtrLdpNgTargIPv6KATimeout specifies the time 
         interval, in seconds, that LDP waits before tearing down a session.
         If no LDP messages are exchanged during this time interval, the LDP
         session is torn down. Generally the value of 
         vRtrLdpNgTargIPv6KATimeout is configured to be 3 times the
         keepalive time (the time interval between successive LDP keepalive
         messages).

         This value is only applicable to IPv6 LDP targeted peer."
    DEFVAL { 40 }
    ::= { vRtrLdpNgTargEntry 17 }

vRtrLdpNgTargIPv4HelloFactor    OBJECT-TYPE
    SYNTAX      TmnxLdpHelloFactor
    MAX-ACCESS  read-write
    STATUS      current
    DESCRIPTION
        "The value of vRtrLdpNgTargIPv4HelloFactor specifies the value by 
         which the hello timeout (vRtrLdpNgTargIPv4HelloTimeout) should be
         divided to give the hello time i.e. the time interval, in seconds, 
         between LDP Hello messages. LDP uses hello messages to discover
         neighbors and to detect loss of connectivity with its neighbors.

         This value is only applicable to IPv4 LDP targeted peer."
    DEFVAL { 3 }
    ::= { vRtrLdpNgTargEntry 18 }

vRtrLdpNgTargIPv6HelloFactor    OBJECT-TYPE
    SYNTAX      TmnxLdpHelloFactor
    MAX-ACCESS  read-write
    STATUS      current
    DESCRIPTION
        "The value of vRtrLdpNgTargIPv6HelloFactor specifies the value by 
         which the hello timeout (vRtrLdpNgTargIPv6HelloTimeout) should be
         divided to give the hello time i.e. the time interval, in seconds, 
         between LDP Hello messages. LDP uses hello messages to discover
         neighbors and to detect loss of connectivity with its neighbors.

         This value is only applicable to IPv6 LDP targeted peer."
    DEFVAL { 3 }
    ::= { vRtrLdpNgTargEntry 19 }

vRtrLdpNgTargIPv4HelloTimeout    OBJECT-TYPE
    SYNTAX      TmnxLdpNewHelloTimeout
    UNITS       "seconds"
    MAX-ACCESS  read-write
    STATUS      current
    DESCRIPTION
        "The value of vRtrLdpNgTargIPv4HelloTimeout specifies the hello time 
         also known as hold time. It is the time interval, in seconds, that
         LDP waits before declaring a neighbor to be down. Hello timeout 
         is local to the system and is sent in the hello messages to a
         neighbor. Hello timeout cannot be set to a value that is less 
         than 3 times the hello time.

         This value is only applicable to IPv4 LDP targeted peer."
    DEFVAL { 45 }
    ::= { vRtrLdpNgTargEntry 20 }

vRtrLdpNgTargIPv6HelloTimeout    OBJECT-TYPE
    SYNTAX      TmnxLdpNewHelloTimeout
    UNITS       "seconds"
    MAX-ACCESS  read-write
    STATUS      current
    DESCRIPTION
        "The value of vRtrLdpNgTargIPv6HelloTimeout specifies the hello time 
         also known as hold time. It is the time interval, in seconds, that
         LDP waits before declaring a neighbor to be down. Hello timeout 
         is local to the system and is sent in the hello messages to a
         neighbor. Hello timeout cannot be set to a value that is less 
         than 3 times the hello time.

         This value is only applicable to IPv6 LDP targeted peer."
    DEFVAL { 45 }
    ::= { vRtrLdpNgTargEntry 21 }

vRtrLdpNgTargIPv4HelloReduction  OBJECT-TYPE
    SYNTAX      TruthValue
    MAX-ACCESS  read-write
    STATUS      current
    DESCRIPTION
        "The value of vRtrLdpNgTargIPv4HelloReduction specifies whether hello
         reduction to this targeted peer is enabled or not. If enabled, the
         sender advertises further dampened vRtrLdpNgTargIPv4HelloTimeout, to
         the targeted peer after LDP session is established.

         The value of 'true' means targeted hello reduction is enabled."
    DEFVAL { false }
    ::= { vRtrLdpNgTargEntry 22 }

vRtrLdpNgTargIPv6HelloReduction  OBJECT-TYPE
    SYNTAX      TruthValue
    MAX-ACCESS  read-write
    STATUS      current
    DESCRIPTION
        "The value of vRtrLdpNgTargIPv6HelloReduction specifies whether hello
         reduction to this targeted peer is enabled or not. If enabled, the
         sender advertises further dampened vRtrLdpNgTargIPv6HelloTimeout, to
         the targeted peer after LDP session is established.

         The value of 'true' means targeted hello reduction is enabled."
    DEFVAL { false }
    ::= { vRtrLdpNgTargEntry 23 }

vRtrLdpNgTargIPv4HelloReduceFctr  OBJECT-TYPE
    SYNTAX      Unsigned32 (3..20)
    MAX-ACCESS  read-write
    STATUS      current
    DESCRIPTION
        "The value of vRtrLdpNgTargIPv4HelloReduceFctr specifies the number of
         hello messages that are sent at consistent
         vRtrLdpNgTargIPv4HelloTimeout, before advertising further dampened
         vRtrLdpNgTargIPv4HelloTimeout.

         An 'inconsistentValue' error is returned if this object is set when
         vRtrLdpNgTargIPv4HelloReduction is disabled."
    DEFVAL { 3 }
    ::= { vRtrLdpNgTargEntry 24 }

vRtrLdpNgTargIPv6HelloReduceFctr  OBJECT-TYPE
    SYNTAX      Unsigned32 (3..20)
    MAX-ACCESS  read-write
    STATUS      current
    DESCRIPTION
        "The value of vRtrLdpNgTargIPv6HelloReduceFctr specifies the number of
         hello messages that are sent at consistent
         vRtrLdpNgTargIPv6HelloTimeout, before advertising further dampened
         vRtrLdpNgTargIPv6HelloTimeout.

         An 'inconsistentValue' error is returned if this object is set when
         vRtrLdpNgTargIPv6HelloReduction is disabled."
    DEFVAL { 3 }
    ::= { vRtrLdpNgTargEntry 25 }


--
--  The Label Distribution Protocol (LDP) Aggregate Prefix Match Table
--

vRtrLdpNgAggrPreMatchTableLstCh OBJECT-TYPE
    SYNTAX     TimeStamp
    MAX-ACCESS read-only
    STATUS     current
    DESCRIPTION
        "The value of vRtrLdpNgAggrPreMatchTableLstCh indicates the last
         timestamp when an entry in the vRtrLdpNgAggrPreMatchTable was last 
         changed."
    ::= { tmnxLdpNgObjs 54 }

vRtrLdpNgAggrPreMatchTable    OBJECT-TYPE
    SYNTAX      SEQUENCE OF VRtrLdpNgAggrPreMatchEntry
    MAX-ACCESS  not-accessible
    STATUS      current
    DESCRIPTION
         "vRtrLdpNgAggrPreMatchTable keeps information about
          aggregate prefix match procedures.

          Use of AUGMENTS clause implies a one-to-one dependent
          relationship between the base table, vRtrLdpNgGeneralTable,
          and the augmenting table, vRtrLdpNgAggrPreMatchTable. This in
          effect extends the vRtrLdpNgGeneralTable with additional
          columns.  Creation or deletion of a row in the 
          vRtrLdpNgGeneralTable results in the same fate for the row 
          in the vRtrLdpNgAggrPreMatchTable."
    REFERENCE 
        "RFC5283 LDP Extension for Inter-Area Label Switched Paths (LSPs)"      
    ::= { tmnxLdpNgObjs 55 }

vRtrLdpNgAggrPreMatchEntry    OBJECT-TYPE
    SYNTAX      VRtrLdpNgAggrPreMatchEntry
    MAX-ACCESS  not-accessible
    STATUS      current
    DESCRIPTION
        "A row in this table represents information about the aggregate prefix 
         match procedures."
    AUGMENTS  { vRtrLdpNgGeneralEntry }
    ::= { vRtrLdpNgAggrPreMatchTable 1 }

VRtrLdpNgAggrPreMatchEntry ::= SEQUENCE {
    vRtrLdpNgAggrPreMatchRowLastCh          TimeStamp,
    vRtrLdpNgAggrPreMatchEnabled            TruthValue,
    vRtrLdpNgAggrPreMatchExcPolicy1         TPolicyStatementNameOrEmpty,
    vRtrLdpNgAggrPreMatchExcPolicy2         TPolicyStatementNameOrEmpty,
    vRtrLdpNgAggrPreMatchExcPolicy3         TPolicyStatementNameOrEmpty,
    vRtrLdpNgAggrPreMatchExcPolicy4         TPolicyStatementNameOrEmpty,
    vRtrLdpNgAggrPreMatchExcPolicy5         TPolicyStatementNameOrEmpty,
    vRtrLdpNgAggrPreMatchAdminState         TmnxAdminState
}

vRtrLdpNgAggrPreMatchRowLastCh OBJECT-TYPE
    SYNTAX     TimeStamp
    MAX-ACCESS read-only
    STATUS     current
    DESCRIPTION
        "The value of vRtrLdpNgAggrPreMatchRowLastCh indicates the timestamp when 
         this row was last modified."
    ::= { vRtrLdpNgAggrPreMatchEntry 1 }

vRtrLdpNgAggrPreMatchEnabled OBJECT-TYPE
    SYNTAX      TruthValue
    MAX-ACCESS  read-write
    STATUS      current
    DESCRIPTION
        "The value of vRtrLdpNgAggrPreMatchEnabled specifies whether aggregate 
        prefix match procedures are enabled."
    DEFVAL { false }    
    ::= { vRtrLdpNgAggrPreMatchEntry 2 }
    
vRtrLdpNgAggrPreMatchExcPolicy1 OBJECT-TYPE
    SYNTAX       TPolicyStatementNameOrEmpty
    MAX-ACCESS   read-write
    STATUS       current
    DESCRIPTION
        "The value of vRtrLdpNgAggrPreMatchExcPolicy1 specifies the policy 
         name containing the prefixes to be excluded from the aggregate prefix 
         match procedures. A maximum of 5 policies can be specified.  
         vRtrLdpNgAggrPreMatchExcPolicy1 specifies the
        first policy."
    DEFVAL { ''H }
    ::= { vRtrLdpNgAggrPreMatchEntry 3 }

vRtrLdpNgAggrPreMatchExcPolicy2 OBJECT-TYPE
    SYNTAX       TPolicyStatementNameOrEmpty
    MAX-ACCESS   read-write
    STATUS       current
    DESCRIPTION
        "The value of vRtrLdpNgAggrPreMatchExcPolicy2 specifies the second 
         policy name containing the prefixes to be excluded from the aggregate 
         prefix match procedures."  
    DEFVAL { ''H }
    ::= { vRtrLdpNgAggrPreMatchEntry 4 }

vRtrLdpNgAggrPreMatchExcPolicy3 OBJECT-TYPE
    SYNTAX       TPolicyStatementNameOrEmpty
    MAX-ACCESS   read-write
    STATUS       current
    DESCRIPTION
        "The value of vRtrLdpNgAggrPreMatchExcPolicy3 specifies the third 
         policy name containing the prefixes to be excluded from the aggregate 
         prefix match procedures." 
    DEFVAL { ''H }
    ::= { vRtrLdpNgAggrPreMatchEntry 5 }

vRtrLdpNgAggrPreMatchExcPolicy4 OBJECT-TYPE
    SYNTAX       TPolicyStatementNameOrEmpty
    MAX-ACCESS   read-write
    STATUS       current
    DESCRIPTION
        "The value of vRtrLdpNgAggrPreMatchExcPolicy4 specifies the fourth 
         policy name containing the prefixes to be excluded from the aggregate 
         prefix match procedures." 
    DEFVAL { ''H }
    ::= { vRtrLdpNgAggrPreMatchEntry 6 }

vRtrLdpNgAggrPreMatchExcPolicy5 OBJECT-TYPE
    SYNTAX       TPolicyStatementNameOrEmpty
    MAX-ACCESS   read-write
    STATUS       current
    DESCRIPTION
        "The value of vRtrLdpNgAggrPreMatchExcPolicy5 specifies the fifth 
         policy name containing the prefixes to be excluded from the aggregate 
         prefix match procedures." 
    DEFVAL { ''H }
    ::= { vRtrLdpNgAggrPreMatchEntry 7 }

vRtrLdpNgAggrPreMatchAdminState    OBJECT-TYPE
    SYNTAX      TmnxAdminState
    MAX-ACCESS  read-write
    STATUS      current
    DESCRIPTION
        "The value of vRtrLdpNgAggrPreMatchAdminState specifies whether the 
         aggregate prefix procedures will be used by LDP."
    DEFVAL { outOfService }
    ::= { vRtrLdpNgAggrPreMatchEntry 8 }
    
--
-- Notification Definitions
--

vRtrLdpNgSessMaxFecThresReached  NOTIFICATION-TYPE
    OBJECTS {
              vRtrLdpNgSessParamMaxFec,
              vRtrLdpNgSessOperMaxFecThreshold
    }
    STATUS current
    DESCRIPTION
        "[CAUSE] A vRtrLdpNgSessMaxFecThresReached notification is generated when
         the number of FECs accepted from the peer has exceeded
         vRtrLdpNgSessParamMaxFecThold percent of the value specified by
         vRtrLdpNgSessParamMaxFec or when the number of FECs exceeds
         vRtrLdpNgSessParamMaxFec limit.  New notification will not be generated 
         if multiple internal event change occurs during 15 minute interval.

         [EFFECT] No direct effect but if the peer LSR continues to send further
         Label Mapping Message, then the number of FECs may exceed the
         configured maximum (vRtrLdpNgSessParamMaxFec) resulting in any of the
         following:

         (2) If vRtrLdpNgSessParamMaxFecLogOnly is set to 'false' and LSR 
         Overload Capability is supported, then Overload procedure will take place.

         (2) If vRtrLdpNgSessParamMaxFecLogOnly is set to 'false' and LSR 
         Overload Capability is not supported, Label Mapping Message will be 
         returned with Label Release Message.

         (3) If vRtrLdpNgSessParamMaxFecLogOnly is set to 'true', no action will
         be taken.

         [RECOVERY] Appropriate Configuration changes in local or peer
         LSR will be required."
    ::= { tmnxLdpNgNotifications 1 }


--
-- Conformance Information
--

tmnxLdpNgV12v0Compliance  MODULE-COMPLIANCE
    STATUS  obsolete
    DESCRIPTION
            "The compliance statement for management of extended LDP
             on Alcatel-Lucent SROS series systems 12.0 release."
    MODULE  -- this module
        MANDATORY-GROUPS {
            tmnxLdpNgIfV12v0Group,
            tmnxLdpNgAdjV12v0Group,
            tmnxLdpNgSessionV12v0Group,
            tmnxLdpNgPeerParamsV12v0Group,
            tmnxLdpNgAddrFecV12v0Group,
            tmnxLdpNgP2MPFecV12v0Group,
            tmnxLdpNgServFecV12v0Group,
            tmnxLdpNgFec129V12v0Group,
            tmnxLdpNgCepTdmFecV12v0Group,
            tmnxLdpNgStaticFecV12v0Group,
            tmnxLdpNgSessionStatsV12v0Group,
            tmnxLdpNgTargPeerV12v0Group,
            tmnxLdpNgInetIfV12v0Group,
            tmnxLdpNgStatsV12v0Group,
            tmnxLdpNgCapabilityV12v0Group,
            tmnxLdpNgTcpSessParamsV12v0Group,
            tmnxLdpNgGeneralV12v0Group,
            tmnxLdpNgPolicyV12v0Group,
            tmnxLdpNgIfParamsV12v0Group,
            tmnxLdpNgTargetedPeerV12v0Group,
            tmnxLdpNgAggrPreMatchV12v0Group
        }
    ::= { tmnxLdpNgCompliances 1 }

tmnxLdpNgV13v0Compliance  MODULE-COMPLIANCE
    STATUS  current
    DESCRIPTION
            "The compliance statement for management of extended LDP
             on Alcatel-Lucent SROS series systems 13.0 release."
    MODULE  -- this module
        MANDATORY-GROUPS {
            tmnxLdpNgIfV12v0Group,
            tmnxLdpNgAdjV12v0Group,
            tmnxLdpNgSessionV12v0Group,
            tmnxLdpNgPeerParamsV12v0Group,
            tmnxLdpNgAddrFecV12v0Group,
            tmnxLdpNgP2MPFecV12v0Group,
            tmnxLdpNgServFecV12v0Group,
            tmnxLdpNgFec129V12v0Group,
            tmnxLdpNgCepTdmFecV12v0Group,
            tmnxLdpNgStaticFecV12v0Group,
            tmnxLdpNgSessionStatsV12v0Group,
            tmnxLdpNgTargPeerV12v0Group,
            tmnxLdpNgInetIfV12v0Group,
            tmnxLdpNgStatsV12v0Group,
            tmnxLdpNgCapabilityV12v0Group,
            tmnxLdpNgTcpSessParamsV12v0Group,
            tmnxLdpNgGeneralV12v0Group,
            tmnxLdpNgPolicyV12v0Group,
            tmnxLdpNgIfParamsV12v0Group,
            tmnxLdpNgTargetedPeerV12v0Group,
            tmnxLdpNgAggrPreMatchV12v0Group,
            tmnxLdpNgFecLimPerPeerV13v0Group,
            tmnxLdpNgFecLimitPerPeerNotify
        }
    ::= { tmnxLdpNgCompliances 2 }



tmnxLdpNgIfV12v0Group   OBJECT-GROUP
    OBJECTS {
            vRtrLdpNgIfTableLstChanged,
            vRtrLdpNgIfRowStatus,
            vRtrLdpNgIfLastChange,
            vRtrLdpNgIfAdminState,
            vRtrLdpNgIfOperState,
            vRtrLdpNgIfOperDownReason,
            vRtrLdpNgIfBfdEnabled,
            vRtrLdpNgInetIfStatsExistingAdj
            }
    STATUS      current
    DESCRIPTION
        "The group of objects supporting general management of extended LDP
         interfaces on Alcatel-Lucent SROS series systems 12.0 release."
    ::= { tmnxLdpNgGroups 1 }

tmnxLdpNgAdjV12v0Group     OBJECT-GROUP
    OBJECTS {   vRtrLdpNgHelloAdjLclLdpIdType,
                vRtrLdpNgHelloAdjLclLdpId,
                vRtrLdpNgHelloAdjEntityIndex,
                vRtrLdpNgHelloAdjIndex,
                vRtrLdpNgHelloAdjHoldTimeRem,
                vRtrLdpNgHelloAdjType,
                vRtrLdpNgHelloAdjRemConfSeqNum,
                vRtrLdpNgHelloAdjRemIpAddrType,
                vRtrLdpNgHelloAdjRemIpAddress,
                vRtrLdpNgHelloAdjUpTime,
                vRtrLdpNgHelloAdjLclConfSeqNum,
                vRtrLdpNgHelloAdjLclIpAddrType,
                vRtrLdpNgHelloAdjLclIpAddress,
                vRtrLdpNgHelloAdjInHelloMsgCnt,
                vRtrLdpNgHelloAdjOutHelloMsgCnt,
                vRtrLdpNgHelloAdjLclTimeout,
                vRtrLdpNgHelloAdjRemTimeout,
                vRtrLdpNgHelloAdjBfdStatus,
                vRtrLdpNgHelloAdjMapIndex
            }
    STATUS      current
    DESCRIPTION
        "The group of objects supporting management of extended LDP 
         Adjacencies for LDP sessions on Alcatel-Lucent SROS series systems
         12.0 Release."
    ::= { tmnxLdpNgGroups 2 }

tmnxLdpNgSessionV12v0Group    OBJECT-GROUP
    OBJECTS {   vRtrLdpNgSessLocalLdpIdType,
                vRtrLdpNgSessLocalLdpId,
                vRtrLdpNgSessEntityIndex,
                vRtrLdpNgSessLabelDistMethod,
                vRtrLdpNgSessLoopDetectForPV,
                vRtrLdpNgSessPathVectorLimit,
                vRtrLdpNgSessState,
                vRtrLdpNgSessAdjacencyType,
                vRtrLdpNgSessProtocolVersion,
                vRtrLdpNgSessLocalUdpPort,
                vRtrLdpNgSessPeerUdpPort,
                vRtrLdpNgSessLocalTcpPort,
                vRtrLdpNgSessPeerTcpPort,
                vRtrLdpNgSessLocalAddrType,
                vRtrLdpNgSessLocalAddress,
                vRtrLdpNgSessPeerAddrType,
                vRtrLdpNgSessPeerAddress,
                vRtrLdpNgSessKAHoldTimeRemaining,
                vRtrLdpNgSessMaxPduLength,
                vRtrLdpNgSessUpTime,
                vRtrLdpNgSessLocalKATimeout,
                vRtrLdpNgSessPeerKATimeout,
                vRtrLdpNgSessAdvertise,
                vRtrLdpNgSessLclGRHelperState,
                vRtrLdpNgSessPeerGRState,
                vRtrLdpNgSessPeerNumRestart,
                vRtrLdpNgSessLastRestartTime,
                vRtrLdpNgSessLocalFtReconTime,
                vRtrLdpNgSessPeerFtReconTime,
                vRtrLdpNgSessLocalFtRecovTime,
                vRtrLdpNgSessPeerFtRecovTime,
                vRtrLdpNgSessFtReconTimeRem,
                vRtrLdpNgSessFtRecovTimeRem, 
                vRtrLdpNgSessBfdStatus,
                vRtrLdpNgSessLocalP2MPCap,
                vRtrLdpNgSessPeerP2MPCap,
                vRtrLdpNgSessLocalMPMBBCap,
                vRtrLdpNgSessPeerMPMBBCap,
                vRtrLdpNgSessLocalDynCap,
                vRtrLdpNgSessPeerDynCap,
                vRtrLdpNgSessLocalOLoadCap,
                vRtrLdpNgSessPeerOLoadCap,
                vRtrLdpNgSessIPv4PfxFecOLoadSent,
                vRtrLdpNgSessIPv6PfxFecOLoadSent,
                vRtrLdpNgSessIPv4PfxFecOLoadRecv,
                vRtrLdpNgSessIPv6PfxFecOLoadRecv,
                vRtrLdpNgSessIPv4P2MPFecOLSent,
                vRtrLdpNgSessIPv6P2MPFecOLSent,
                vRtrLdpNgSessIPv4P2MPFecOLRecv,
                vRtrLdpNgSessIPv6P2MPFecOLRecv,
                vRtrLdpNgSessSvcFec128OLoadSent,
                vRtrLdpNgSessSvcFec128OLoadRecv,
                vRtrLdpNgSessSvcFec129OLoadSent,
                vRtrLdpNgSessSvcFec129OLoadRecv,
                vRtrLdpNgSessLocalIPv4PfxFecCap,
                vRtrLdpNgSessPeerIPv4PfxFecCap,
                vRtrLdpNgSessLocalIPv6PfxFecCap,
                vRtrLdpNgSessPeerIPv6PfxFecCap,
                vRtrLdpNgSessLocalSvcFec128Cap,
                vRtrLdpNgSessPeerSvcFec128Cap,
                vRtrLdpNgSessLocalSvcFec129Cap,
                vRtrLdpNgSessPeerSvcFec129Cap
            }
    STATUS      current
    DESCRIPTION
        "The group of objects supporting management of extended LDP 
         Sessions on Alcatel-Lucent SROS series systems 12.0 Release."
    ::= { tmnxLdpNgGroups 3 }

tmnxLdpNgSessionStatsV12v0Group    OBJECT-GROUP
    OBJECTS {   vRtrLdpNgSessStatsTargAdj,
                vRtrLdpNgSessStatsLinkAdj,
                vRtrLdpNgSessStatsHelloIn,
                vRtrLdpNgSessStatsHelloOut,
                vRtrLdpNgSessStatsKeepaliveIn,
                vRtrLdpNgSessStatsKeepaliveOut,
                vRtrLdpNgSessStatsInitIn,
                vRtrLdpNgSessStatsInitOut,
                vRtrLdpNgSessStatsLblMappingIn,
                vRtrLdpNgSessStatsLblMappingOut,
                vRtrLdpNgSessStatsLblRequestIn,
                vRtrLdpNgSessStatsLblRequestOut,
                vRtrLdpNgSessStatsLblReleaseIn,
                vRtrLdpNgSessStatsLblReleaseOut,
                vRtrLdpNgSessStatsLblWithdrawIn,
                vRtrLdpNgSessStatsLblWithdrawOut,
                vRtrLdpNgSessStatsLblAbortIn,
                vRtrLdpNgSessStatsLblAbortOut,
                vRtrLdpNgSessStatsAddrIn,
                vRtrLdpNgSessStatsAddrOut,
                vRtrLdpNgSessStatsAddrWithdrIn,
                vRtrLdpNgSessStatsAddrWithdrOut,
                vRtrLdpNgSessStatsNotifIn,
                vRtrLdpNgSessStatsNotifOut,
                vRtrLdpNgSessStatsIPv4PfxFecRcv,
                vRtrLdpNgSessStatsIPv6PfxFecRcv,
                vRtrLdpNgSessStatsIPv4PfxFecSnt,
                vRtrLdpNgSessStatsIPv6PfxFecSnt,
                vRtrLdpNgSessStatsIPv4P2MPFecRcv,
                vRtrLdpNgSessStatsIPv6P2MPFecRcv,
                vRtrLdpNgSessStatsIPv4P2MPFecSnt,
                vRtrLdpNgSessStatsIPv6P2MPFecSnt,
                vRtrLdpNgSessStatsSvcFec128Recv,
                vRtrLdpNgSessStatsSvcFec128Sent,
                vRtrLdpNgSessStatsSvcFec129Recv,
                vRtrLdpNgSessStatsSvcFec129Sent,
                vRtrLdpNgSessStatsIPv4AddrRecv,
                vRtrLdpNgSessStatsIPv6AddrRecv,
                vRtrLdpNgSessStatsIPv4AddrSent,
                vRtrLdpNgSessStatsIPv6AddrSent,
                vRtrLdpNgSessStatsCapabilityIn,
                vRtrLdpNgSessStatsCapabilityOut
            }
    STATUS      current
    DESCRIPTION
        "The group of objects supporting management of extended LDP 
         Session statistics on Alcatel-Lucent SROS series systems 12.0 Release."
    ::= { tmnxLdpNgGroups 4 }

tmnxLdpNgPeerParamsV12v0Group    OBJECT-GROUP
    OBJECTS {  vRtrLdpNgTargPeerLspRowStatus,
               vRtrLdpNgSessParamRowStatus, 
               vRtrLdpNgSessParamAuth,
               vRtrLdpNgSessParamAuthKey,
               vRtrLdpNgSessParamMinTTLValue, 
               vRtrLdpNgSessParamTTLLogId,
               vRtrLdpNgSessParamAuthKeyChain,
               vRtrLdpNgSessParamDODLblDistrib,
               vRtrLdpNgSessParamImportPolicy1,
               vRtrLdpNgSessParamImportPolicy2,
               vRtrLdpNgSessParamImportPolicy3,
               vRtrLdpNgSessParamImportPolicy4,
               vRtrLdpNgSessParamImportPolicy5,
               vRtrLdpNgSessParamExportPolicy1,
               vRtrLdpNgSessParamExportPolicy2,
               vRtrLdpNgSessParamExportPolicy3,
               vRtrLdpNgSessParamExportPolicy4,
               vRtrLdpNgSessParamExportPolicy5,
               vRtrLdpNgSessFec129CiscoInterop,
               vRtrLdpNgSessParamPMTUDiscovery,
               vRtrLdpNgSessParamAdvAdjAddrOnly,
               vRtrLdpNgSessAddrLclLdpIdType,
               vRtrLdpNgSessionAddrLocalLdpId,
               vRtrLdpNgSessionAddrNumInAddrs,
               vRtrLdpNgSessionAddrNumOutAddrs,
               vRtrLdpNgSessInAddrLclLdpIdType,
               vRtrLdpNgSessionInAddrLocalLdpId,
               vRtrLdpNgSessOutAddrLclLdpIdType,
               vRtrLdpNgSessionOutAddrLclLdpId,
               vRtrLdpNgTargPeerTunlLspTblLstCh,
               vRtrLdpNgSessionParamsTableLstCh,
               vRtrLdpNgSessPeIDMacFlushInterop,
               vRtrLdpNgSessParamIPv4PfxFecCap,
               vRtrLdpNgSessParamIPv6PfxFecCap,
               vRtrLdpNgSessParamP2MPFecCap
           }
    STATUS      current       
    DESCRIPTION
        "The group of objects supporting management of extended LDP 
         interfaces and targeted peers on Alcatel-Lucent SROS series systems
         12.0 release."
    ::= { tmnxLdpNgGroups 5 }

tmnxLdpNgAddrFecV12v0Group    OBJECT-GROUP
    OBJECTS {
                vRtrLdpNgAddrFecFlags,
                vRtrLdpNgAddrFecNumInLabels,
                vRtrLdpNgAddrFecNumOutLabels,
                vRtrLdpNgAddrFecInLbl,
                vRtrLdpNgAddrFecInLblStatus,
                vRtrLdpNgAddrFecInLblIfIndex,
                vRtrLdpNgAddrFecOutLbl,
                vRtrLdpNgAddrFecOutLblStatus,
                vRtrLdpNgAddrFecOutLblIfIndex,
                vRtrLdpNgAddrFecOutLblNHType,
                vRtrLdpNgAddrFecOutLblNHAddr,
                vRtrLdpNgAddrFecOutLblMetric,
                vRtrLdpNgAddrFecOutLblMtu,
                vRtrLdpNgAddrFecOutLblLspId,
                vRtrLdpNgAddrFecMapFlags,
                vRtrLdpNgAddrFecMapNumInLabels,
                vRtrLdpNgAddrFecMapNumOutLabels
            }
    STATUS      current
    DESCRIPTION
        "The group of objects supporting Address FEC's on Alcatel-Lucent SROS
         series systems 12.0 Release."
    ::= { tmnxLdpNgGroups 6 }

tmnxLdpNgP2MPFecV12v0Group    OBJECT-GROUP
    OBJECTS {
                vRtrLdpNgExtP2MPFecFlags,
                vRtrLdpNgExtP2MPFecNumInLabels,
                vRtrLdpNgExtP2MPFecNumOutLabels,
                vRtrLdpNgExtP2MPFecTunnelIfId,
                vRtrLdpNgExtP2MPFecMetric,
                vRtrLdpNgExtP2MPFecMTU,
                vRtrLdpNgExtP2MPFecInLbl,
                vRtrLdpNgExtP2MPFecInLblStatus,
                vRtrLdpNgExtP2MPFecOutLbl,
                vRtrLdpNgExtP2MPFecOutLblStatus,
                vRtrLdpNgExtP2MPFecOutLblNHType,
                vRtrLdpNgExtP2MPFecOutLblNHAdr,
                vRtrLdpNgExtP2MPFecOutLblIfIndex,   
                vRtrLdpNgExtP2MPFecOutLblLspId,
                vRtrLdpNgExtP2MPFecMapFlags,
                vRtrLdpNgExtP2MPFecMapNumInLbls,
                vRtrLdpNgExtP2MPFecMapNumOutLbls,
                vRtrLdpNgExtP2MPFecMapTunnelIfId,
                vRtrLdpNgExtP2MPFecMapMetric,
                vRtrLdpNgExtP2MPFecMapMTU
            }
    STATUS      current
    DESCRIPTION
        "The group of objects supporting P2MP FEC's on Alcatel-Lucent SROS
         series systems 12.0 Release."
    ::= { tmnxLdpNgGroups 7 }

tmnxLdpNgServFecV12v0Group     OBJECT-GROUP
    OBJECTS { 
              vLdpNgFec128ServType,                 
              vLdpNgFec128ServId,                   
              vLdpNgFec128VpnId,                  
              vLdpNgFec128Flags,                    
              vLdpNgFec128NumInLabels,
              vLdpNgFec128NumOutLabels,            
              vLdpNgFec128SdpId,             
              vLdpNgFec128MateEndptVcId,          
              vLdpNgFec128MateEndptSdpId, 
              vLdpNgFec128InLabel,
              vLdpNgFec128InLabelStatus,            
              vLdpNgFec128InLabelSigStatus,        
              vLdpNgFec128InLblWdwReason,        
              vLdpNgFec128InLblMaxCellConcat,       
              vLdpNgFec128InLblFLTxCap,      
              vLdpNgFec128InLblFLRxCap,
              vLdpNgFec128InLblIPv4CeIpAdType,        
              vLdpNgFec128InLblIPv4CeIpAddr,        
              vLdpNgFec128InLblIPv4Cap,       
              vLdpNgFec128InLblIPv6Cap,        
              vLdpNgFec128InLblMTU,     
              vLdpNgFec128InLblVlanTag,             
              vLdpNgFec128InLblVccvCV,             
              vLdpNgFec128InLblVccvCC,            
              vLdpNgFec128InLblPwStatus, 
              vLdpNgFec128OutLabel,
              vLdpNgFec128OutLabelStatus,
              vLdpNgFec128OutLabelSigStatus,
              vLdpNgFec128OutLblMaxCellConcat,
              vLdpNgFec128OutLblFLTxCap,
              vLdpNgFec128OutLblFLRxCap,
              vLdpNgFec128OutLblIPv4CeAddrType,
              vLdpNgFec128OutLblIPv4CeIpAddr,
              vLdpNgFec128OutLblIPv4Cap,
              vLdpNgFec128OutLblIPv6Cap,
              vLdpNgFec128OutLblMTU,
              vLdpNgFec128OutLblVlanTag,
              vLdpNgFec128OutLblVccvCV, 
              vLdpNgFec128OutLblVccvCC,
              vLdpNgFec128OutLblPwStatus
              }
    STATUS      current
    DESCRIPTION
        "The group of objects supporting management of extended LDP 
         service FECs sent to or received from an LDP peer
         on Alcatel-Lucent SROS series systems release 12.0."
    ::= { tmnxLdpNgGroups 8 }

tmnxLdpNgFec129V12v0Group     OBJECT-GROUP
    OBJECTS {             
             vLdpNgFec129ServType,
             vLdpNgFec129ServId,
             vLdpNgFec129VpnId,
             vLdpNgFec129Flags,
             vLdpNgFec129NumInLabels,
             vLdpNgFec129NumOutLabels,   
             vLdpNgFec129SdpId,
             vLdpNgFec129MateAgiType,
             vLdpNgFec129MateAgiLen,
             vLdpNgFec129MateAgiVal,
             vLdpNgFec129MateSrcAiiType,
             vLdpNgFec129MateSrcAiiLen,
             vLdpNgFec129MateSrcAiiVal,
             vLdpNgFec129MateTgtAiiType,
             vLdpNgFec129MateTgtAiiLen,
             vLdpNgFec129MateTgtAiiVal,
             vLdpNgFec129MateSdpId,
             vLdpNgFec129InLabel,
             vLdpNgFec129InLabelStatus,   
             vLdpNgFec129InLblMTU,
             vLdpNgFec129InLblVlanTag,
             vLdpNgFec129InLblMaxCellConcat,
             vLdpNgFec129InLblSigStatus,
             vLdpNgFec129InLblIPv4Cap,
             vLdpNgFec129InLblIPv6Cap,
             vLdpNgFec129InLblIPv4CeAddrType,
             vLdpNgFec129InLblIPv4CeIpAddr,
             vLdpNgFec129InLblWdwReason,
             vLdpNgFec129InLblFLTxCap,
             vLdpNgFec129InLblFLRxCap,
             vLdpNgFec129InLblVccvCV,
             vLdpNgFec129InLblVccvCC,
             vLdpNgFec129InLblPwStatus, 
             vLdpNgFec129OutLabel,
             vLdpNgFec129OutLabelStatus,   
             vLdpNgFec129OutLblMTU,
             vLdpNgFec129OutLblVlanTag,
             vLdpNgFec129OutLblMaxCellConcat,
             vLdpNgFec129OutLblSigStatus,
             vLdpNgFec129OutLblIPv4Cap,
             vLdpNgFec129OutLblIPv6Cap,
             vLdpNgFec129OutLblIPv4CeAddrType,
             vLdpNgFec129OutLblIPv4CeIpAddr,
             vLdpNgFec129OutLblFLTxCap,
             vLdpNgFec129OutLblFLRxCap,
             vLdpNgFec129OutLblVccvCV,
             vLdpNgFec129OutLblVccvCC,
             vLdpNgFec129OutLblPwStatus
     }
    STATUS      current
    DESCRIPTION
        "The group of objects supporting management of LDP 
         FEC-129s sent to or received from an LDP peer
         on Alcatel-Lucent SROS series systems release 12.0."
    ::= { tmnxLdpNgGroups 9 }

tmnxLdpNgCepTdmFecV12v0Group     OBJECT-GROUP
    OBJECTS {   
                vLdpNgCepTdmFec128InLblPayldSize,
                vLdpNgCepTdmFec128InLblBitrate,
                vLdpNgCepTdmFec128InLblRtpHeader,
                vLdpNgCepTdmFec128InLblDiffTStmp,
                vLdpNgCepTdmFec128InLblSigPkts,
                vLdpNgCepTdmFec128InLblCasTrunk,
                vLdpNgCepTdmFec128InLblTStmpFreq,
                vLdpNgCepTdmFec128InLblPayldType,
                vLdpNgCepTdmFec128InLblSsrcId,
                vLdpNgCepTdmFec128OutLblPyldSze,
                vLdpNgCepTdmFec128OutLblBitrate,
                vLdpNgCepTdmFec128OutLblRtpHdr,
                vLdpNgCepTdmFec128OutLblDfTstmp,
                vLdpNgCepTdmFec128OutLblSigPkts,
                vLdpNgCepTdmFec128OutLblCasTrnk,
                vLdpNgCepTdmFec128OutLblTstmpFq,
                vLdpNgCepTdmFec128OutLblPyldTyp,
                vLdpNgCepTdmFec128OutLblSsrcId,
                vLdpNgCepTdmFec129InLblPayldSize,
                vLdpNgCepTdmFec129InLblBitrate,
                vLdpNgCepTdmFec129InLblRtpHeader,
                vLdpNgCepTdmFec129InLblDiffTStmp,
                vLdpNgCepTdmFec129InLblSigPkts,
                vLdpNgCepTdmFec129InLblCasTrunk,
                vLdpNgCepTdmFec129InLblTStmpFreq,
                vLdpNgCepTdmFec129InLblPayldType,
                vLdpNgCepTdmFec129InLblSsrcId,
                vLdpNgCepTdmFec129OutLblPyldSize,
                vLdpNgCepTdmFec129OutLblBitrate,
                vLdpNgCepTdmFec129OutLblRtpHdr,
                vLdpNgCepTdmFec129OutLblDifTStmp,
                vLdpNgCepTdmFec129OutLblSigPkts,
                vLdpNgCepTdmFec129OutLblCasTrnk,
                vLdpNgCepTdmFec129OutLblTStmpFrq,
                vLdpNgCepTdmFec129OutLblPyldType,
                vLdpNgCepTdmFec129OutLblSsrcId            
     }
    STATUS      current
    DESCRIPTION
        "The group of objects supporting management of extended LDP 
         CEP/TDM FECs sent to or received from an LDP peer
         on Alcatel-Lucent SROS series systems release 12.0."
    ::= { tmnxLdpNgGroups 10 }
    
tmnxLdpNgStaticFecV12v0Group    OBJECT-GROUP
    OBJECTS {   
                vRtrLdpNgStaticFecTableLstCh,
                vRtrLdpNgStaticFecRowStatus,
                vRtrLdpNgStaticFecNumInLabel,
                vRtrLdpNgStaticFecNumOutLabel,
                vRtrLdpNgSFecInLabelRowStatus,
                vRtrLdpNgSFecOperInLabel,
                vRtrLdpNgSFecOutLabelRowStatus,
                vRtrLdpNgSFecOutLabel
            }
    STATUS      current
    DESCRIPTION
        "The group of objects supporting management of LDP Static
         FECs on Alcatel-Lucent SROS series systems 12.0 release."
    ::= { tmnxLdpNgGroups 11 }

tmnxLdpNgTargPeerV12v0Group    OBJECT-GROUP
    OBJECTS {   
                vRtrLdpNgTargPeerTableLstCh,
                vRtrLdpNgTargPeerRowStatus,
                vRtrLdpNgTargPeerLastChange,
                vRtrLdpNgTargPeerAdminState,
                vRtrLdpNgTargPeerOperState,
                vRtrLdpNgTargPeerUpTime,
                vRtrLdpNgTargPeerOperDownReason,
                vRtrLdpNgTargPeerInheritance,
                vRtrLdpNgTargPeerKAFactor,
                vRtrLdpNgTargPeerKATimeout,
                vRtrLdpNgTargPeerHelloFactor,
                vRtrLdpNgTargPeerHelloTimeout,
                vRtrLdpNgTargPeerOprHelloTimeout,
                vRtrLdpNgTargPeerHelloReduction,
                vRtrLdpNgTargPeerHelloRdctnFctr,
                vRtrLdpNgTargPeerBackoffTime,
                vRtrLdpNgTargPeerMaxBackoffTime,
                vRtrLdpNgTargPeerTunneling,
                vRtrLdpNgTargPeerBfdEnabled,
                vRtrLdpNgTargPeerLsrIfIndex,
                vRtrLdpNgTargPeerAutoCreate,
                vRtrLdpNgTargPeerCreator,
                vRtrLdpNgTargPeerTemplName,
                vRtrLdpNgTargPeerStatExistingAdj
            }
    STATUS      current
    DESCRIPTION
        "The group of objects supporting management of extended LDP 
         targetted peer on Alcatel-Lucent SROS series systems release 12.0."
    ::= { tmnxLdpNgGroups 14 }            

tmnxLdpNgInetIfV12v0Group    OBJECT-GROUP
    OBJECTS {   
                vRtrLdpNgInetIfTableLstCh,
                vRtrLdpNgInetIfRowStatus,
                vRtrLdpNgInetIfUpTime,
                vRtrLdpNgInetIfLastChange,
                vRtrLdpNgInetIfAdminState,
                vRtrLdpNgInetIfOperState,
                vRtrLdpNgInetIfOperDownReason,
                vRtrLdpNgInetIfInheritance, 
                vRtrLdpNgInetIfKAFactor,
                vRtrLdpNgInetIfKATimeout,
                vRtrLdpNgInetIfHelloFactor,
                vRtrLdpNgInetIfHelloTimeout,
                vRtrLdpNgInetIfOperHelloTimeout,
                vRtrLdpNgInetIfBackoffTime,
                vRtrLdpNgInetIfMaxBackoffTime,
                vRtrLdpNgInetIfTransAddrType,
                vRtrLdpNgInetIfLsrIfType,
                vRtrLdpNgInetIfLsrIfIndex,
                vRtrLdpNgInetIfIPv4P2MPFecCap,
                vRtrLdpNgInetIfIPv6P2MPFecCap,
                vRtrLdpNgInetIfIPv4PfxFecCap,
                vRtrLdpNgInetIfIPv6PfxFecCap
            }
    STATUS      current
    DESCRIPTION
        "The group of objects supporting management of extended LDP 
         Inet family interfaces on Alcatel-Lucent SROS series systems 
         release 12.0."
    ::= { tmnxLdpNgGroups 15 }

tmnxLdpNgStatsV12v0Group    OBJECT-GROUP
    OBJECTS {
                vLdpNgStatsOperDownEvents,  
                vLdpNgStatsIPv4ActiveSess,        
                vLdpNgStatsIPv6ActiveSess,
                vLdpNgStatsIPv4ActiveLinkAdj,
                vLdpNgStatsIPv6ActiveLinkAdj,
                vLdpNgStatsIPv4ActiveTargAdj,
                vLdpNgStatsIPv6ActiveTargAdj,
                vLdpNgStatsIPv4ActiveIf,
                vLdpNgStatsIPv6ActiveIf,
                vLdpNgStatsIPv4InactiveIf,
                vLdpNgStatsIPv6InactiveIf,
                vLdpNgStatsIPv4ActiveTargPeers,
                vLdpNgStatsIPv6ActiveTargPeers,
                vLdpNgStatsIPv4InactiveTargPeers,
                vLdpNgStatsIPv6InactiveTargPeers,
                vLdpNgStatsIPv4PfxFecRecv,
                vLdpNgStatsIPv6PfxFecRecv, 
                vLdpNgStatsIPv4PfxFecSent,
                vLdpNgStatsIPv6PfxFecSent,
                vLdpNgStatsFec128FecSent,
                vLdpNgStatsFec128FecRecv,  
                vLdpNgStatsFec129FecSent,
                vLdpNgStatsFec129FecRecv,
                vLdpNgStatsIPv4AttemptedSessions,
                vLdpNgStatsIPv6AttemptedSessions,
                vLdpNgStatsSessRejNoHelloErrs,
                vLdpNgStatsSessRejAdvErrors,
                vLdpNgStatsSessRejMaxPduErrs,
                vLdpNgStatsSessRejLblRngeErrs,
                vLdpNgStatsBadLdpIdErrors,
                vLdpNgStatsBadPduLengthErrors,
                vLdpNgStatsBadMsgLengthErrors,
                vLdpNgStatsBadTlvLengthErrors,
                vLdpNgStatsMalformedTlvErrors,
                vLdpNgStatsKeepAliveExpErrors,
                vLdpNgStatsShutdownNotifRecv,
                vLdpNgStatsShutdownNotifSent,
                vLdpNgStatsIPv4EgrFecPfxCount,
                vLdpNgStatsIPv6EgrFecPfxCount,
                vLdpNgStatsUnknownTlvErrors, 
                vLdpNgStatsIPv4P2MPFecSent,
                vLdpNgStatsIPv6P2MPFecSent,  
                vLdpNgStatsIPv4P2MPFecRecv,
                vLdpNgStatsIPv6P2MPFecRecv,
                vLdpNgStatsIPv4PfxFecOLSessSent,
                vLdpNgStatsIPv6PfxFecOLSessSent,
                vLdpNgStatsIPv4PfxFecOLSessRecv,
                vLdpNgStatsIPv6PfxFecOLSessRecv,
                vLdpNgStatsIPv4P2MPFecOLSessSent,
                vLdpNgStatsIPv6P2MPFecOLSessSent,
                vLdpNgStatsIPv4P2MPFecOLSessRecv,
                vLdpNgStatsIPv6P2MPFecOLSessRecv,
                vLdpNgStatsFec128FecOLSessSent,
                vLdpNgStatsFec128FecOLSessRecv,
                vLdpNgStatsFec129FecOLSessSent,
                vLdpNgStatsFec129FecOLSessRecv,
                vLdpNgStatsIPv4OLoadInterfaces,
                vLdpNgStatsIPv6OLoadInterfaces,
                vLdpNgStatsIPv4OLoadTargPeers,
                vLdpNgStatsIPv6OLoadTargPeers,
                vLdpNgStatsIPv4PfxFecInOLoad,
                vLdpNgStatsIPv6PfxFecInOLoad,
                vLdpNgStatsIPv4P2MPFecInOLoad,
                vLdpNgStatsIPv6P2MPFecInOLoad,
                vLdpNgStatsFec128FecInOLoad,
                vLdpNgStatsFec129FecInOLoad
            }
    STATUS      current
    DESCRIPTION
        "The group of objects supporting management of extended LDP 
         statistics on Alcatel-Lucent SROS series systems release 12.0."
    ::= { tmnxLdpNgGroups 16 }
    
tmnxLdpNgCapabilityV12v0Group    OBJECT-GROUP
    OBJECTS {  
                vRtrLdpNgGenP2MPCapability,
                vRtrLdpNgGenMPMBBCapability,
                vRtrLdpNgGenDynamicCapability,
                vRtrLdpNgGenOverloadCapability,
                vRtrLdpNgGenFec128Capability,
                vRtrLdpNgGenFec129Capability,
                vRtrLdpNgGenIPv4PfxFecCapability,
                vRtrLdpNgGenIPv6PfxFecCapability
            }
    STATUS      current
    DESCRIPTION
        "The group of objects supporting management of extended LDP 
         capabilities on Alcatel-Lucent SROS series systems release 12.0."
    ::= { tmnxLdpNgGroups 17 }
    
tmnxLdpNgTcpSessParamsV12v0Group    OBJECT-GROUP
    OBJECTS {  
                vRtrLdpNgTcpSessParamsTableLstCh,
                vRtrLdpNgTcpSessRowStatus,
                vRtrLdpNgTcpSessAuth,
                vRtrLdpNgTcpSessAuthKey,
                vRtrLdpNgTcpSessAuthKeyChain,
                vRtrLdpNgTcpSessPMTUDiscovery
            }
    STATUS      current
    DESCRIPTION
        "The group of objects supporting management of extended LDP 
         TCP session parameters on Alcatel-Lucent SROS series systems 
         release 12.0."
    ::= { tmnxLdpNgGroups 18 }
    
tmnxLdpNgGeneralV12v0Group   OBJECT-GROUP
    OBJECTS {       
                vRtrLdpNgGeneralTableLstCh,
                vRtrLdpNgGenCreateTime,
                vRtrLdpNgGenUpTime,
                vRtrLdpNgGenRowLastCh,
                vRtrLdpNgGenLastChange,
                vRtrLdpNgGenAdminState,
                vRtrLdpNgGenOperState,
                vRtrLdpNgGenOperDownReason,
                vRtrLdpNgGenLdpIPv4LsrId,
                vRtrLdpNgGenLdpIPv6LsrId,
                vRtrLdpNgGenProtocolVersion,
                vRtrLdpNgGenBackoffTime,
                vRtrLdpNgGenMaxBackoffTime,
                vRtrLdpNgGenTunnelDownDampTime,
                vRtrLdpNgGenGracefulRestart,
                vRtrLdpNgGenGRNbrLiveTime,
                vRtrLdpNgGenGRMaxRecoveryTime,
                vRtrLdpNgGenLabelWithdrawalDelay,
                vRtrLdpNgGenImplicitNull,
                vRtrLdpNgGenShortTTLPropLocal,
                vRtrLdpNgGenShortTTLPropTransit,
                vRtrLdpNgGenMPMBBTime,
                vRtrLdpNgGenLdpFrr,
                vRtrLdpNgGenMcastUpstreamFrr,
                vRtrLdpNgGenDeaggregateFec,
                vRtrLdpNgGenControlMode,
                vRtrLdpNgGenDistMethod,
                vRtrLdpNgGenRetentionMode,
                vRtrLdpNgGenPropagatePolicy,
                vRtrLdpNgGenLoopDetectCap,
                vRtrLdpNgGenHopLimit,
                vRtrLdpNgGenPathVectorLimit,
                vRtrLdpNgGenRoutePreference
            }
    STATUS      current
    DESCRIPTION
        "The group of objects supporting general management of extended LDP 
         on Alcatel-Lucent SROS series systems 12.0 release."
    ::= { tmnxLdpNgGroups 19 }

tmnxLdpNgPolicyV12v0Group   OBJECT-GROUP
    OBJECTS {       
                vRtrLdpNgPolicyTableLstCh,
                vRtrLdpNgPolRowLastCh,
                vRtrLdpNgPolImportPolicy1,
                vRtrLdpNgPolImportPolicy2,
                vRtrLdpNgPolImportPolicy3,
                vRtrLdpNgPolImportPolicy4,
                vRtrLdpNgPolImportPolicy5,
                vRtrLdpNgPolExportPolicy1,
                vRtrLdpNgPolExportPolicy2,
                vRtrLdpNgPolExportPolicy3,
                vRtrLdpNgPolExportPolicy4,
                vRtrLdpNgPolExportPolicy5,
                vRtrLdpNgPolTunlTblExportPolicy1,
                vRtrLdpNgPolTunlTblExportPolicy2,
                vRtrLdpNgPolTunlTblExportPolicy3,
                vRtrLdpNgPolTunlTblExportPolicy4,
                vRtrLdpNgPolTunlTblExportPolicy5
            }
    STATUS      current
    DESCRIPTION
        "The group of objects supporting policies of extended LDP protocol 
         on Alcatel-Lucent SROS series systems 12.0 release."
    ::= { tmnxLdpNgGroups 20 }

tmnxLdpNgIfParamsV12v0Group   OBJECT-GROUP
    OBJECTS {       
                vRtrLdpNgIfParamsTableLstCh,
                vRtrLdpNgIfParamRowLastCh,
                vRtrLdpNgIfParamIPv4KAFactor,
                vRtrLdpNgIfParamIPv6KAFactor,
                vRtrLdpNgIfParamIPv4KATimeout,
                vRtrLdpNgIfParamIPv6KATimeout,
                vRtrLdpNgIfParamIPv4HelloFactor,
                vRtrLdpNgIfParamIPv6HelloFactor,
                vRtrLdpNgIfParamIPv4HelloTimeout,
                vRtrLdpNgIfParamIPv6HelloTimeout,
                vRtrLdpNgIfParamIPv4TransAddrTyp,
                vRtrLdpNgIfParamIPv6TransAddrTyp
            }
    STATUS      current
    DESCRIPTION
        "The group of objects supporting interface parameters of extended LDP 
         on Alcatel-Lucent SROS series systems 12.0 release."
    ::= { tmnxLdpNgGroups 21 }

tmnxLdpNgTargetedPeerV12v0Group   OBJECT-GROUP
    OBJECTS {   
                vRtrLdpNgTargTableLstCh,
                vRtrLdpNgTargRowLastCh,
                vRtrLdpNgTargImportPolicy1,
                vRtrLdpNgTargImportPolicy2,
                vRtrLdpNgTargImportPolicy3,
                vRtrLdpNgTargImportPolicy4,
                vRtrLdpNgTargImportPolicy5,
                vRtrLdpNgTargExportPolicy1,
                vRtrLdpNgTargExportPolicy2,
                vRtrLdpNgTargExportPolicy3,
                vRtrLdpNgTargExportPolicy4,
                vRtrLdpNgTargExportPolicy5,
                vRtrLdpNgTargTunnelPreference,
                vRtrLdpNgTargetedSessions,
                vRtrLdpNgTargIPv4KAFactor,
                vRtrLdpNgTargIPv6KAFactor,
                vRtrLdpNgTargIPv4KATimeout,
                vRtrLdpNgTargIPv6KATimeout,
                vRtrLdpNgTargIPv4HelloFactor,
                vRtrLdpNgTargIPv6HelloFactor,
                vRtrLdpNgTargIPv4HelloTimeout,
                vRtrLdpNgTargIPv6HelloTimeout,
                vRtrLdpNgTargIPv4HelloReduction,
                vRtrLdpNgTargIPv6HelloReduction,
                vRtrLdpNgTargIPv4HelloReduceFctr,
                vRtrLdpNgTargIPv6HelloReduceFctr
            }
    STATUS      current
    DESCRIPTION
        "The group of objects supporting Targeted Peers of extended LDP 
         on Alcatel-Lucent SROS series systems 12.0 release."
    ::= { tmnxLdpNgGroups 22 }
    
tmnxLdpNgAggrPreMatchV12v0Group   OBJECT-GROUP
    OBJECTS {   
                vRtrLdpNgAggrPreMatchTableLstCh,
                vRtrLdpNgAggrPreMatchRowLastCh,
                vRtrLdpNgAggrPreMatchEnabled,
                vRtrLdpNgAggrPreMatchExcPolicy1,
                vRtrLdpNgAggrPreMatchExcPolicy2,
                vRtrLdpNgAggrPreMatchExcPolicy3,
                vRtrLdpNgAggrPreMatchExcPolicy4,
                vRtrLdpNgAggrPreMatchExcPolicy5,
                vRtrLdpNgAggrPreMatchAdminState
            }
    STATUS      current
    DESCRIPTION
        "The group of objects supporting Aggregate Prefix Match policies of 
         extended LDP on Alcatel-Lucent SROS series systems 12.0 release."
    ::= { tmnxLdpNgGroups 23 }    

tmnxLdpNgFecLimPerPeerV13v0Group    OBJECT-GROUP
    OBJECTS { vRtrLdpNgSessParamMaxFec,
              vRtrLdpNgSessParamMaxFecLogOnly,
              vRtrLdpNgSessParamMaxFecThold,
              vRtrLdpNgSessOperMaxFecThreshold
            }
    STATUS      current
    DESCRIPTION
        "The group of notifications supporting LSR FEC limit per LDP peer 
         feature on Alcatel-Lucent SROS series systems."
    ::= { tmnxLdpNgGroups 24 }

tmnxLdpNgFecLimitPerPeerNotify NOTIFICATION-GROUP
    NOTIFICATIONS   {   vRtrLdpNgSessMaxFecThresReached
                    }
    STATUS      current
    DESCRIPTION
        "The group of notifications supporting LSR FEC limit per LDP peer 
         feature on Alcatel-Lucent SROS series systems."
    ::= { tmnxLdpNgGroups 25 }    
        
END
