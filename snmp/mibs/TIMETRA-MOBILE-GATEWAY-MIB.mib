--       TIMETRA MOBILE GATEWAY 
--       Management Information Base

TIMETRA-MOBILE-GATEWAY-MIB DEFINITIONS ::= BEGIN

IMPORTS
   MODULE-IDENTITY, OBJECT-TYPE, NOTIFICATION-TYPE, Unsigned32, Counter32,
   Gauge32, Integer32 
       FROM SNMPv2-SMI

   MODULE-COMPLIANCE, OBJECT-GROUP, NOTIFICATION-GROUP
       FROM SNMPv2-CONF

   RowStatus, TimeStamp
       FROM SNMPv2-TC

   InetAddress, InetAddressType, InetPortNumber
       FROM INET-ADDRESS-MIB

   timetraSRMIBModules, tmnxSRObjs, tmnxSRConfs, tmnxSRNotifyPrefix
       FROM TIMETRA-GLOBAL-MIB

   TmnxVRtrID, TItemDescription, TmnxOperState, TmnxEnabledDisabled,
   TmnxThresholdGroupType, TNamedItem, TNamedItemOrEmpty
       FROM TIMETRA-TC-MIB

   TmnxMobGwType, TmnxMobPeerType, TmnxMobProfName, TmnxMobGwId,
   TmnxMobPathMgmtState, TmnxMobDiaPathMgmtState,
   TmnxMobDiaDetailPathMgmtState, TmnxMobDfPeerId,
   TmnxMobLiTarget, TmnxMobLiTargetType
       FROM TIMETRA-TC-MG-MIB

   tmnxChassisIndex, tmnxCardSlotNum
       FROM TIMETRA-CHASSIS-MIB

   vRtrID
       FROM TIMETRA-VRTR-MIB

   tmnxMobProfDiaPeerName, tmnxMobProfDiaPeerListIndex, 
   tmnxMobGtpPriServerAddrType, tmnxMobGtpPriServerAddr,
   tmnxMobGtpPriServerPort
       FROM TIMETRA-MOBILE-PROFILE-MIB

   ;

timetraMobGatewayMIBModule    MODULE-IDENTITY
    LAST-UPDATED    "0912230000Z"
    ORGANIZATION    "Alcatel-Lucent"
    CONTACT-INFO
    "Alcatel-Lucent 7xxx Support
    Web: http://www.alcatel.com/comps/pages/carrier_support.jhtml"
    DESCRIPTION
    "This document is the SNMP MIB module to manage and provision
    a mobile gateway.

    Copyright 2008-2014 Alcatel-Lucent. All rights reserved.
    Reproduction of this document is authorized on the condition that
    the foregoing copyright notice is included.

    This SNMP MIB module (Specification) embodies Alcatel-Lucent's
    proprietary intellectual property. Alcatel-Lucent retains all title and
    ownership in the Specification, including any revisions.

    Alcatel-Lucent grants all interested parties a non-exclusive
    license to use and distribute an unmodified copy of this
    Specification in connection with management of Alcatel-Lucent products,
    and without fee, provided this copyright notice and license appear
    on all copies.

    This Specification is supplied 'as is', and Alcatel-Lucent
    makes no warranty, either express or implied, as to the use,
    operation, condition, or performance of the Specification."

--
--  Revision History
--

    REVISION        "200912230000Z"
    DESCRIPTION     "Rev MG-1.0             23 Dec 2009 00:00
                     MG-1.0 release of the TIMETRA-MOBILE-GATEWAY-MIB."

    ::= { timetraSRMIBModules 70 }

-- ----------------------------------------------------------------------------
--  Alcatel-Lucent 7xxx series MOBILE-GATEWAY MIB structure
-- ----------------------------------------------------------------------------
tmnxMobGateway                OBJECT IDENTIFIER ::= { tmnxSRObjs 70 }
    tmnxMobGatewayObjs              OBJECT IDENTIFIER ::= { tmnxMobGateway 1 }
    tmnxMobGatewayGlobalObjs        OBJECT IDENTIFIER ::= { tmnxMobGateway 2 }
    tmnxMobGatewayNotificationObjs   OBJECT IDENTIFIER ::= { tmnxMobGateway 3 }
    tmnxMobGatewayChargingRecObjs   OBJECT IDENTIFIER ::= { tmnxMobGateway 4 }

tmnxMobGatewayConformance     OBJECT IDENTIFIER ::= { tmnxSRConfs 70 }
    tmnxMobGatewayCompliances       OBJECT IDENTIFIER ::=
                                            { tmnxMobGatewayConformance 1 }
    tmnxMobGatewayGroups            OBJECT IDENTIFIER ::=
                                            { tmnxMobGatewayConformance 2 }

tmnxMobGatewayNotifyPrefix    OBJECT IDENTIFIER ::= { tmnxSRNotifyPrefix 70 }
    tmnxMobGatewayNotifications     OBJECT IDENTIFIER ::=
                                            { tmnxMobGatewayNotifyPrefix 0 }

-- --------------------------
--  Mib objects
-- --------------------------

--
--  Common gateway table
--

tmnxMobGwTableLastChanged     OBJECT-TYPE
    SYNTAX      TimeStamp
    MAX-ACCESS  read-only
    STATUS      current
    DESCRIPTION
        "The value of tmnxMobGwTableLastChanged indicates the sysUpTime at
         the time of the last modification to tmnxMobGwTable by adding,
         deleting an entry or change to a writable object in the table.

         If no changes were made to the table since the last re-initialization
         of the local network management subsystem, then this object contains
         a zero value."
    ::= { tmnxMobGatewayGlobalObjs 1 }

tmnxMobGwTable  OBJECT-TYPE
    SYNTAX      SEQUENCE OF TmnxMobGwEntry
    MAX-ACCESS  not-accessible
    STATUS      current
    DESCRIPTION
        "The tmnxMobGwTable has an entry for each mobile gateway configured in
         the system."
    ::= { tmnxMobGatewayObjs 1 }

tmnxMobGwEntry  OBJECT-TYPE
    SYNTAX      TmnxMobGwEntry
    MAX-ACCESS  not-accessible
    STATUS      current
    DESCRIPTION
        "Each row entry represents a mobile gateway. Entries can be
         created and deleted by the user.

         The values of tmnxMobGwRowStatus and tmnxMobGwType must be set in the
         same SNMP SET PDU for the row creation to succeed."
    INDEX { tmnxMobGwId }
    ::= { tmnxMobGwTable 1 }

TmnxMobGwEntry ::= SEQUENCE {
        tmnxMobGwId                        TmnxMobGwId,
        tmnxMobGwRowStatus                 RowStatus,
        tmnxMobGwLastChanged               TimeStamp,
        tmnxMobGwDescription               TItemDescription,
        tmnxMobGwType                      TmnxMobGwType,
        tmnxMobGwRestartCounter            Unsigned32
    }

tmnxMobGwId  OBJECT-TYPE
    SYNTAX      TmnxMobGwId
    MAX-ACCESS  not-accessible
    STATUS      current
    DESCRIPTION
        "The value of tmnxMobGwId uniquely identifies a mobile gateway
         configured in the system."
    ::= { tmnxMobGwEntry 1 }

tmnxMobGwRowStatus  OBJECT-TYPE
    SYNTAX      RowStatus
    MAX-ACCESS  read-create
    STATUS      current
    DESCRIPTION
        "The value of tmnxMobGwRowStatus specifies the row status of this
         entry. It is used for the creation and deletion of this mobile gateway.

         In order for the row creation to succeed, value for tmnxMobGwType must
         be included in the same SNMP SET PDU as tmnxMobGwRowStatus. Otherwise,
         the SET request will fail with an 'inconsistentValue' error.

         The creation or deletion of an entry in this table causes creation or
         deletion of a corresponding entry in tmnxMobServTable or
         tmnxMobPdnTable depending on the value of tmnxMobGwType.

         To delete an entry from this table, the corresponding mobile gateway
         must be administratively down."
    ::= { tmnxMobGwEntry 2 }

tmnxMobGwLastChanged  OBJECT-TYPE
    SYNTAX      TimeStamp
    MAX-ACCESS  read-only
    STATUS      current
    DESCRIPTION
        "The value of tmnxMobGwLastChanged indicates the timestamp of the last
         change to this row in tmnxMobGwTable."
    ::= { tmnxMobGwEntry 3 }

tmnxMobGwDescription  OBJECT-TYPE
    SYNTAX      TItemDescription
    MAX-ACCESS  read-create
    STATUS      current
    DESCRIPTION
        "The value of tmnxMobGwDescription specifies the description
         string for this mobile gateway. It can consist of any 
         printable, seven-bit ASCII characters up to 80 characters in length."
    DEFVAL { ''H }
    ::= { tmnxMobGwEntry 4 }

tmnxMobGwType  OBJECT-TYPE
    SYNTAX      TmnxMobGwType
    MAX-ACCESS  read-create
    STATUS      current
    DESCRIPTION
        "The value of tmnxMobGwType specifies the type of mobile gateway. The
         value of this object must be set when the row is created and
         cannot be changed while the row status is 'active'."
    ::= { tmnxMobGwEntry 5 }

tmnxMobGwRestartCounter  OBJECT-TYPE
    SYNTAX      Unsigned32
    MAX-ACCESS  read-only
    STATUS      current
    DESCRIPTION
        "The value of tmnxMobGwRestartCounter indicates the number of times
         this gateway was restarted."
    ::= { tmnxMobGwEntry 6 }

--
--  System Group table
--

tmnxMobGwSysGroupTblLstChgd  OBJECT-TYPE
    SYNTAX      TimeStamp
    MAX-ACCESS  read-only
    STATUS      current
    DESCRIPTION
        "The value of tmnxMobGwSysGroupTblLstChgd indicates the sysUpTime at the
         time of the last modification to tmnxMobGwSysGroupTable by adding,
         deleting an entry or change to a writable object in the table.

         If no changes were made to the table since the last re-initialization
         of the local network management subsystem, then this object contains
         a zero value."
    ::= { tmnxMobGatewayGlobalObjs 2 }

tmnxMobGwSysGroupTable  OBJECT-TYPE
    SYNTAX      SEQUENCE OF TmnxMobGwSysGroupEntry
    MAX-ACCESS  not-accessible
    STATUS      current
    DESCRIPTION
        "The tmnxMobGwSysGroupTable has an entry for each mobile system group
         configured in the system."
    ::= { tmnxMobGatewayObjs 2 }

tmnxMobGwSysGroupEntry  OBJECT-TYPE
    SYNTAX      TmnxMobGwSysGroupEntry
    MAX-ACCESS  not-accessible
    STATUS      current
    DESCRIPTION
        "Each row entry represents a mobile system group configured in the
         system. Entries can be created and deleted by the user."
    INDEX { tmnxMobGwSysGroupId }
    ::= { tmnxMobGwSysGroupTable 1 }

TmnxMobGwSysGroupEntry ::= SEQUENCE {
        tmnxMobGwSysGroupId              Unsigned32,
        tmnxMobGwSysGroupRowStatus       RowStatus,
        tmnxMobGwSysGroupLastChanged     TimeStamp,
        tmnxMobGwSysGroupDescription     TItemDescription,
        tmnxMobGwSysGroupOperState       TmnxOperState,
        tmnxMobGwSysGroupApp             TmnxMobGwType,
        tmnxMobGwSysGroupRed             INTEGER,
        tmnxMobGwSysGroupGateway         TmnxMobGwId,
        tmnxMobGwSysGroupSysLimitName    TmnxMobProfName,
        tmnxMobGwSysGroupProtectDelay    Unsigned32,
        tmnxMobGwSysGroupSwitchoverCount Counter32,
        tmnxMobGwSysGroupSwitchoverTime  TimeStamp,
        tmnxMobGwSysGroupRedState        INTEGER
    }

tmnxMobGwSysGroupId  OBJECT-TYPE
    SYNTAX      Unsigned32 (1..8)
    MAX-ACCESS  not-accessible
    STATUS      current
    DESCRIPTION
        "The value of tmnxMobGwSysGroupId uniquely identifies a mobile system
         group."
    ::= { tmnxMobGwSysGroupEntry 1 }

tmnxMobGwSysGroupRowStatus  OBJECT-TYPE
    SYNTAX         RowStatus
    MAX-ACCESS     read-create
    STATUS         current
    DESCRIPTION
        "The value of tmnxMobGwSysGroupRowStatus specifies the row status
         of this entry. It is used for the creation and deletion of this system
         group.

         In order for the row creation to succeed, values for 
         tmnxMobGwSysGroupRed and tmnxMobGwSysGroupGateway must be included in 
         the same SNMP SET PDU as tmnxMobGwSysGroupRowStatus. Otherwise,
         the SET request will fail with an 'inconsistentValue' error."
    ::= { tmnxMobGwSysGroupEntry 2 }

tmnxMobGwSysGroupLastChanged  OBJECT-TYPE
    SYNTAX      TimeStamp
    MAX-ACCESS  read-only
    STATUS      current
    DESCRIPTION
        "The value of tmnxMobGwSysGroupLastChanged indicates the timestamp of
         the last change to this row in tmnxMobGwSysGroupTable."
    ::= { tmnxMobGwSysGroupEntry 3 }

tmnxMobGwSysGroupDescription  OBJECT-TYPE
    SYNTAX      TItemDescription
    MAX-ACCESS  read-create
    STATUS      current
    DESCRIPTION
        "The value of tmnxMobGwSysGroupDescription specifies the description
         string for this system group. It can consist of any 
         printable, seven-bit ASCII characters up to 80 characters in length."
    DEFVAL { ''H }
    ::= { tmnxMobGwSysGroupEntry 4 }

tmnxMobGwSysGroupOperState                OBJECT-TYPE
    SYNTAX         TmnxOperState
    MAX-ACCESS     read-only
    STATUS         current
    DESCRIPTION
        "The value of tmnxMobGwSysGroupOperState indicates the current
         operational state of this group."
    ::= { tmnxMobGwSysGroupEntry 5 }

tmnxMobGwSysGroupApp  OBJECT-TYPE
    SYNTAX      TmnxMobGwType
    MAX-ACCESS  read-only
    STATUS      current
    DESCRIPTION
        "The value of tmnxMobGwSysGroupApp indicates the application type as
         Serving Gateway (SGW) or Packet Data Network Gateway (PGW)."
    ::= { tmnxMobGwSysGroupEntry 6 }

tmnxMobGwSysGroupRed  OBJECT-TYPE
    SYNTAX      INTEGER {
                    none        (0),
                    oneToOne    (1)
                }
    MAX-ACCESS  read-create
    STATUS      current
    DESCRIPTION
        "The value of tmnxMobGwSysGroupRed specifies the redundancy type. If the
         value of the object is set to 'none', then the cards in this group are
         unprotected. If the value of the object is set to 'oneToOne', each
         card has one redundant backup card.

         The value of this object must be set when the row is created and
         cannot be changed while the row status is 'active'."
    ::= { tmnxMobGwSysGroupEntry 7 }

tmnxMobGwSysGroupGateway  OBJECT-TYPE
    SYNTAX         TmnxMobGwId
    MAX-ACCESS     read-create
    STATUS         current
    DESCRIPTION
        "The value of tmnxMobGwSysGroupGateway specifies the mobile gateway to
         which this system group belongs.

         The value of this object must be set when the row is created and
         cannot be changed while the row status is 'active'. If a corresponding 
         gateway entry does not exist in tmnxMobGwTable, an 'inconsistentValue'
         error will be returned."
    ::= { tmnxMobGwSysGroupEntry 8 }

tmnxMobGwSysGroupSysLimitName  OBJECT-TYPE
    SYNTAX         TmnxMobProfName
    MAX-ACCESS     read-create
    STATUS         current
    DESCRIPTION
        "The value of tmnxMobGwSysGroupSysLimitName specifies the system limit
         profile name for this group.

         If a corresponding system limit profile does not exist in
         TIMETRA-MOBILE-PROFILE-MIB::tmnxMobProfSysTable, an 'inconsistentValue'
         error will be returned."
    DEFVAL { "default" }
    ::= { tmnxMobGwSysGroupEntry 9 }

tmnxMobGwSysGroupProtectDelay    OBJECT-TYPE
    SYNTAX      Unsigned32 (1..30)
    UNITS       "seconds"
    MAX-ACCESS  read-create
    STATUS      current
    DESCRIPTION
        "The value of tmnxMobGwSysGroupProtectDelay specifies the time to wait 
         for the working card to come online before a standby card becomes 
         active.

         The value of this object is applicable only when the value of 
         tmnxMobGwSysGroupRed is not equal to 'none'."
    DEFVAL { 10 }
    ::= { tmnxMobGwSysGroupEntry 10 }

tmnxMobGwSysGroupSwitchoverCount  OBJECT-TYPE
    SYNTAX      Counter32
    MAX-ACCESS  read-only
    STATUS      current
    DESCRIPTION
        "The value of tmnxMobGwSysGroupSwitchoverCount indicates the number of 
         times successful switchover happened since boot."
    ::= { tmnxMobGwSysGroupEntry 11 }

tmnxMobGwSysGroupSwitchoverTime  OBJECT-TYPE
    SYNTAX      TimeStamp
    MAX-ACCESS  read-only
    STATUS      current
    DESCRIPTION
        "The value of tmnxMobGwSysGroupSwitchoverTime indicates the timestamp
         for the last switchover in this group."
    ::= { tmnxMobGwSysGroupEntry 12 }

tmnxMobGwSysGroupRedState                OBJECT-TYPE
    SYNTAX      INTEGER {
                    none    (1),
                    hot     (2),
                    warm    (3),
                    cold    (4)
                }
    MAX-ACCESS     read-only
    STATUS         current
    DESCRIPTION
        "The value of tmnxMobGwSysGroupOperState indicates the current
         redundancy state of this group. The redundancy state may be one of:
         'none' - no redundancy is configured in this group.
         'hot'  - standby card is ready to become active in case of a active 
                  card failure.
         'warm' - No card is ready to become active in case of a active card 
                  failure. Backup card is up, but not in sync with the active 
                  card.
         'cold' - No card is ready to become active in case of a active card 
                  failure. No protect card is configured in this group or the 
                  backup card is operationally down."
    ::= { tmnxMobGwSysGroupEntry 13 }

--
--  System Group Card table
--

tmnxMobGwSysGroupCardTblLstChgd  OBJECT-TYPE
    SYNTAX      TimeStamp
    MAX-ACCESS  read-only
    STATUS      current
    DESCRIPTION
        "The value of tmnxMobGwSysGroupCardTblLstChgd indicates the sysUpTime at
         the time of the last modification to tmnxMobGwSysGroupCardTable by
         adding, deleting an entry or change to a writable object in the table.

         If no changes were made to the table since the last re-initialization
         of the local network management subsystem, then this object contains
         a zero value."
    ::= { tmnxMobGatewayGlobalObjs 3 }

tmnxMobGwSysGroupCardTable  OBJECT-TYPE
    SYNTAX      SEQUENCE OF TmnxMobGwSysGroupCardEntry
    MAX-ACCESS  not-accessible
    STATUS      current
    DESCRIPTION
        "The tmnxMobGwSysGroupCardTable has an entry for each Mobility Service
         Module (MSM) in the group."
    ::= { tmnxMobGatewayObjs 3 }

tmnxMobGwSysGroupCardEntry  OBJECT-TYPE
    SYNTAX      TmnxMobGwSysGroupCardEntry
    MAX-ACCESS  not-accessible
    STATUS      current
    DESCRIPTION
        "Each row entry represents a Mobility Service Module (MSM) in the
         group. Entries can be created and deleted by the user."
    INDEX { tmnxMobGwSysGroupId,
            tmnxChassisIndex,
            tmnxCardSlotNum
          }
    ::= { tmnxMobGwSysGroupCardTable 1 }

TmnxMobGwSysGroupCardEntry ::= SEQUENCE {
        tmnxMobGwSysGroupCardRowStatus      RowStatus,
        tmnxMobGwSysGroupCardLastChanged    TimeStamp,
        tmnxMobGwSysGroupCardRole           INTEGER,
        tmnxMobGwSysGroupCardRedState       INTEGER
    }

tmnxMobGwSysGroupCardRowStatus  OBJECT-TYPE
    SYNTAX         RowStatus
    MAX-ACCESS     read-create
    STATUS         current
    DESCRIPTION
        "The value of tmnxMobGwSysGroupCardRowStatus specifies the row status
         of this entry. It is used for creation and deletion of this card entry
         in the mobile system group."
    ::= { tmnxMobGwSysGroupCardEntry 1 }

tmnxMobGwSysGroupCardLastChanged  OBJECT-TYPE
    SYNTAX      TimeStamp
    MAX-ACCESS  read-only
    STATUS      current
    DESCRIPTION
        "The value of tmnxMobGwSysGroupCardLastChanged indicates the timestamp
         of the last change to this row in tmnxMobGwSysGroupCardTable."
    ::= { tmnxMobGwSysGroupCardEntry 2 }

tmnxMobGwSysGroupCardRole  OBJECT-TYPE
    SYNTAX         INTEGER {
                        working   (1),
                        protect   (2)
                    }
    MAX-ACCESS     read-create
    STATUS         current
    DESCRIPTION
        "The value of tmnxMobGwSysGroupCardRole specifies the card role. The 
         role may be one of: 
        'working'   - the card is currently working and providing service
        'protect'   - the card is reduntant backup card"
    DEFVAL { working }
    ::= { tmnxMobGwSysGroupCardEntry 3 }

tmnxMobGwSysGroupCardRedState  OBJECT-TYPE
    SYNTAX         INTEGER {
                        notValid      (1),
                        active        (2),
                        standby       (3),
                        standbyInProg (4)
                    }
    MAX-ACCESS     read-only
    STATUS         current
    DESCRIPTION
        "The value of tmnxMobGwSysGroupCardRedState indicates the state of this
         card in the redundancy group. The state may be one of:
         'notValid' - card is operationally down or the corresponding group has
                      no redundancy configured.
         'active'   - card is online and providing service.
         'standby'  - card is online and backing up an active card, but not 
                      providing service.
         'standbyInProg' - card is operationally up, but not in sync with the 
                           active card."
    ::= { tmnxMobGwSysGroupCardEntry 4 }

--
-- System Limit Profile for all cards
--

tmnxMobGwSysLimitName    OBJECT-TYPE
    SYNTAX      TmnxMobProfName
    MAX-ACCESS  read-write
    STATUS      current
    DESCRIPTION
        "The value of tmnxMobGwSysLimitName specifies the system limit profile
         name for all the mobile system groups defined in the
         tmnxMobGwSysGroupTable.

         If a corresponding system limit profile does not exist in
         TIMETRA-MOBILE-PROFILE-MIB::tmnxMobProfSysTable, an
         'inconsistentValue' error will be returned."
    DEFVAL { "default" }
    ::= { tmnxMobGatewayGlobalObjs 4 }

--
--  S5 peer list table
--

tmnxMobGwS5PeerTableLastChanged     OBJECT-TYPE
    SYNTAX      TimeStamp
    MAX-ACCESS  read-only
    STATUS      current
    DESCRIPTION
        "The value of tmnxMobGwS5PeerTableLastChanged indicates the sysUpTime at
         the time of the last modification to tmnxMobGwS5PeerTable by adding,
         deleting an entry or change to a writable object in the table.

         If no changes were made to the table since the last re-initialization
         of the local network management subsystem, then this object contains
         a zero value."
    ::= { tmnxMobGatewayGlobalObjs 5 }

tmnxMobGwS5PeerTable  OBJECT-TYPE
    SYNTAX      SEQUENCE OF TmnxMobGwS5PeerEntry
    MAX-ACCESS  not-accessible
    STATUS      current
    DESCRIPTION
        "The tmnxMobGwS5PeerTable has an entry for each peer on the S5
         reference point."
    ::= { tmnxMobGatewayObjs 4 }

tmnxMobGwS5PeerEntry  OBJECT-TYPE
    SYNTAX      TmnxMobGwS5PeerEntry
    MAX-ACCESS  not-accessible
    STATUS      current
    DESCRIPTION
        "Each row entry represents a peer on the S5 reference point."
    INDEX { vRtrID,
            tmnxMobGwS5PeerAddressType,
            tmnxMobGwS5PeerAddress,
            tmnxMobGwS5PeerPort
          }
    ::= { tmnxMobGwS5PeerTable 1 }

TmnxMobGwS5PeerEntry ::= SEQUENCE {
        tmnxMobGwS5PeerAddressType        InetAddressType,
        tmnxMobGwS5PeerAddress            InetAddress,
        tmnxMobGwS5PeerPort               InetPortNumber,
        tmnxMobGwS5PeerLastChanged        TimeStamp,
        tmnxMobGwS5PeerCreateTime         TimeStamp,
        tmnxMobGwS5PeerPathMgmtState      TmnxMobPathMgmtState,
        tmnxMobGwS5PeerGatewayId          TmnxMobGwId,
        tmnxMobGwS5PeerType               TmnxMobPeerType
    }

tmnxMobGwS5PeerAddressType  OBJECT-TYPE
    SYNTAX      InetAddressType
    MAX-ACCESS  not-accessible
    STATUS      current
    DESCRIPTION
        "The value of tmnxMobGwS5PeerAddressType indicates the type of
         address represented by tmnxMobGwS5PeerAddress."
    ::= { tmnxMobGwS5PeerEntry 1 }

tmnxMobGwS5PeerAddress  OBJECT-TYPE
    SYNTAX      InetAddress (SIZE (4|16))
    MAX-ACCESS  not-accessible
    STATUS      current
    DESCRIPTION
        "The value of tmnxMobGwS5PeerAddress indicates the IP address of the
         peer on S5 reference point."
    ::= { tmnxMobGwS5PeerEntry 2 }

tmnxMobGwS5PeerPort  OBJECT-TYPE
    SYNTAX      InetPortNumber
    MAX-ACCESS  not-accessible
    STATUS      current
    DESCRIPTION
        "The value of tmnxMobGwS5PeerPort indicates the port number of this
         peer."
    ::= { tmnxMobGwS5PeerEntry 3 }

tmnxMobGwS5PeerLastChanged  OBJECT-TYPE
    SYNTAX      TimeStamp
    MAX-ACCESS  read-only
    STATUS      current
    DESCRIPTION
        "The value of tmnxMobGwS5PeerLastChanged indicates the timestamp of
         the last change to this row in tmnxMobGwS5PeerTable."
    ::= { tmnxMobGwS5PeerEntry 4 }

tmnxMobGwS5PeerCreateTime  OBJECT-TYPE
    SYNTAX      TimeStamp
    MAX-ACCESS  read-only
    STATUS      current
    DESCRIPTION
        "The value of tmnxMobGwS5PeerCreateTime indicates the sysUpTime when
         this entry was created."
    ::= { tmnxMobGwS5PeerEntry 5 }

tmnxMobGwS5PeerPathMgmtState  OBJECT-TYPE
    SYNTAX      TmnxMobPathMgmtState
    MAX-ACCESS  read-only
    STATUS      current
    DESCRIPTION
        "The value of tmnxMobGwS5PeerPathMgmtState indicates the state of
         path."
    ::= { tmnxMobGwS5PeerEntry 6 }

tmnxMobGwS5PeerGatewayId  OBJECT-TYPE
    SYNTAX      TmnxMobGwId
    MAX-ACCESS  read-only
    STATUS      current
    DESCRIPTION
        "The value of tmnxMobGwS5PeerGatewayId indicates the gateway 
         to which this peer belongs."
    ::= { tmnxMobGwS5PeerEntry 7 }

tmnxMobGwS5PeerType  OBJECT-TYPE
    SYNTAX      TmnxMobPeerType
    MAX-ACCESS  read-only
    STATUS      current
    DESCRIPTION
        "The value of tmnxMobGwS5PeerType indicates the type of this peer."
    ::= { tmnxMobGwS5PeerEntry 8 }

--
--  S5 Stats Table
--

tmnxMobGwS5StatTable  OBJECT-TYPE
    SYNTAX      SEQUENCE OF TmnxMobGwS5StatEntry
    MAX-ACCESS  not-accessible
    STATUS      current
    DESCRIPTION
        "The tmnxMobGwS5StatTable has an entry for each peer on the S5
         reference point."
    ::= { tmnxMobGatewayObjs 5 }

tmnxMobGwS5StatEntry  OBJECT-TYPE
    SYNTAX      TmnxMobGwS5StatEntry
    MAX-ACCESS  not-accessible
    STATUS      current
    DESCRIPTION
        "Each row entry represents a peer on the S5 reference point
         and contains statistics for this peer on a card."
    INDEX { vRtrID,
            tmnxMobGwS5PeerAddressType,
            tmnxMobGwS5PeerAddress,
            tmnxMobGwS5PeerPort,
            tmnxChassisIndex,
            tmnxCardSlotNum
          }
    ::= { tmnxMobGwS5StatTable 1 }

TmnxMobGwS5StatEntry ::= SEQUENCE {
        tmnxMobGwS5StatCreateSessnReq     Counter32,
        tmnxMobGwS5StatCreateSessnResp    Counter32,
        tmnxMobGwS5StatDeleteSessnReq     Counter32,
        tmnxMobGwS5StatDeleteSessnResp    Counter32,
        tmnxMobGwS5StatCreateBearerReq    Counter32,
        tmnxMobGwS5StatCreateBearerRsp    Counter32,
        tmnxMobGwS5StatDeleteBearerReq    Counter32,
        tmnxMobGwS5StatDeleteBearerRsp    Counter32,
        tmnxMobGwS5StatModifyBearerReq    Counter32,
        tmnxMobGwS5StatModifyBearerRsp    Counter32,
        tmnxMobGwS5StatRxEchoRequests     Counter32,
        tmnxMobGwS5StatTxEchoResponses    Counter32,
        tmnxMobGwS5StatTxEchoRequests     Counter32,
        tmnxMobGwS5StatRxEchoResponses    Counter32,
        tmnxMobGwS5StatRxMalformedPkts    Counter32,
        tmnxMobGwS5StatRxUnknownPkts      Counter32,
        tmnxMobGwS5StatRxMissingIePkts    Counter32,
        tmnxMobGwS5StatCreatePbu          Counter32,
        tmnxMobGwS5StatCreatePba          Counter32,
        tmnxMobGwS5StatDeletePbu          Counter32,
        tmnxMobGwS5StatDeletePba          Counter32,
        tmnxMobGwS5StatBri                Counter32,
        tmnxMobGwS5StatBra                Counter32,
        tmnxMobGwS5StatPeerRestarts       Counter32,
        tmnxMobGwS5StatPeerRestrtCount    Counter32,
        tmnxMobGwS5StatPathMgmtFails      Counter32,        
        tmnxMobGwS5StatUpdateBearerReq    Counter32,
        tmnxMobGwS5StatUpdateBearerRsp    Counter32,
        tmnxMobGwS5StatBearersIpv4        Gauge32,
        tmnxMobGwS5StatBearersIpv6        Gauge32,
        tmnxMobGwS5StatBearerIpv4v6       Gauge32,
        tmnxMobGwS5StatDedctdBearers      Gauge32,
        tmnxMobGwS5StatUlBytes            Counter32,
        tmnxMobGwS5StatDlBytes            Counter32,
        tmnxMobGwS5StatUlPackets          Counter32,
        tmnxMobGwS5StatDlPackets          Counter32,
        tmnxMobGwS5StatBearers            Gauge32,
        tmnxMobGwS5StatDefBearers         Gauge32,
        tmnxMobGwS5StatRoamers            Gauge32,
        tmnxMobGwS5StatActiveBearers      Gauge32,
        tmnxMobGwS5StatIdleBearers        Gauge32,
        tmnxMobGwS5StatModifyBearrCmd     Counter32,
        tmnxMobGwS5StatModifyBearrFlr     Counter32,
        tmnxMobGwS5StatDeleteBearrCmd     Counter32,
        tmnxMobGwS5StatDeleteBearrFlr     Counter32,
        tmnxMobGwS5StatBearrResCmd        Counter32,
        tmnxMobGwS5StatBearrResFailInd    Counter32,
        tmnxMobGwS5StatSuspNoticeReq      Counter32,
        tmnxMobGwS5StatSuspNoticeAck      Counter32,
        tmnxMobGwS5StatResumeNoticeReq    Counter32,
        tmnxMobGwS5StatResumeNoticeAck    Counter32,
        tmnxMobGwS5StatCreateSessnRespFl  Counter32,
        tmnxMobGwS5StatDeleteSessnRespFl  Counter32,
        tmnxMobGwS5StatCreateBearerRspFl  Counter32,
        tmnxMobGwS5StatDeleteBearerRspFl  Counter32,
        tmnxMobGwS5StatModifyBearerRspFl  Counter32,
        tmnxMobGwS5StatUpdateBearerRspFl  Counter32
    }

tmnxMobGwS5StatCreateSessnReq  OBJECT-TYPE
    SYNTAX      Counter32
    MAX-ACCESS  read-only
    STATUS      current
    DESCRIPTION
        "The value of tmnxMobGwS5StatCreateSessnReq indicates the number of
         create session request messages received from this peer or transmitted 
         to this peer."
    ::= { tmnxMobGwS5StatEntry 1 }

tmnxMobGwS5StatCreateSessnResp  OBJECT-TYPE
    SYNTAX      Counter32
    MAX-ACCESS  read-only
    STATUS      current
    DESCRIPTION
        "The value of tmnxMobGwS5StatCreateSessnResp indicates the number of
         create session response messages received from this peer or transmitted 
         to this peer with cause code set to request accepted."
    ::= { tmnxMobGwS5StatEntry 2 }

tmnxMobGwS5StatDeleteSessnReq  OBJECT-TYPE
    SYNTAX      Counter32
    MAX-ACCESS  read-only
    STATUS      current
    DESCRIPTION
        "The value of tmnxMobGwS5StatDeleteSessnReq indicates the number of
         delete session request messages received from this peer or transmitted 
         to this peer."
    ::= { tmnxMobGwS5StatEntry 3 }

tmnxMobGwS5StatDeleteSessnResp  OBJECT-TYPE
    SYNTAX      Counter32
    MAX-ACCESS  read-only
    STATUS      current
    DESCRIPTION
        "The value of tmnxMobGwS5StatDeleteSessnResp indicates the number of
         delete session response messages received from this peer or transmitted 
         to this peer with cause code set to request accepted."
    ::= { tmnxMobGwS5StatEntry 4 }

tmnxMobGwS5StatCreateBearerReq  OBJECT-TYPE
    SYNTAX      Counter32
    MAX-ACCESS  read-only
    STATUS      current
    DESCRIPTION
        "The value of tmnxMobGwS5StatCreateBearerReq indicates the number of
         create bearer request messages received from this peer or transmitted 
         to this peer."
    ::= { tmnxMobGwS5StatEntry 5 }

tmnxMobGwS5StatCreateBearerRsp  OBJECT-TYPE
    SYNTAX      Counter32
    MAX-ACCESS  read-only
    STATUS      current
    DESCRIPTION
        "The value of tmnxMobGwS5StatCreateBearerRsp indicates the number of
         create bearer response messages received from this peer or transmitted 
         to this peer with cause code set to request accepted."
    ::= { tmnxMobGwS5StatEntry 6 }

tmnxMobGwS5StatDeleteBearerReq  OBJECT-TYPE
    SYNTAX      Counter32
    MAX-ACCESS  read-only
    STATUS      current
    DESCRIPTION
        "The value of tmnxMobGwS5StatDeleteBearerReq indicates the number of
         delete bearer request messages received from this peer or transmitted 
         to this peer."
    ::= { tmnxMobGwS5StatEntry 7 }

tmnxMobGwS5StatDeleteBearerRsp  OBJECT-TYPE
    SYNTAX      Counter32
    MAX-ACCESS  read-only
    STATUS      current
    DESCRIPTION
        "The value of tmnxMobGwS5StatDeleteBearerRsp indicates the number of
         delete bearer response messages received from this peer or transmitted 
         to this peer with cause code set to request accepted."
    ::= { tmnxMobGwS5StatEntry 8 }

tmnxMobGwS5StatModifyBearerReq  OBJECT-TYPE
    SYNTAX      Counter32
    MAX-ACCESS  read-only
    STATUS      current
    DESCRIPTION
        "The value of tmnxMobGwS5StatModifyBearerReq indicates the number of
         modify bearer request messages received from this peer or transmitted 
         to this peer."
    ::= { tmnxMobGwS5StatEntry 9 }

tmnxMobGwS5StatModifyBearerRsp  OBJECT-TYPE
    SYNTAX      Counter32
    MAX-ACCESS  read-only
    STATUS      current
    DESCRIPTION
        "The value of tmnxMobGwS5StatModifyBearerRsp indicates the number of
         modify bearer response messages received from this peer or transmitted 
         to this peer with cause code set to request accepted."
    ::= { tmnxMobGwS5StatEntry 10 }

tmnxMobGwS5StatRxEchoRequests  OBJECT-TYPE
    SYNTAX      Counter32
    MAX-ACCESS  read-only
    STATUS      current
    DESCRIPTION
        "The value of tmnxMobGwS5StatRxEchoRequests indicates the number of
         echo request messages received from this peer."
    ::= { tmnxMobGwS5StatEntry 11 }

tmnxMobGwS5StatTxEchoResponses  OBJECT-TYPE
    SYNTAX      Counter32
    MAX-ACCESS  read-only
    STATUS      current
    DESCRIPTION
        "The value of tmnxMobGwS5StatTxEchoResponses indicates the number of
         echo response messages transmitted to this peer."
    ::= { tmnxMobGwS5StatEntry 12 }

tmnxMobGwS5StatTxEchoRequests  OBJECT-TYPE
    SYNTAX      Counter32
    MAX-ACCESS  read-only
    STATUS      current
    DESCRIPTION
        "The value of tmnxMobGwS5StatTxEchoRequests indicates the number of
         echo request messages transmitted to this peer."
    ::= { tmnxMobGwS5StatEntry 13 }

tmnxMobGwS5StatRxEchoResponses  OBJECT-TYPE
    SYNTAX      Counter32
    MAX-ACCESS  read-only
    STATUS      current
    DESCRIPTION
        "The value of tmnxMobGwS5StatRxEchoResponses indicates the number of
         echo response messages received from this peer."
    ::= { tmnxMobGwS5StatEntry 14 }

tmnxMobGwS5StatRxMalformedPkts  OBJECT-TYPE
    SYNTAX      Counter32
    MAX-ACCESS  read-only
    STATUS      current
    DESCRIPTION
        "The value of tmnxMobGwS5StatRxMalformedPkts indicates the number of
         malformed packets received from this peer."
    ::= { tmnxMobGwS5StatEntry 15 }

tmnxMobGwS5StatRxUnknownPkts  OBJECT-TYPE
    SYNTAX      Counter32
    MAX-ACCESS  read-only
    STATUS      current
    DESCRIPTION
        "The value of tmnxMobGwS5StatRxUnknownPkts indicates the number of
         unknown message type packets received from this peer."
    ::= { tmnxMobGwS5StatEntry 16 }

tmnxMobGwS5StatRxMissingIePkts  OBJECT-TYPE
    SYNTAX      Counter32
    MAX-ACCESS  read-only
    STATUS      current
    DESCRIPTION
        "The value of tmnxMobGwS5StatRxMissingIePkts indicates the number of
         missing mandatory Information Element (IE) packets received from this
         peer."
    ::= { tmnxMobGwS5StatEntry 17 }

tmnxMobGwS5StatCreatePbu  OBJECT-TYPE
    SYNTAX      Counter32
    MAX-ACCESS  read-only
    STATUS      current
    DESCRIPTION
        "The value of tmnxMobGwS5StatCreatePbu indicates the number of Create
         Proxy Binding Update (PBU) messages transmitted to this peer."
    ::= { tmnxMobGwS5StatEntry 18 }

tmnxMobGwS5StatCreatePba  OBJECT-TYPE
    SYNTAX      Counter32
    MAX-ACCESS  read-only
    STATUS      current
    DESCRIPTION
        "The value of tmnxMobGwS5StatCreatePba indicates the number of Create
         Proxy Binding Acknowledgement (PBA) messages received from this
         peer."
    ::= { tmnxMobGwS5StatEntry 19 }

tmnxMobGwS5StatDeletePbu  OBJECT-TYPE
    SYNTAX      Counter32
    MAX-ACCESS  read-only
    STATUS      current
    DESCRIPTION
        "The value of tmnxMobGwS5StatDeletePbu indicates the number of Delete
         Proxy Binding Update (PBU) messages transmitted to this peer."
    ::= { tmnxMobGwS5StatEntry 20 }

tmnxMobGwS5StatDeletePba  OBJECT-TYPE
    SYNTAX      Counter32
    MAX-ACCESS  read-only
    STATUS      current
    DESCRIPTION
        "The value of tmnxMobGwS5StatDeletePba indicates the number of Delete
         Proxy Binding Acknowledgement (PBA) messages received from this
         peer."
    ::= { tmnxMobGwS5StatEntry 21 }

tmnxMobGwS5StatBri  OBJECT-TYPE
    SYNTAX      Counter32
    MAX-ACCESS  read-only
    STATUS      current
    DESCRIPTION
        "The value of tmnxMobGwS5StatBri indicates the number of network
         initiated delete Basic Rate Interface (BRI) messages received from
         this peer."
    ::= { tmnxMobGwS5StatEntry 22 }

tmnxMobGwS5StatBra  OBJECT-TYPE
    SYNTAX      Counter32
    MAX-ACCESS  read-only
    STATUS      current
    DESCRIPTION
        "The value of tmnxMobGwS5StatBra indicates the number of network
         initiated delete Basic Rate Access (BRA) messages transmitted to
         this peer."
    ::= { tmnxMobGwS5StatEntry 23 }

tmnxMobGwS5StatPeerRestarts  OBJECT-TYPE
    SYNTAX      Counter32
    MAX-ACCESS  read-only
    STATUS      current
    DESCRIPTION
        "The value of tmnxMobGwS5StatPeerRestarts indicates the number of
         times this peer restarted after registering with the system."
    ::= { tmnxMobGwS5StatEntry 24 }

tmnxMobGwS5StatPeerRestrtCount  OBJECT-TYPE
    SYNTAX      Counter32
    MAX-ACCESS  read-only
    STATUS      current
    DESCRIPTION
        "The value of tmnxMobGwS5StatPeerRestrtCount indicates the counter
         value of the number of times this peer restarted."
    ::= { tmnxMobGwS5StatEntry 25 }

tmnxMobGwS5StatPathMgmtFails  OBJECT-TYPE
    SYNTAX      Counter32
    MAX-ACCESS  read-only
    STATUS      current
    DESCRIPTION
        "The value of tmnxMobGwS5StatPathMgmtFails indicates the number of
         path management failures for this peer."
    ::= { tmnxMobGwS5StatEntry 26 }

tmnxMobGwS5StatUpdateBearerReq  OBJECT-TYPE
    SYNTAX      Counter32
    MAX-ACCESS  read-only
    STATUS      current
    DESCRIPTION
        "The value of tmnxMobGwS5StatUpdateBearerReq indicates the number of
         update bearer request messages received from this peer or transmitted 
         to this peer."
    ::= { tmnxMobGwS5StatEntry 27 }

tmnxMobGwS5StatUpdateBearerRsp  OBJECT-TYPE
    SYNTAX      Counter32
    MAX-ACCESS  read-only
    STATUS      current
    DESCRIPTION
        "The value of tmnxMobGwS5StatUpdateBearerRsp indicates the number of
         update bearer response messages received from this peer or transmitted 
         to this peer with cause code set to request accepted."
    ::= { tmnxMobGwS5StatEntry 28 }

tmnxMobGwS5StatBearersIpv4  OBJECT-TYPE
    SYNTAX      Gauge32
    MAX-ACCESS  read-only
    STATUS      obsolete
    DESCRIPTION
        "The value of tmnxMobGwS5StatBearersIpv4 indicates the number of
         IPv4 bearers being served by this peer.

         This object was made obsolete in the 3.1R2 release."
    ::= { tmnxMobGwS5StatEntry 29 }

tmnxMobGwS5StatBearersIpv6  OBJECT-TYPE
    SYNTAX      Gauge32
    MAX-ACCESS  read-only
    STATUS      obsolete
    DESCRIPTION
        "The value of tmnxMobGwS5StatBearersIpv6 indicates the number of
         IPv6 bearers being served by this peer.

         This object was made obsolete in the 3.1R2 release."
    ::= { tmnxMobGwS5StatEntry 30 }

tmnxMobGwS5StatBearerIpv4v6  OBJECT-TYPE
    SYNTAX      Gauge32
    MAX-ACCESS  read-only
    STATUS      obsolete
    DESCRIPTION
        "The value of tmnxMobGwS5StatBearerIpv4v6 indicates the number of
         IPv4v6 bearers being served by this peer.

         This object was made obsolete in the 3.1R2 release."
    ::= { tmnxMobGwS5StatEntry 31 }

tmnxMobGwS5StatDedctdBearers  OBJECT-TYPE
    SYNTAX      Gauge32
    MAX-ACCESS  read-only
    STATUS      obsolete
    DESCRIPTION
        "The value of tmnxMobGwS5StatDedctdBearers indicates the number of
         dedicated bearers being served by this peer.

         This object was made obsolete in the 3.1R2 release."
    ::= { tmnxMobGwS5StatEntry 32 }

tmnxMobGwS5StatUlBytes  OBJECT-TYPE
    SYNTAX      Counter32
    MAX-ACCESS  read-only
    STATUS      current
    DESCRIPTION
        "The value of tmnxMobGwS5StatUlBytes indicates the number of
         uplink bytes received from this peer or transmitted 
         to this peer."
    ::= { tmnxMobGwS5StatEntry 33 }

tmnxMobGwS5StatDlBytes  OBJECT-TYPE
    SYNTAX      Counter32
    MAX-ACCESS  read-only
    STATUS      current
    DESCRIPTION
        "The value of tmnxMobGwS5StatDlBytes indicates the number of
         downlink bytes received from this peer or transmitted 
         to this peer."
    ::= { tmnxMobGwS5StatEntry 34 }

tmnxMobGwS5StatUlPackets  OBJECT-TYPE
    SYNTAX      Counter32
    MAX-ACCESS  read-only
    STATUS      current
    DESCRIPTION
        "The value of tmnxMobGwS5StatUlPackets indicates the number of
         uplink packets received from this peer or transmitted 
         to this peer."
    ::= { tmnxMobGwS5StatEntry 35 }

tmnxMobGwS5StatDlPackets  OBJECT-TYPE
    SYNTAX      Counter32
    MAX-ACCESS  read-only
    STATUS      current
    DESCRIPTION
        "The value of tmnxMobGwS5StatDlPackets indicates the number of
         downlink packets received from this peer or transmitted 
         to this peer."
    ::= { tmnxMobGwS5StatEntry 36 }

tmnxMobGwS5StatBearers  OBJECT-TYPE
    SYNTAX      Gauge32
    MAX-ACCESS  read-only
    STATUS      current
    DESCRIPTION
        "The value of tmnxMobGwS5StatBearers indicates the number of
         bearers being served by this peer."
    ::= { tmnxMobGwS5StatEntry 37 }

tmnxMobGwS5StatDefBearers  OBJECT-TYPE
    SYNTAX      Gauge32
    MAX-ACCESS  read-only
    STATUS      obsolete
    DESCRIPTION
        "The value of tmnxMobGwS5StatDefBearers indicates the number of
         default bearers being served by this peer.

         This object was made obsolete in the 3.1R2 release."
    ::= { tmnxMobGwS5StatEntry 38 }

tmnxMobGwS5StatRoamers  OBJECT-TYPE
    SYNTAX      Gauge32
    MAX-ACCESS  read-only
    STATUS      obsolete
    DESCRIPTION
        "The value of tmnxMobGwS5StatRoamers indicates the number of
         roamers being served by this peer.

         This object was made obsolete in the 3.1R2 release."
    ::= { tmnxMobGwS5StatEntry 39 }

tmnxMobGwS5StatActiveBearers  OBJECT-TYPE
    SYNTAX      Gauge32
    MAX-ACCESS  read-only
    STATUS      obsolete
    DESCRIPTION
        "The value of tmnxMobGwS5StatActiveBearers indicates the number of
         active bearers being served by this peer.

         This object was made obsolete in the 3.1R2 release."
    ::= { tmnxMobGwS5StatEntry 40 }

tmnxMobGwS5StatIdleBearers  OBJECT-TYPE
    SYNTAX      Gauge32
    MAX-ACCESS  read-only
    STATUS      obsolete
    DESCRIPTION
        "The value of tmnxMobGwS5StatIdleBearers indicates the number of
         idle bearers being served by this peer.

         This object was made obsolete in the 3.1R2 release."
    ::= { tmnxMobGwS5StatEntry 41 }    

tmnxMobGwS5StatModifyBearrCmd  OBJECT-TYPE
    SYNTAX      Counter32
    MAX-ACCESS  read-only
    STATUS      current
    DESCRIPTION
        "The value of tmnxMobGwS5StatModifyBearrCmd indicates the number of
         modify bearer command messages received from this peer."
    ::= { tmnxMobGwS5StatEntry 42 }

tmnxMobGwS5StatModifyBearrFlr  OBJECT-TYPE
    SYNTAX      Counter32
    MAX-ACCESS  read-only
    STATUS      current
    DESCRIPTION
        "The value of tmnxMobGwS5StatModifyBearrFlr indicates the number of
         modify bearer failure messages received from this peer."
    ::= { tmnxMobGwS5StatEntry 43 }

tmnxMobGwS5StatDeleteBearrCmd  OBJECT-TYPE
    SYNTAX      Counter32
    MAX-ACCESS  read-only
    STATUS      current
    DESCRIPTION
        "The value of tmnxMobGwS5StatDeleteBearrCmd indicates the number of
         delete bearer command messages received from this peer."
    ::= { tmnxMobGwS5StatEntry 44 }

tmnxMobGwS5StatDeleteBearrFlr  OBJECT-TYPE
    SYNTAX      Counter32
    MAX-ACCESS  read-only
    STATUS      current
    DESCRIPTION
        "The value of tmnxMobGwS5StatDeleteBearrFlr indicates the number of
         delete bearer failure messages received from this peer."
    ::= { tmnxMobGwS5StatEntry 45 }

tmnxMobGwS5StatBearrResCmd  OBJECT-TYPE
    SYNTAX      Counter32
    MAX-ACCESS  read-only
    STATUS      current
    DESCRIPTION
        "The value of tmnxMobGwS5StatBearrResCmd indicates the number of
         bearer resource command packets on the gateway."
    ::= { tmnxMobGwS5StatEntry 46 }

tmnxMobGwS5StatBearrResFailInd  OBJECT-TYPE
    SYNTAX      Counter32
    MAX-ACCESS  read-only
    STATUS      current
    DESCRIPTION
        "The value of tmnxMobGwS5StatBearrResFailInd indicates the number of
        bearer resource failure indication packets on the gateway."
    ::= { tmnxMobGwS5StatEntry 47 }

tmnxMobGwS5StatSuspNoticeReq  OBJECT-TYPE
    SYNTAX      Counter32
    MAX-ACCESS  read-only
    STATUS      current
    DESCRIPTION
        "The value of tmnxMobGwS5StatSuspNoticeReq indicates the number of
        suspend notification requests received from this peer or transmitted to 
        this peer."
    ::= { tmnxMobGwS5StatEntry 48 }

tmnxMobGwS5StatSuspNoticeAck  OBJECT-TYPE
    SYNTAX      Counter32
    MAX-ACCESS  read-only
    STATUS      current
    DESCRIPTION
        "The value of tmnxMobGwS5StatSuspNoticeAck indicates the number of
        suspend notification acknowledgements received from this peer or transmitted to 
        this peer."
    ::= { tmnxMobGwS5StatEntry 49 }

tmnxMobGwS5StatResumeNoticeReq  OBJECT-TYPE
    SYNTAX      Counter32
    MAX-ACCESS  read-only
    STATUS      current
    DESCRIPTION
        "The value of tmnxMobGwS5StatResumeNoticeReq indicates the number of
        resume notification requests received from this peer or transmitted to 
        this peer."
    ::= { tmnxMobGwS5StatEntry 50 }

tmnxMobGwS5StatResumeNoticeAck  OBJECT-TYPE
    SYNTAX      Counter32
    MAX-ACCESS  read-only
    STATUS      current
    DESCRIPTION
        "The value of tmnxMobGwS5StatResumeNoticeAck indicates the number of
        resume notification acknowledgements received from this peer or transmitted to 
        this peer."
    ::= { tmnxMobGwS5StatEntry 51 }

tmnxMobGwS5StatCreateSessnRespFl  OBJECT-TYPE
    SYNTAX      Counter32
    MAX-ACCESS  read-only
    STATUS      current
    DESCRIPTION
        "The value of tmnxMobGwS5StatCreateSessnRespFl indicates the number of
         create session response messages received from this peer or transmitted 
         to this peer with cause code not set to request accepted."
    ::= { tmnxMobGwS5StatEntry 52 }

tmnxMobGwS5StatDeleteSessnRespFl  OBJECT-TYPE
    SYNTAX      Counter32
    MAX-ACCESS  read-only
    STATUS      current
    DESCRIPTION
        "The value of tmnxMobGwS5StatDeleteSessnRespFl indicates the number of
         delete session response messages received from this peer or transmitted 
         to this peer with cause code not set to request accepted."
    ::= { tmnxMobGwS5StatEntry 53 }

tmnxMobGwS5StatCreateBearerRspFl  OBJECT-TYPE
    SYNTAX      Counter32
    MAX-ACCESS  read-only
    STATUS      current
    DESCRIPTION
        "The value of tmnxMobGwS5StatCreateBearerRspFl indicates the number of
         create bearer response messages received from this peer or transmitted 
         to this peer with cause code not set to request accepted."
    ::= { tmnxMobGwS5StatEntry 54 }

tmnxMobGwS5StatDeleteBearerRspFl  OBJECT-TYPE
    SYNTAX      Counter32
    MAX-ACCESS  read-only
    STATUS      current
    DESCRIPTION
        "The value of tmnxMobGwS5StatDeleteBearerRspFl indicates the number of
         delete bearer response messages received from this peer or transmitted 
         to this peer with cause code not set to request accepted."
    ::= { tmnxMobGwS5StatEntry 55 }

tmnxMobGwS5StatModifyBearerRspFl  OBJECT-TYPE
    SYNTAX      Counter32
    MAX-ACCESS  read-only
    STATUS      current
    DESCRIPTION
        "The value of tmnxMobGwS5StatModifyBearerRspFl indicates the number of
         modify bearer response messages received from this peer or transmitted 
         to this peer with cause code not set to request accepted."
    ::= { tmnxMobGwS5StatEntry 56 }

tmnxMobGwS5StatUpdateBearerRspFl  OBJECT-TYPE
    SYNTAX      Counter32
    MAX-ACCESS  read-only
    STATUS      current
    DESCRIPTION
        "The value of tmnxMobGwS5StatUpdateBearerRspFl indicates the number of
         update bearer response messages received from this peer or transmitted 
         to this peer with cause code not set to request accepted."
    ::= { tmnxMobGwS5StatEntry 57 }


--
--  S8 peer list table
--

tmnxMobGwS8PeerTableLastChanged     OBJECT-TYPE
    SYNTAX      TimeStamp
    MAX-ACCESS  read-only
    STATUS      current
    DESCRIPTION
        "The value of tmnxMobGwS8PeerTableLastChanged indicates the sysUpTime at
         the time of the last modification to tmnxMobGwS8PeerTable by adding,
         deleting an entry or change to a writable object in the table.

         If no changes were made to the table since the last re-initialization
         of the local network management subsystem, then this object contains
         a zero value."
    ::= { tmnxMobGatewayGlobalObjs 6 }

tmnxMobGwS8PeerTable  OBJECT-TYPE
    SYNTAX      SEQUENCE OF TmnxMobGwS8PeerEntry
    MAX-ACCESS  not-accessible
    STATUS      current
    DESCRIPTION
        "The tmnxMobGwS8PeerTable has an entry for each peer on the S8
         reference point."
    ::= { tmnxMobGatewayObjs 6 }

tmnxMobGwS8PeerEntry  OBJECT-TYPE
    SYNTAX      TmnxMobGwS8PeerEntry
    MAX-ACCESS  not-accessible
    STATUS      current
    DESCRIPTION
        "Each row entry represents a peer on the S8 reference point."
    INDEX { vRtrID,
            tmnxMobGwS8PeerAddressType,
            tmnxMobGwS8PeerAddress,
            tmnxMobGwS8PeerPort
          }
    ::= { tmnxMobGwS8PeerTable 1 }

TmnxMobGwS8PeerEntry ::= SEQUENCE {
        tmnxMobGwS8PeerAddressType        InetAddressType,
        tmnxMobGwS8PeerAddress            InetAddress,
        tmnxMobGwS8PeerPort               InetPortNumber,
        tmnxMobGwS8PeerLastChanged        TimeStamp,
        tmnxMobGwS8PeerCreateTime         TimeStamp,
        tmnxMobGwS8PeerPathMgmtState      TmnxMobPathMgmtState,
        tmnxMobGwS8PeerGatewayId          TmnxMobGwId,
        tmnxMobGwS8PeerType               TmnxMobPeerType
    }

tmnxMobGwS8PeerAddressType  OBJECT-TYPE
    SYNTAX      InetAddressType
    MAX-ACCESS  not-accessible
    STATUS      current
    DESCRIPTION
        "The value of tmnxMobGwS8PeerAddressType indicates the type of
         address represented by tmnxMobGwS8PeerAddress."
    ::= { tmnxMobGwS8PeerEntry 1 }

tmnxMobGwS8PeerAddress  OBJECT-TYPE
    SYNTAX      InetAddress (SIZE (4|16))
    MAX-ACCESS  not-accessible
    STATUS      current
    DESCRIPTION
        "The value of tmnxMobGwS8PeerAddress indicates the IP address of the
         peer on S8 reference point."
    ::= { tmnxMobGwS8PeerEntry 2 }

tmnxMobGwS8PeerPort  OBJECT-TYPE
    SYNTAX      InetPortNumber
    MAX-ACCESS  not-accessible
    STATUS      current
    DESCRIPTION
        "The value of tmnxMobGwS8PeerPort indicates the port number of this
         peer."
    ::= { tmnxMobGwS8PeerEntry 3 }

tmnxMobGwS8PeerLastChanged  OBJECT-TYPE
    SYNTAX      TimeStamp
    MAX-ACCESS  read-only
    STATUS      current
    DESCRIPTION
        "The value of tmnxMobGwS8PeerLastChanged indicates the timestamp of
         the last change to this row in tmnxMobGwS8PeerTable."
    ::= { tmnxMobGwS8PeerEntry 4 }

tmnxMobGwS8PeerCreateTime  OBJECT-TYPE
    SYNTAX      TimeStamp
    MAX-ACCESS  read-only
    STATUS      current
    DESCRIPTION
        "The value of tmnxMobGwS8PeerCreateTime indicates the sysUpTime when
         this entry was created."
    ::= { tmnxMobGwS8PeerEntry 5 }

tmnxMobGwS8PeerPathMgmtState  OBJECT-TYPE
    SYNTAX      TmnxMobPathMgmtState
    MAX-ACCESS  read-only
    STATUS      current
    DESCRIPTION
        "The value of tmnxMobGwS8PeerPathMgmtState indicates the state of
         path."
    ::= { tmnxMobGwS8PeerEntry 6 }

tmnxMobGwS8PeerGatewayId  OBJECT-TYPE
    SYNTAX      TmnxMobGwId
    MAX-ACCESS  read-only
    STATUS      current
    DESCRIPTION
        "The value of tmnxMobGwS8PeerGatewayId indicates the gateway 
         to which this peer belongs."
    ::= { tmnxMobGwS8PeerEntry 7 }

tmnxMobGwS8PeerType  OBJECT-TYPE
    SYNTAX      TmnxMobPeerType
    MAX-ACCESS  read-only
    STATUS      current
    DESCRIPTION
        "The value of tmnxMobGwS8PeerType indicates the type of this peer."
    ::= { tmnxMobGwS8PeerEntry 8 }

--
--  S8 Stats Table
--

tmnxMobGwS8StatTable  OBJECT-TYPE
    SYNTAX      SEQUENCE OF TmnxMobGwS8StatEntry
    MAX-ACCESS  not-accessible
    STATUS      current
    DESCRIPTION
        "The tmnxMobGwS8StatTable has an entry for each peer on the S8
         reference point."
    ::= { tmnxMobGatewayObjs 7 }

tmnxMobGwS8StatEntry  OBJECT-TYPE
    SYNTAX      TmnxMobGwS8StatEntry
    MAX-ACCESS  not-accessible
    STATUS      current
    DESCRIPTION
        "Each row entry represents a peer on the S8 reference point
         and contains statistics for this peer on a card."
    INDEX { vRtrID,
            tmnxMobGwS8PeerAddressType,
            tmnxMobGwS8PeerAddress,
            tmnxMobGwS8PeerPort,
            tmnxChassisIndex,
            tmnxCardSlotNum
          }
    ::= { tmnxMobGwS8StatTable 1 }

TmnxMobGwS8StatEntry ::= SEQUENCE {
        tmnxMobGwS8StatCreateSessnReq     Counter32,
        tmnxMobGwS8StatCreateSessnResp    Counter32,
        tmnxMobGwS8StatDeleteSessnReq     Counter32,
        tmnxMobGwS8StatDeleteSessnResp    Counter32,
        tmnxMobGwS8StatCreateBearerReq    Counter32,
        tmnxMobGwS8StatCreateBearerRsp    Counter32,
        tmnxMobGwS8StatDeleteBearerReq    Counter32,
        tmnxMobGwS8StatDeleteBearerRsp    Counter32,
        tmnxMobGwS8StatModifyBearerReq    Counter32,
        tmnxMobGwS8StatModifyBearerRsp    Counter32,
        tmnxMobGwS8StatRxEchoRequests     Counter32,
        tmnxMobGwS8StatTxEchoResponses    Counter32,
        tmnxMobGwS8StatTxEchoRequests     Counter32,
        tmnxMobGwS8StatRxEchoResponses    Counter32,
        tmnxMobGwS8StatRxMalformedPkts    Counter32,
        tmnxMobGwS8StatRxUnknownPkts      Counter32,
        tmnxMobGwS8StatRxMissingIePkts    Counter32,
        tmnxMobGwS8StatCreatePbu          Counter32,
        tmnxMobGwS8StatCreatePba          Counter32,
        tmnxMobGwS8StatDeletePbu          Counter32,
        tmnxMobGwS8StatDeletePba          Counter32,
        tmnxMobGwS8StatBri                Counter32,
        tmnxMobGwS8StatBra                Counter32,
        tmnxMobGwS8StatPeerRestarts       Counter32,
        tmnxMobGwS8StatPeerRestrtCount    Counter32,
        tmnxMobGwS8StatPathMgmtFails      Counter32,
        tmnxMobGwS8StatUpdateBearerReq    Counter32,
        tmnxMobGwS8StatUpdateBearerRsp    Counter32,
        tmnxMobGwS8StatCreatSessnRspFl    Counter32,
        tmnxMobGwS8StatDelSessnRspFail    Counter32,
        tmnxMobGwS8StatCreatBearrRspFl    Counter32,
        tmnxMobGwS8StatDelBearrRspFail    Counter32,
        tmnxMobGwS8StatModBearrRspFail    Counter32,
        tmnxMobGwS8StatUpdatBearrRspFl    Counter32
    }

tmnxMobGwS8StatCreateSessnReq  OBJECT-TYPE
    SYNTAX      Counter32
    MAX-ACCESS  read-only
    STATUS      current
    DESCRIPTION
        "The value of tmnxMobGwS8StatCreateSessnReq indicates the number of
         create session request messages received from this peer or transmitted 
         to this peer."
    ::= { tmnxMobGwS8StatEntry 1 }

tmnxMobGwS8StatCreateSessnResp  OBJECT-TYPE
    SYNTAX      Counter32
    MAX-ACCESS  read-only
    STATUS      current
    DESCRIPTION
        "The value of tmnxMobGwS8StatCreateSessnResp indicates the number of
         create session response messages received from this peer or transmitted 
         to this peer with cause code set to request accepted."
    ::= { tmnxMobGwS8StatEntry 2 }

tmnxMobGwS8StatDeleteSessnReq  OBJECT-TYPE
    SYNTAX      Counter32
    MAX-ACCESS  read-only
    STATUS      current
    DESCRIPTION
        "The value of tmnxMobGwS8StatDeleteSessnReq indicates the number of
         delete session request messages received from this peer or transmitted 
         to this peer."
    ::= { tmnxMobGwS8StatEntry 3 }

tmnxMobGwS8StatDeleteSessnResp  OBJECT-TYPE
    SYNTAX      Counter32
    MAX-ACCESS  read-only
    STATUS      current
    DESCRIPTION
        "The value of tmnxMobGwS8StatDeleteSessnResp indicates the number of
         delete session response messages received from this peer or transmitted 
         to this peer with cause code set to request accepted."
    ::= { tmnxMobGwS8StatEntry 4 }

tmnxMobGwS8StatCreateBearerReq  OBJECT-TYPE
    SYNTAX      Counter32
    MAX-ACCESS  read-only
    STATUS      current
    DESCRIPTION
        "The value of tmnxMobGwS8StatCreateBearerReq indicates the number of
         create bearer request messages received from this peer or transmitted 
         to this peer."
    ::= { tmnxMobGwS8StatEntry 5 }

tmnxMobGwS8StatCreateBearerRsp  OBJECT-TYPE
    SYNTAX      Counter32
    MAX-ACCESS  read-only
    STATUS      current
    DESCRIPTION
        "The value of tmnxMobGwS8StatCreateBearerRsp indicates the number of
         create bearer response messages received from this peer or transmitted 
         to this peer with cause code set to request accepted."
    ::= { tmnxMobGwS8StatEntry 6 }

tmnxMobGwS8StatDeleteBearerReq  OBJECT-TYPE
    SYNTAX      Counter32
    MAX-ACCESS  read-only
    STATUS      current
    DESCRIPTION
        "The value of tmnxMobGwS8StatDeleteBearerReq indicates the number of
         delete bearer request messages received from this peer or transmitted 
         to this peer."
    ::= { tmnxMobGwS8StatEntry 7 }

tmnxMobGwS8StatDeleteBearerRsp  OBJECT-TYPE
    SYNTAX      Counter32
    MAX-ACCESS  read-only
    STATUS      current
    DESCRIPTION
        "The value of tmnxMobGwS8StatDeleteBearerRsp indicates the number of
         delete bearer response messages received from this peer or transmitted 
         to this peer with cause code set to request accepted."
    ::= { tmnxMobGwS8StatEntry 8 }

tmnxMobGwS8StatModifyBearerReq  OBJECT-TYPE
    SYNTAX      Counter32
    MAX-ACCESS  read-only
    STATUS      current
    DESCRIPTION
        "The value of tmnxMobGwS8StatModifyBearerReq indicates the number of
         modify bearer request messages received from this peer or transmitted 
         to this peer."
    ::= { tmnxMobGwS8StatEntry 9 }

tmnxMobGwS8StatModifyBearerRsp  OBJECT-TYPE
    SYNTAX      Counter32
    MAX-ACCESS  read-only
    STATUS      current
    DESCRIPTION
        "The value of tmnxMobGwS8StatModifyBearerRsp indicates the number of
         modify bearer response messages received from this peer or transmitted 
         to this peer with cause code set to request accepted."
    ::= { tmnxMobGwS8StatEntry 10 }

tmnxMobGwS8StatRxEchoRequests  OBJECT-TYPE
    SYNTAX      Counter32
    MAX-ACCESS  read-only
    STATUS      current
    DESCRIPTION
        "The value of tmnxMobGwS8StatRxEchoRequests indicates the number of
         echo request messages received from this peer."
    ::= { tmnxMobGwS8StatEntry 11 }

tmnxMobGwS8StatTxEchoResponses  OBJECT-TYPE
    SYNTAX      Counter32
    MAX-ACCESS  read-only
    STATUS      current
    DESCRIPTION
        "The value of tmnxMobGwS8StatTxEchoResponses indicates the number of
         echo response messages transmitted to this peer."
    ::= { tmnxMobGwS8StatEntry 12 }

tmnxMobGwS8StatTxEchoRequests  OBJECT-TYPE
    SYNTAX      Counter32
    MAX-ACCESS  read-only
    STATUS      current
    DESCRIPTION
        "The value of tmnxMobGwS8StatTxEchoRequests indicates the number of
         echo request messages transmitted to this peer."
    ::= { tmnxMobGwS8StatEntry 13 }

tmnxMobGwS8StatRxEchoResponses  OBJECT-TYPE
    SYNTAX      Counter32
    MAX-ACCESS  read-only
    STATUS      current
    DESCRIPTION
        "The value of tmnxMobGwS8StatRxEchoResponses indicates the number of
         echo response messages received from this peer."
    ::= { tmnxMobGwS8StatEntry 14 }

tmnxMobGwS8StatRxMalformedPkts  OBJECT-TYPE
    SYNTAX      Counter32
    MAX-ACCESS  read-only
    STATUS      current
    DESCRIPTION
        "The value of tmnxMobGwS8StatRxMalformedPkts indicates the number of
         malformed packets received from this peer."
    ::= { tmnxMobGwS8StatEntry 15 }

tmnxMobGwS8StatRxUnknownPkts  OBJECT-TYPE
    SYNTAX      Counter32
    MAX-ACCESS  read-only
    STATUS      current
    DESCRIPTION
        "The value of tmnxMobGwS8StatRxUnknownPkts indicates the number of
         unknown message type packets received from this peer."
    ::= { tmnxMobGwS8StatEntry 16 }

tmnxMobGwS8StatRxMissingIePkts  OBJECT-TYPE
    SYNTAX      Counter32
    MAX-ACCESS  read-only
    STATUS      current
    DESCRIPTION
        "The value of tmnxMobGwS8StatRxMissingIePkts indicates the number of
         missing mandatory Information Element (IE) packets received from this
         peer."
    ::= { tmnxMobGwS8StatEntry 17 }

tmnxMobGwS8StatCreatePbu  OBJECT-TYPE
    SYNTAX      Counter32
    MAX-ACCESS  read-only
    STATUS      current
    DESCRIPTION
        "The value of tmnxMobGwS8StatCreatePbu indicates the number of Create
         Proxy Binding Update (PBU) messages transmitted to this peer."
    ::= { tmnxMobGwS8StatEntry 18 }

tmnxMobGwS8StatCreatePba  OBJECT-TYPE
    SYNTAX      Counter32
    MAX-ACCESS  read-only
    STATUS      current
    DESCRIPTION
        "The value of tmnxMobGwS8StatCreatePba indicates the number of Create
         Proxy Binding Acknowledgement (PBA) messages received from this
         peer."
    ::= { tmnxMobGwS8StatEntry 19 }

tmnxMobGwS8StatDeletePbu  OBJECT-TYPE
    SYNTAX      Counter32
    MAX-ACCESS  read-only
    STATUS      current
    DESCRIPTION
        "The value of tmnxMobGwS8StatDeletePbu indicates the number of Delete
         Proxy Binding Update (PBU) messages transmitted to this peer."
    ::= { tmnxMobGwS8StatEntry 20 }

tmnxMobGwS8StatDeletePba  OBJECT-TYPE
    SYNTAX      Counter32
    MAX-ACCESS  read-only
    STATUS      current
    DESCRIPTION
        "The value of tmnxMobGwS8StatDeletePba indicates the number of Delete
         Proxy Binding Acknowledgement (PBA) messages received from this
         peer."
    ::= { tmnxMobGwS8StatEntry 21 }

tmnxMobGwS8StatBri  OBJECT-TYPE
    SYNTAX      Counter32
    MAX-ACCESS  read-only
    STATUS      current
    DESCRIPTION
        "The value of tmnxMobGwS8StatBri indicates the number of network
         initiated delete Basic Rate Interface (BRI) messages received from
         this peer."
    ::= { tmnxMobGwS8StatEntry 22 }

tmnxMobGwS8StatBra  OBJECT-TYPE
    SYNTAX      Counter32
    MAX-ACCESS  read-only
    STATUS      current
    DESCRIPTION
        "The value of tmnxMobGwS8StatBra indicates the number of network
         initiated delete Basic Rate Access (BRA) messages transmitted to
         this peer."
    ::= { tmnxMobGwS8StatEntry 23 }

tmnxMobGwS8StatPeerRestarts  OBJECT-TYPE
    SYNTAX      Counter32
    MAX-ACCESS  read-only
    STATUS      current
    DESCRIPTION
        "The value of tmnxMobGwS8StatPeerRestarts indicates the number of
         times this peer restarted after registering with the system."
    ::= { tmnxMobGwS8StatEntry 24 }

tmnxMobGwS8StatPeerRestrtCount  OBJECT-TYPE
    SYNTAX      Counter32
    MAX-ACCESS  read-only
    STATUS      current
    DESCRIPTION
        "The value of tmnxMobGwS8StatPeerRestrtCount indicates the counter
         value of the number of times this peer restarted."
    ::= { tmnxMobGwS8StatEntry 25 }

tmnxMobGwS8StatPathMgmtFails  OBJECT-TYPE
    SYNTAX      Counter32
    MAX-ACCESS  read-only
    STATUS      current
    DESCRIPTION
        "The value of tmnxMobGwS8StatPathMgmtFails indicates the number of
         path management failures for this peer."
    ::= { tmnxMobGwS8StatEntry 26 }

tmnxMobGwS8StatUpdateBearerReq  OBJECT-TYPE
    SYNTAX      Counter32
    MAX-ACCESS  read-only
    STATUS      current
    DESCRIPTION
        "The value of tmnxMobGwS8StatUpdateBearerReq indicates the number of
         update bearer request messages received from this peer or transmitted 
         to this peer."
    ::= { tmnxMobGwS8StatEntry 27 }

tmnxMobGwS8StatUpdateBearerRsp  OBJECT-TYPE
    SYNTAX      Counter32
    MAX-ACCESS  read-only
    STATUS      current
    DESCRIPTION
        "The value of tmnxMobGwS8StatUpdateBearerRsp indicates the number of
         update bearer response messages received from this peer or transmitted 
         to this peer with cause code set to request accepted."
    ::= { tmnxMobGwS8StatEntry 28 }

tmnxMobGwS8StatCreatSessnRspFl    OBJECT-TYPE
    SYNTAX      Counter32
    MAX-ACCESS  read-only
    STATUS      current
    DESCRIPTION
        "The value of tmnxMobGwS8StatCreatSessnRspFl indicates the number of
         create session response messages received from this peer or transmitted 
         to this peer with cause code not set to request accepted."
    ::= { tmnxMobGwS8StatEntry 29 }

tmnxMobGwS8StatDelSessnRspFail    OBJECT-TYPE
    SYNTAX      Counter32
    MAX-ACCESS  read-only
    STATUS      current
    DESCRIPTION
        "The value of tmnxMobGwS8StatDelSessnRspFail indicates the number of
         delete session response messages received from this peer or transmitted 
         to this peer with cause code not set to request accepted."
    ::= { tmnxMobGwS8StatEntry 30 }

tmnxMobGwS8StatCreatBearrRspFl    OBJECT-TYPE
    SYNTAX      Counter32
    MAX-ACCESS  read-only
    STATUS      current
    DESCRIPTION
        "The value of tmnxMobGwS8StatCreatBearrRspFl indicates the number of
         create bearer response messages received from this peer or transmitted 
         to this peer with cause code not set to request accepted."
    ::= { tmnxMobGwS8StatEntry 31 }

tmnxMobGwS8StatDelBearrRspFail    OBJECT-TYPE
    SYNTAX      Counter32
    MAX-ACCESS  read-only
    STATUS      current
    DESCRIPTION
        "The value of tmnxMobGwS8StatDelBearrRspFail indicates the number of
         delete bearer response messages received from this peer or transmitted 
         to this peer with cause code not set to request accepted."
    ::= { tmnxMobGwS8StatEntry 32 }

tmnxMobGwS8StatModBearrRspFail    OBJECT-TYPE
    SYNTAX      Counter32
    MAX-ACCESS  read-only
    STATUS      current
    DESCRIPTION
        "The value of tmnxMobGwS8StatModBearrRspFail indicates the number of
         modify bearer response messages received from this peer or transmitted 
         to this peer with cause code not set to request accepted."
    ::= { tmnxMobGwS8StatEntry 33 }

tmnxMobGwS8StatUpdatBearrRspFl    OBJECT-TYPE
    SYNTAX      Counter32
    MAX-ACCESS  read-only
    STATUS      current
    DESCRIPTION
        "The value of tmnxMobGwS8StatUpdatBearrRspFl indicates the number of
         update bearer response messages received from this peer or transmitted 
         to this peer with cause code not set to request accepted."
    ::= { tmnxMobGwS8StatEntry 34 }

--
--  Rf peer list Table
--

tmnxMobGwRfPeerTableLastChngd     OBJECT-TYPE
    SYNTAX      TimeStamp
    MAX-ACCESS  read-only
    STATUS      current
    DESCRIPTION
        "The value of tmnxMobGwRfPeerTableLastChngd indicates the sysUpTime
         at the time of the last modification to tmnxMobGwRfPeerTable by
         adding, deleting an entry or change to a writable object in the table.

         If no changes were made to the table since the last re-initialization
         of the local network management subsystem, then this object contains
         a zero value."
    ::= { tmnxMobGatewayGlobalObjs 7 }

tmnxMobGwRfPeerTable  OBJECT-TYPE
    SYNTAX      SEQUENCE OF TmnxMobGwRfPeerEntry
    MAX-ACCESS  not-accessible
    STATUS      current
    DESCRIPTION
        "The tmnxMobGwRfPeerTable has an entry for each peer on the Rf
         reference point served by a mobile gateway."
    ::= { tmnxMobGatewayObjs 8 }

tmnxMobGwRfPeerEntry  OBJECT-TYPE
    SYNTAX      TmnxMobGwRfPeerEntry
    MAX-ACCESS  not-accessible
    STATUS      current
    DESCRIPTION
        "Each row entry represents a peer on the Rf reference point."
    INDEX { tmnxMobGwId,
            vRtrID,
            tmnxMobProfDiaPeerName,
            tmnxMobProfDiaPeerListIndex,
            tmnxMobGwRfPeerAddressType,
            tmnxMobGwRfPeerAddress,
            tmnxMobGwRfPeerPort
          }
    ::= { tmnxMobGwRfPeerTable 1 }

TmnxMobGwRfPeerEntry ::= SEQUENCE {
        tmnxMobGwRfPeerAddressType       InetAddressType,
        tmnxMobGwRfPeerAddress           InetAddress,
        tmnxMobGwRfPeerPort              InetPortNumber,
        tmnxMobGwRfPeerLastChanged       TimeStamp,
        tmnxMobGwRfPeerCreateTime        TimeStamp,
        tmnxMobGwRfPeerPathMgmtState     TmnxMobDiaPathMgmtState,
        tmnxMobGwRfPeerDetailState       TmnxMobDiaDetailPathMgmtState
    }

tmnxMobGwRfPeerAddressType  OBJECT-TYPE
    SYNTAX      InetAddressType
    MAX-ACCESS  not-accessible
    STATUS      current
    DESCRIPTION
        "The value of tmnxMobGwRfPeerAddressType indicates the type of
         address represented by tmnxMobGwRfPeerAddress."
    ::= { tmnxMobGwRfPeerEntry 1 }

tmnxMobGwRfPeerAddress  OBJECT-TYPE
    SYNTAX      InetAddress (SIZE (0|4|16))
    MAX-ACCESS  not-accessible
    STATUS      current
    DESCRIPTION
        "The value of tmnxMobGwRfPeerAddress indicates the IP address of the
         peer on Rf reference point."
    ::= { tmnxMobGwRfPeerEntry 2 }

tmnxMobGwRfPeerPort  OBJECT-TYPE
    SYNTAX      InetPortNumber
    MAX-ACCESS  not-accessible
    STATUS      current
    DESCRIPTION
        "The value of tmnxMobGwRfPeerPort indicates the port number of this
         peer."
    ::= { tmnxMobGwRfPeerEntry 3 }

tmnxMobGwRfPeerLastChanged  OBJECT-TYPE
    SYNTAX      TimeStamp
    MAX-ACCESS  read-only
    STATUS      current
    DESCRIPTION
        "The value of tmnxMobGwRfPeerLastChanged indicates the timestamp of
         the last change to this row in tmnxMobGwRfPeerTable."
    ::= { tmnxMobGwRfPeerEntry 4 }

tmnxMobGwRfPeerCreateTime  OBJECT-TYPE
    SYNTAX      TimeStamp
    MAX-ACCESS  read-only
    STATUS      current
    DESCRIPTION
        "The value of tmnxMobGwRfPeerCreateTime indicates the sysUpTime when
         this entry was created."
    ::= { tmnxMobGwRfPeerEntry 5 }

tmnxMobGwRfPeerPathMgmtState  OBJECT-TYPE
    SYNTAX      TmnxMobDiaPathMgmtState
    MAX-ACCESS  read-only
    STATUS      current
    DESCRIPTION
        "The value of tmnxMobGwRfPeerPathMgmtState indicates the state of
         the path."
    ::= { tmnxMobGwRfPeerEntry 6 }

tmnxMobGwRfPeerDetailState  OBJECT-TYPE
    SYNTAX      TmnxMobDiaDetailPathMgmtState
    MAX-ACCESS  read-only
    STATUS      current
    DESCRIPTION
        "The value of tmnxMobGwRfPeerDetailState indicates the detail state
         of the path."
    ::= { tmnxMobGwRfPeerEntry 7 }

--
--  Rf Stats Table
--

tmnxMobGwRfStatTable  OBJECT-TYPE
    SYNTAX      SEQUENCE OF TmnxMobGwRfStatEntry
    MAX-ACCESS  not-accessible
    STATUS      current
    DESCRIPTION
        "The tmnxMobGwRfStatTable has an entry for each peer on the Rf
         reference point served by a mobile gateway."
    ::= { tmnxMobGatewayObjs 9 }

tmnxMobGwRfStatEntry  OBJECT-TYPE
    SYNTAX      TmnxMobGwRfStatEntry
    MAX-ACCESS  not-accessible
    STATUS      current
    DESCRIPTION
        "Each row entry represents a peer on the Rf reference point and
         contain statistics for this peer on a card."
    INDEX { tmnxMobGwId,
            vRtrID,
            tmnxMobProfDiaPeerName,
            tmnxMobProfDiaPeerListIndex,
            tmnxMobGwRfPeerAddressType,
            tmnxMobGwRfPeerAddress,
            tmnxMobGwRfPeerPort,
            tmnxChassisIndex,
            tmnxCardSlotNum
          }
    ::= { tmnxMobGwRfStatTable 1 }
    
TmnxMobGwRfStatEntry ::= SEQUENCE {
        tmnxMobGwRfStatTxCer               Counter32,
        tmnxMobGwRfStatRxCea               Counter32,
        tmnxMobGwRfStatRxDpr               Counter32,
        tmnxMobGwRfStatTxDpa               Counter32,
        tmnxMobGwRfStatTxDwr               Counter32,
        tmnxMobGwRfStatRxDwa               Counter32,
        tmnxMobGwRfStatConnAttempts        Counter32,
        tmnxMobGwRfStatConnFailures        Counter32,
        tmnxMobGwRfStatRxTransportDisc     Counter32,
        tmnxMobGwRfStatRxMsgUnexpectVer    Counter32,
        tmnxMobGwRfStatRxMsgTooBig         Counter32,
        tmnxMobGwRfStatRxMsgTooSmall       Counter32,
        tmnxMobGwRfStatRxInvalidCea        Counter32,
        tmnxMobGwRfStatRxMsgs              Counter32,
        tmnxMobGwRfStatTxMsgs              Counter32,
        tmnxMobGwRfStatTxRetransmitMsgs    Counter32,
        tmnxMobGwRfStatTxAcrStart          Counter32,
        tmnxMobGwRfStatTxAcrInterim        Counter32,
        tmnxMobGwRfStatTxAcrStop           Counter32,
        tmnxMobGwRfStatTxAcrStartFails     Counter32,
        tmnxMobGwRfStatTxAcrInterimFail    Counter32,
        tmnxMobGwRfStatTxAcrStopFails      Counter32,
        tmnxMobGwRfStatBearers             Gauge32, 
        tmnxMobGwRfStatDefBearers          Gauge32,
        tmnxMobGwRfStatDedctdBearers       Gauge32,
        tmnxMobGwRfStatRoamers             Gauge32,
        tmnxMobGwRfStatBearersIpv4         Gauge32,
        tmnxMobGwRfStatBearersIpv6         Gauge32,
        tmnxMobGwRfStatBearersIpv4v6       Gauge32,
        tmnxMobGwRfStatActiveBearers       Gauge32,
        tmnxMobGwRfStatIdleBearers         Gauge32,
        tmnxMobGwRfStatTxDpr               Counter32,
        tmnxMobGwRfStatRxDpa               Counter32,
        tmnxMobGwRfStatRxDwr               Counter32,
        tmnxMobGwRfStatTxDwa               Counter32
    }

tmnxMobGwRfStatTxCer  OBJECT-TYPE
    SYNTAX      Counter32
    MAX-ACCESS  read-only
    STATUS      current
    DESCRIPTION
        "The value of tmnxMobGwRfStatTxCer indicates the number of Capabilities
         Exchange Request (CER) messages transmitted to this peer."
    ::= { tmnxMobGwRfStatEntry 1 }

tmnxMobGwRfStatRxCea  OBJECT-TYPE
    SYNTAX      Counter32
    MAX-ACCESS  read-only
    STATUS      current
    DESCRIPTION
        "The value of tmnxMobGwRfStatRxCea indicates the number of Capabilities
         Exchange Answer (CEA) messages received from this peer."
    ::= { tmnxMobGwRfStatEntry 2 }

tmnxMobGwRfStatRxDpr  OBJECT-TYPE
    SYNTAX      Counter32
    MAX-ACCESS  read-only
    STATUS      current
    DESCRIPTION
        "The value of tmnxMobGwRfStatRxDpr indicates the number of Disconnect
         Peer Request (DPR) messages received from this peer."
    ::= { tmnxMobGwRfStatEntry 3 }

tmnxMobGwRfStatTxDpa  OBJECT-TYPE
    SYNTAX      Counter32
    MAX-ACCESS  read-only
    STATUS      current
    DESCRIPTION
        "The value of tmnxMobGwRfStatTxDpa indicates the number of Disconnect
         Peer Answer (DPA) messages transmitted to this peer."
    ::= { tmnxMobGwRfStatEntry 4 }

tmnxMobGwRfStatTxDwr  OBJECT-TYPE
    SYNTAX      Counter32
    MAX-ACCESS  read-only
    STATUS      current
    DESCRIPTION
        "The value of tmnxMobGwRfStatTxDwr indicates the number of Device
         Watchdog Request (DWR) messages transmitted to this peer."
    ::= { tmnxMobGwRfStatEntry 5 }

tmnxMobGwRfStatRxDwa  OBJECT-TYPE
    SYNTAX      Counter32
    MAX-ACCESS  read-only
    STATUS      current
    DESCRIPTION
        "The value of tmnxMobGwRfStatRxDwa indicates the number of Device
         Watchdog Answer (DWA) messages received from this peer."
    ::= { tmnxMobGwRfStatEntry 6 }

tmnxMobGwRfStatConnAttempts  OBJECT-TYPE
    SYNTAX      Counter32
    MAX-ACCESS  read-only
    STATUS      current
    DESCRIPTION
        "The value of tmnxMobGwRfStatConnAttempts indicates the number of 
         connections attempted to this peer."
    ::= { tmnxMobGwRfStatEntry 7 }

tmnxMobGwRfStatConnFailures  OBJECT-TYPE
    SYNTAX      Counter32
    MAX-ACCESS  read-only
    STATUS      current
    DESCRIPTION
        "The value of tmnxMobGwRfStatConnFailures indicates the number of 
         failed connections with this peer."
    ::= { tmnxMobGwRfStatEntry 8 }

tmnxMobGwRfStatRxTransportDisc  OBJECT-TYPE
    SYNTAX      Counter32
    MAX-ACCESS  read-only
    STATUS      current
    DESCRIPTION
        "The value of tmnxMobGwRfStatRxTransportDisc indicates the number of 
         remote transport disconnect messages received from this peer."
    ::= { tmnxMobGwRfStatEntry 9 }

tmnxMobGwRfStatRxMsgUnexpectVer  OBJECT-TYPE
    SYNTAX      Counter32
    MAX-ACCESS  read-only
    STATUS      current
    DESCRIPTION
        "The value of tmnxMobGwRfStatRxMsgUnexpectVer indicates the number of 
         unexpected version messages received from this peer."
    ::= { tmnxMobGwRfStatEntry 10 }

tmnxMobGwRfStatRxMsgTooBig  OBJECT-TYPE
    SYNTAX      Counter32
    MAX-ACCESS  read-only
    STATUS      current
    DESCRIPTION
        "The value of tmnxMobGwRfStatRxMsgTooBig indicates the number of 
         oversize messages received from this peer."
    ::= { tmnxMobGwRfStatEntry 11 }

tmnxMobGwRfStatRxMsgTooSmall  OBJECT-TYPE
    SYNTAX      Counter32
    MAX-ACCESS  read-only
    STATUS      current
    DESCRIPTION
        "The value of tmnxMobGwRfStatRxMsgTooSmall indicates the number of 
         small messages received from this peer."
    ::= { tmnxMobGwRfStatEntry 12 }

tmnxMobGwRfStatRxInvalidCea  OBJECT-TYPE
    SYNTAX      Counter32
    MAX-ACCESS  read-only
    STATUS      current
    DESCRIPTION
        "The value of tmnxMobGwRfStatRxInvalidCea indicates the number of 
         invalid Capabilities Exchange Answer (CEA) messages received from 
         this peer."
    ::= { tmnxMobGwRfStatEntry 13 }

tmnxMobGwRfStatRxMsgs  OBJECT-TYPE
    SYNTAX      Counter32
    MAX-ACCESS  read-only
    STATUS      current
    DESCRIPTION
        "The value of tmnxMobGwRfStatRxMsgs indicates the total number of 
         messages received from this peer."
    ::= { tmnxMobGwRfStatEntry 14 }

tmnxMobGwRfStatTxMsgs  OBJECT-TYPE
    SYNTAX      Counter32
    MAX-ACCESS  read-only
    STATUS      current
    DESCRIPTION
        "The value of tmnxMobGwRfStatTxMsgs indicates the total number of 
         messages transmitted to this peer."
    ::= { tmnxMobGwRfStatEntry 15 }

tmnxMobGwRfStatTxRetransmitMsgs  OBJECT-TYPE
    SYNTAX      Counter32
    MAX-ACCESS  read-only
    STATUS      current
    DESCRIPTION
        "The value of tmnxMobGwRfStatTxRetransmitMsgs indicates the number of 
         retransmit messages transmitted to this peer."
    ::= { tmnxMobGwRfStatEntry 16 }

tmnxMobGwRfStatTxAcrStart  OBJECT-TYPE
    SYNTAX      Counter32
    MAX-ACCESS  read-only
    STATUS      current
    DESCRIPTION
        "The value of tmnxMobGwRfStatTxAcrStart indicates the number of
         Accounting Request (ACR) Start messages transmitted to this peer."
    ::= { tmnxMobGwRfStatEntry 17 }

tmnxMobGwRfStatTxAcrInterim  OBJECT-TYPE
    SYNTAX      Counter32
    MAX-ACCESS  read-only
    STATUS      current
    DESCRIPTION
        "The value of tmnxMobGwRfStatTxAcrInterim indicates the number of
         Accounting Request (ACR) Interim messages transmitted to this peer."
    ::= { tmnxMobGwRfStatEntry 18 }

tmnxMobGwRfStatTxAcrStop  OBJECT-TYPE
    SYNTAX      Counter32
    MAX-ACCESS  read-only
    STATUS      current
    DESCRIPTION
        "The value of tmnxMobGwRfStatTxAcrStop indicates the number of
         Accounting Request (ACR) Stop messages transmitted to this peer."
    ::= { tmnxMobGwRfStatEntry 19 }

tmnxMobGwRfStatTxAcrStartFails  OBJECT-TYPE
    SYNTAX      Counter32
    MAX-ACCESS  read-only
    STATUS      current
    DESCRIPTION
        "The value of tmnxMobGwRfStatTxAcrStartFails indicates the number of
         Accounting Request (ACR) Start message failures."
    ::= { tmnxMobGwRfStatEntry 20 }

tmnxMobGwRfStatTxAcrInterimFail  OBJECT-TYPE
    SYNTAX      Counter32
    MAX-ACCESS  read-only
    STATUS      current
    DESCRIPTION
        "The value of tmnxMobGwRfStatTxAcrInterimFail indicates the number of
         Accounting Request (ACR) Interim message failures."
    ::= { tmnxMobGwRfStatEntry 21 }

tmnxMobGwRfStatTxAcrStopFails  OBJECT-TYPE
    SYNTAX      Counter32
    MAX-ACCESS  read-only
    STATUS      current
    DESCRIPTION
        "The value of tmnxMobGwRfStatTxAcrStopFails indicates the number of
         Accounting Request (ACR) Stop message failures."
    ::= { tmnxMobGwRfStatEntry 22 }

tmnxMobGwRfStatBearers  OBJECT-TYPE
    SYNTAX      Gauge32
    MAX-ACCESS  read-only
    STATUS      current
    DESCRIPTION
        "The value of tmnxMobGwRfStatBearers indicates the number of
         bearers being served by this peer."
    ::= { tmnxMobGwRfStatEntry 23 }

tmnxMobGwRfStatDefBearers  OBJECT-TYPE
    SYNTAX      Gauge32
    MAX-ACCESS  read-only
    STATUS      current
    DESCRIPTION
        "The value of tmnxMobGwRfStatDefBearers indicates the number of
         default bearers being served by this peer."
    ::= { tmnxMobGwRfStatEntry 24 }

tmnxMobGwRfStatDedctdBearers  OBJECT-TYPE
    SYNTAX      Gauge32
    MAX-ACCESS  read-only
    STATUS      current
    DESCRIPTION
        "The value of tmnxMobGwRfStatDedctdBearers indicates the number of
         dedicated bearers being served by this peer."
    ::= { tmnxMobGwRfStatEntry 25 }

tmnxMobGwRfStatRoamers  OBJECT-TYPE
    SYNTAX      Gauge32
    MAX-ACCESS  read-only
    STATUS      current
    DESCRIPTION
        "The value of tmnxMobGwRfStatRoamers indicates the number of
         roamers being served by this peer."
    ::= { tmnxMobGwRfStatEntry 26 }

tmnxMobGwRfStatBearersIpv4  OBJECT-TYPE
    SYNTAX      Gauge32
    MAX-ACCESS  read-only
    STATUS      current
    DESCRIPTION
        "The value of tmnxMobGwRfStatBearersIpv4 indicates the number of
         IPv4 bearers being served by this peer."
    ::= { tmnxMobGwRfStatEntry 27 }    

tmnxMobGwRfStatBearersIpv6  OBJECT-TYPE
    SYNTAX      Gauge32
    MAX-ACCESS  read-only
    STATUS      current
    DESCRIPTION
        "The value of tmnxMobGwRfStatBearersIpv6 indicates the number of
         IPv6 bearers being served by this peer."
    ::= { tmnxMobGwRfStatEntry 28 }  

tmnxMobGwRfStatBearersIpv4v6  OBJECT-TYPE
    SYNTAX      Gauge32
    MAX-ACCESS  read-only
    STATUS      current
    DESCRIPTION
        "The value of tmnxMobGwRfStatBearersIpv4v6 indicates the number of
         IPv4v6 bearers being served by this peer."
    ::= { tmnxMobGwRfStatEntry 29 }      

tmnxMobGwRfStatActiveBearers  OBJECT-TYPE
    SYNTAX      Gauge32
    MAX-ACCESS  read-only
    STATUS      current
    DESCRIPTION
        "The value of tmnxMobGwRfStatActiveBearers indicates the number of
         active bearers being served by this peer."
    ::= { tmnxMobGwRfStatEntry 30 }

tmnxMobGwRfStatIdleBearers  OBJECT-TYPE
    SYNTAX      Gauge32
    MAX-ACCESS  read-only
    STATUS      current
    DESCRIPTION
        "The value of tmnxMobGwRfStatIdleBearers indicates the number of
         idle bearers being served by this peer."
    ::= { tmnxMobGwRfStatEntry 31 }    

tmnxMobGwRfStatTxDpr             OBJECT-TYPE
    SYNTAX      Counter32
    MAX-ACCESS  read-only
    STATUS      current
    DESCRIPTION
        "The value of tmnxMobGwRfStatTxDpr indicates the number of Disconnect
         Peer Request (DPR) messages transmitted to this peer."
    ::= { tmnxMobGwRfStatEntry 32 }

tmnxMobGwRfStatRxDpa             OBJECT-TYPE
    SYNTAX      Counter32
    MAX-ACCESS  read-only
    STATUS      current
    DESCRIPTION
        "The value of tmnxMobGwRfStatRxDpa indicates the number of Disconnect
         Peer Answer (DPA) messages received from this peer."
    ::= { tmnxMobGwRfStatEntry 33 }

tmnxMobGwRfStatRxDwr             OBJECT-TYPE
    SYNTAX      Counter32
    MAX-ACCESS  read-only
    STATUS      current
    DESCRIPTION
        "The value of tmnxMobGwRfStatRxDwr indicates the number of Device
         Watchdog Request (DWR) messages received from this peer."
    ::= { tmnxMobGwRfStatEntry 34 }

tmnxMobGwRfStatTxDwa             OBJECT-TYPE
    SYNTAX      Counter32
    MAX-ACCESS  read-only
    STATUS      current
    DESCRIPTION
        "The value of tmnxMobGwRfStatTxDwa indicates the number of Device
         Watchdog Answer (DWA) messages transmitted to this peer."
    ::= { tmnxMobGwRfStatEntry 35 }

--
--  LI Df Peer Table
--

tmnxMobLiDfPeerTableLastChanged     OBJECT-TYPE
    SYNTAX      TimeStamp
    MAX-ACCESS  read-only
    STATUS      current
    DESCRIPTION
        "The value of tmnxMobLiDfPeerTableLastChanged indicates the sysUpTime at
         the time of the last modification to tmnxMobLiDfPeerTable by adding,
         deleting an entry or change to a writable object in the table.

         If no changes were made to the table since the last re-initialization
         of the local network management subsystem, then this object contains
         a zero value."
    ::= { tmnxMobGatewayGlobalObjs 8 }

tmnxMobLiDfPeerTable  OBJECT-TYPE
    SYNTAX      SEQUENCE OF TmnxMobLiDfPeerEntry
    MAX-ACCESS  not-accessible
    STATUS      current
    DESCRIPTION
        "The tmnxMobLiDfPeerTable has an entry for each Delivery Function (DF)
         peer for the Lawful Interception (LI)."
    ::= { tmnxMobGatewayObjs 10 }

tmnxMobLiDfPeerEntry  OBJECT-TYPE
    SYNTAX      TmnxMobLiDfPeerEntry
    MAX-ACCESS  not-accessible
    STATUS      current
    DESCRIPTION
        "Each row entry represents a Delivery Function (DF) peer for Lawful 
         Interception (LI)."
    INDEX { tmnxMobLiDfPeer }
    ::= { tmnxMobLiDfPeerTable 1 }

TmnxMobLiDfPeerEntry ::= SEQUENCE {
        tmnxMobLiDfPeer                   TmnxMobDfPeerId,
        tmnxMobLiDfPeerRowStatus          RowStatus,
        tmnxMobLiDfPeerLastChanged        TimeStamp,
        tmnxMobLiDf2PeerAddressType       InetAddressType,
        tmnxMobLiDf2PeerAddress           InetAddress,
        tmnxMobLiDf2PeerPort              InetPortNumber,
        tmnxMobLiDf3PeerAddressType       InetAddressType,
        tmnxMobLiDf3PeerAddress           InetAddress,
        tmnxMobLiDf3PeerPort              InetPortNumber,
        tmnxMobLiDf2OperState             TmnxOperState,
        tmnxMobLiDf2PeerPktsTx            Counter32,
        tmnxMobLiDf3OperState             TmnxOperState,
        tmnxMobLiDf3PeerPktsTx            Counter32,
        tmnxMobLiTotalTargetPerPeer       Counter32
    }

tmnxMobLiDfPeer  OBJECT-TYPE
    SYNTAX      TmnxMobDfPeerId
    MAX-ACCESS  not-accessible
    STATUS      current
    DESCRIPTION
        "The value of tmnxMobLiDfPeer uniquely identifies a Delivery Function
         (DF) peer configured for Lawful Interception (LI) in the system."
    ::= { tmnxMobLiDfPeerEntry 1 }

tmnxMobLiDfPeerRowStatus  OBJECT-TYPE
    SYNTAX      RowStatus
    MAX-ACCESS  read-create
    STATUS      current
    DESCRIPTION
        "The value of tmnxMobLiDfPeerRowStatus specifies the row status of
         this entry. It is used for creation and deletion of this Delivery 
         Function (DF) peer configured for the Lawful Interception (LI) in the
         system."
    ::= { tmnxMobLiDfPeerEntry 2 }

tmnxMobLiDfPeerLastChanged  OBJECT-TYPE
    SYNTAX      TimeStamp
    MAX-ACCESS  read-only
    STATUS      current
    DESCRIPTION
        "The value of tmnxMobLiDfPeerLastChanged indicates the timestamp of
         the last change to this row in tmnxMobLiDfPeerTable."
    ::= { tmnxMobLiDfPeerEntry 3 }

tmnxMobLiDf2PeerAddressType  OBJECT-TYPE
    SYNTAX      InetAddressType
    MAX-ACCESS  read-create
    STATUS      current
    DESCRIPTION
        "The value of tmnxMobLiDf2PeerAddressType specifies the type of
         address represented by tmnxMobLiDf2PeerAddress."
    DEFVAL { unknown }
    ::= { tmnxMobLiDfPeerEntry 4 }

tmnxMobLiDf2PeerAddress  OBJECT-TYPE
    SYNTAX      InetAddress (SIZE (4|16))
    MAX-ACCESS  read-create
    STATUS      current
    DESCRIPTION
        "The value of tmnxMobLiDf2PeerAddress specifies the IP address of the
         Delivery Function peer."
    DEFVAL { ''H }
    ::= { tmnxMobLiDfPeerEntry 5 }

tmnxMobLiDf2PeerPort  OBJECT-TYPE
    SYNTAX      InetPortNumber
    MAX-ACCESS  read-create
    STATUS      current
    DESCRIPTION
        "The value of tmnxMobLiDf2PeerPort specifies the port number of this
         peer."
    ::= { tmnxMobLiDfPeerEntry 6 }

tmnxMobLiDf3PeerAddressType  OBJECT-TYPE
    SYNTAX      InetAddressType
    MAX-ACCESS  read-create
    STATUS      current
    DESCRIPTION
        "The value of tmnxMobLiDf3PeerAddressType specifies the type of
         address represented by tmnxMobLiDf3PeerAddress."
    DEFVAL { unknown }
    ::= { tmnxMobLiDfPeerEntry 7 }

tmnxMobLiDf3PeerAddress  OBJECT-TYPE
    SYNTAX      InetAddress (SIZE (4|16))
    MAX-ACCESS  read-create
    STATUS      current
    DESCRIPTION
        "The value of tmnxMobLiDf3PeerAddress specifies the IP address of the
         Delivery Function peer."
    DEFVAL { ''H }
    ::= { tmnxMobLiDfPeerEntry 8 }

tmnxMobLiDf3PeerPort  OBJECT-TYPE
    SYNTAX      InetPortNumber
    MAX-ACCESS  read-create
    STATUS      current
    DESCRIPTION
        "The value of tmnxMobLiDf3PeerPort specifies the port number of this
         peer."
    ::= { tmnxMobLiDfPeerEntry 9 }

tmnxMobLiDf2OperState  OBJECT-TYPE
    SYNTAX      TmnxOperState
    MAX-ACCESS  read-only
    STATUS      current
    DESCRIPTION
        "The value of tmnxMobLiDf2OperState indicates the current operational 
         status of the Delivery Function 2 peer."
    ::= { tmnxMobLiDfPeerEntry 10 }

tmnxMobLiDf2PeerPktsTx  OBJECT-TYPE
    SYNTAX      Counter32
    MAX-ACCESS  read-only
    STATUS      current
    DESCRIPTION
        "The value of tmnxMobLiDf2PeerPktsTx indicates the number of packets
         transmitted to the Delivery Function 2 peer."
    ::= { tmnxMobLiDfPeerEntry 11 }

tmnxMobLiDf3OperState  OBJECT-TYPE
    SYNTAX      TmnxOperState
    MAX-ACCESS  read-only
    STATUS      current
    DESCRIPTION
        "The value of tmnxMobLiDf3OperState indicates the current operational 
         status of the Delivery Function 3 peer."
    ::= { tmnxMobLiDfPeerEntry 12 }

tmnxMobLiDf3PeerPktsTx  OBJECT-TYPE
    SYNTAX      Counter32
    MAX-ACCESS  read-only
    STATUS      current
    DESCRIPTION
        "The value of tmnxMobLiDf3PeerPktsTx indicates the number of packets
         transmitted to the Delivery Function 3 peer."
    ::= { tmnxMobLiDfPeerEntry 13 }

tmnxMobLiTotalTargetPerPeer  OBJECT-TYPE
    SYNTAX       Counter32
    MAX-ACCESS   read-only
    STATUS       current
    DESCRIPTION
        "The value of tmnxMobLiTotalTargetPerPeer indicates the total number of 
         targets or subscribers configured per peer"
    ::= { tmnxMobLiDfPeerEntry 14 }

--
--  LI Target Table
--

tmnxMobLiTargetTableLastChanged     OBJECT-TYPE
    SYNTAX      TimeStamp
    MAX-ACCESS  read-only
    STATUS      current
    DESCRIPTION
        "The value of tmnxMobLiTargetTableLastChanged indicates the sysUpTime at
         the time of the last modification to tmnxMobLiTargetTable by adding,
         deleting an entry or change to a writable object in the table.

         If no changes were made to the table since the last re-initialization
         of the local network management subsystem, then this object contains
         a zero value."
    ::= { tmnxMobGatewayGlobalObjs 9 }

tmnxMobLiTargetTable  OBJECT-TYPE
    SYNTAX      SEQUENCE OF TmnxMobLiTargetEntry
    MAX-ACCESS  not-accessible
    STATUS      current
    DESCRIPTION
        "The tmnxMobLiTargetTable has an entry for each target for the 
         interception."
    ::= { tmnxMobGatewayObjs 11 }

tmnxMobLiTargetEntry  OBJECT-TYPE
    SYNTAX      TmnxMobLiTargetEntry
    MAX-ACCESS  not-accessible
    STATUS      current
    DESCRIPTION
        "Each row entry represents a target for the interception."
    INDEX { tmnxMobLiTargetType,
            tmnxMobLiTargetId   
          }
    ::= { tmnxMobLiTargetTable 1 }

TmnxMobLiTargetEntry ::= SEQUENCE {
        tmnxMobLiTargetType               TmnxMobLiTargetType,
        tmnxMobLiTargetId                 TmnxMobLiTarget,
        tmnxMobLiTargetRowStatus          RowStatus,
        tmnxMobLiTargetLastChanged        TimeStamp,
        tmnxMobLiTargetInterceptType      INTEGER,  
        tmnxMobLiTargetDfPeer             TmnxMobDfPeerId,
        tmnxMobTargetLiId                 TNamedItemOrEmpty
    }

tmnxMobLiTargetType  OBJECT-TYPE
    SYNTAX      TmnxMobLiTargetType
    MAX-ACCESS  not-accessible
    STATUS      current
    DESCRIPTION
        "The value of tmnxMobLiTargetType specifies a target type for the 
         interception."
    ::= { tmnxMobLiTargetEntry 1 }

tmnxMobLiTargetId  OBJECT-TYPE
    SYNTAX      TmnxMobLiTarget
    MAX-ACCESS  not-accessible
    STATUS      current
    DESCRIPTION
        "The value of tmnxMobLiTargetId uniquely identifies a target for the 
         interception."
    ::= { tmnxMobLiTargetEntry 2 }

tmnxMobLiTargetRowStatus  OBJECT-TYPE
    SYNTAX      RowStatus
    MAX-ACCESS  read-create
    STATUS      current
    DESCRIPTION
        "The value of tmnxMobLiTargetRowStatus specifies the row status of
         this entry. It is used for creation and deletion of this target for the 
         interception."
    ::= { tmnxMobLiTargetEntry 3 }

tmnxMobLiTargetLastChanged  OBJECT-TYPE
    SYNTAX      TimeStamp
    MAX-ACCESS  read-only
    STATUS      current
    DESCRIPTION
        "The value of tmnxMobLiTargetLastChanged indicates the timestamp of
         the last change to this row in tmnxMobLiTargetTable."
    ::= { tmnxMobLiTargetEntry 4 }

tmnxMobLiTargetInterceptType  OBJECT-TYPE
    SYNTAX      INTEGER {
                         iri    (1),
                         iriCC  (2)
                        }
    MAX-ACCESS  read-create
    STATUS      current
    DESCRIPTION
        "The value of tmnxMobLiTargetInterceptType specifies the interception
         type for the target.
                
         iri    -    Intercept Related Information (IRI)
         iriCC  -    Intercept Related Information (IRI) and Content of 
                     Communication (CC)"
    DEFVAL { iri }
    ::= { tmnxMobLiTargetEntry 5 }

tmnxMobLiTargetDfPeer  OBJECT-TYPE
    SYNTAX      TmnxMobDfPeerId
    MAX-ACCESS  read-create
    STATUS      current
    DESCRIPTION
        "The value of tmnxMobLiTargetDfPeer specifies the Delivery Function (DF)
         Peer associated with the target."
    DEFVAL { 1 }
    ::= { tmnxMobLiTargetEntry 6 }

tmnxMobTargetLiId   OBJECT-TYPE
    SYNTAX         TNamedItemOrEmpty (SIZE (0..25))
    MAX-ACCESS     read-create
    STATUS         current
    DESCRIPTION
        "The value of tmnxMobTargetLiId specifies the special Lawful Intercept
         Identifier (LIID) assigned to each target identity by the authorized 
         operator."
    DEFVAL { ''H }
    ::= { tmnxMobLiTargetEntry 7}

tmnxMobGatewayGlobalLiObjs        OBJECT IDENTIFIER ::= { tmnxMobGatewayGlobalObjs 11 }


tmnxMobLiX3Transport  OBJECT-TYPE
    SYNTAX      INTEGER {
                        tcp   (1),
                        udp   (2)
                        } 
    MAX-ACCESS  read-create
    STATUS      current
    DESCRIPTION
        "The value of tmnxMobLiX3Transport specifies the transport option for
         X3 interface. The same transport option is supported to all the Delivery 
         Function (DF) peers in a service provider network "
    ::= { tmnxMobGatewayGlobalLiObjs 1 }

tmnxMobLiLocalInterfaceType  OBJECT-TYPE
    SYNTAX      InetAddressType
    MAX-ACCESS  read-create
    STATUS      current
    DESCRIPTION
        "The value of tmnxMobLiLocalInterfaceType specifies the type of
         address represented by tmnxMobLiLocalInterface."
    DEFVAL { unknown }
    ::= { tmnxMobGatewayGlobalLiObjs 2 }

tmnxMobLiLocalInterface  OBJECT-TYPE
    SYNTAX      InetAddress (SIZE(4|16))
    MAX-ACCESS  read-create
    STATUS      current
    DESCRIPTION
        "The value of tmnxMobLiLocalInterface specifies the source IP 
         address used by the xGW/GGSN for Lawful Intercept (LI) interface."
    DEFVAL { ''H }
    ::= { tmnxMobGatewayGlobalLiObjs 3 }

tmnxMobLiTotalTargets OBJECT-TYPE
    SYNTAX      Counter32
    MAX-ACCESS  read-only
    STATUS      current
    DESCRIPTION
        "The value of tmnxMobLiTotalTargets specifies the total number of
         subscribers configured for the Lawful Intercept (LI) purposes."
    ::= { tmnxMobGatewayGlobalLiObjs 4 }

tmnxMobLiTotalPeers OBJECT-TYPE
    SYNTAX      Counter32
    MAX-ACCESS  read-only
    STATUS      current
    DESCRIPTION
        "The value of tmnxMobLiTotalPeers specifies the total number of
         peers configured to receive the Lawful Intercept (LI) information."
    ::= { tmnxMobGatewayGlobalLiObjs 5 }

tmnxMobLiTotalIRITargets OBJECT-TYPE
    SYNTAX      Counter32
    MAX-ACCESS  read-only
    STATUS      current
    DESCRIPTION
        "The value of tmnxMobLiTotalIRITargets specifies the total number of
         subscribers for which only the Intercept Related Information (IRI) or
         control plane information is intercepted."
    ::= { tmnxMobGatewayGlobalLiObjs 6 }

tmnxMobLiTotalIRICCTargets OBJECT-TYPE
    SYNTAX      Counter32
    MAX-ACCESS  read-only
    STATUS      current
    DESCRIPTION
        "The value of tmnxMobLiTotalIRICCTargets specifies the total number of
         subscribers for which the Content of Communication (CC) or the data plane
         is intercepted along with the Intercept Related Information (IRI) or control
         plane information."
    ::= { tmnxMobGatewayGlobalLiObjs 7 }

tmnxMobLiVprnId   OBJECT-TYPE
    SYNTAX      TmnxVRtrID
    MAX-ACCESS  read-create
    STATUS      current
    DESCRIPTION
        "The value of tmnxMobLiVprnId specifies the vprn routing context identifier."
    DEFVAL { 1 }
    ::= { tmnxMobGatewayGlobalLiObjs 8 }

tmnxMobLiULICVersion  OBJECT-TYPE
    SYNTAX       INTEGER {
                              v0         (0),
                              v1         (1)
                          }
    MAX-ACCESS     read-create
    STATUS         current
    DESCRIPTION
        "The value of tmnxMobLiULICVersion specifies the UMTS LI Correlation 
         (ULIC) header version used with the X3 interface.

         The value of tmnxMobLiULICVersion defaults to 'v1' when tmnxMobLiX3Transport
         is set to 'tcp' and the value of tmnxMobLiULICVersion defaults to 'v0' when 
         tmnxMobLiX3Transport is set to 'udp'."
    ::= {tmnxMobGatewayGlobalLiObjs 9 }

tmnxMobLiULIChangeReporting  OBJECT-TYPE
    SYNTAX      INTEGER {
                            enable (0),
                            disable(1)
                         }

    MAX-ACCESS     read-create
    STATUS         current
    DESCRIPTION
        "The value of tmnxMobLiULIChangeReporting specifies if the User 
         Location Information (ULI) change report subscription should be 
         enabled with/from the Mobile Management Entity (MME) for the Lawful 
         Intercept (LI) targets."
    DEFVAL { enable }
    ::= { tmnxMobGatewayGlobalLiObjs 10 }

tmnxMobLiOperatorId  OBJECT-TYPE
    SYNTAX      TNamedItem (SIZE (1..5))
    MAX-ACCESS  read-create
    STATUS      current 
    DESCRIPTION
        "The value of tmnxMobLiOperatorId specifies the operator identifier
         for an operator's deployment. This value is used to populate the
         operator-identifier field of the network-identifier Information 
         Element(IE)."
    DEFVAL { "op_id" }
    ::=  {tmnxMobGatewayGlobalLiObjs 11 }

--
--  Threshold based monitoring Group table
--

tmnxMobThresGroupLastChgd  OBJECT-TYPE
    SYNTAX      TimeStamp
    MAX-ACCESS  read-only
    STATUS      current
    DESCRIPTION
        "The value of tmnxMobThresGroupLastChgd indicates the sysUpTime
         at the time of the last modification to tmnxMobThresGroupTable by
         adding, deleting an entry or change to a writable object in the table.

         If no changes were made to the table since the last re-initialization
         of the local network management subsystem, then this object contains
         a zero value."
    ::= { tmnxMobGatewayGlobalObjs 10 }

tmnxMobThresGroupTable OBJECT-TYPE
    SYNTAX      SEQUENCE OF TmnxMobThresGroupEntry
    MAX-ACCESS  not-accessible
    STATUS      current
    DESCRIPTION
        "The tmnxMobThresGroupTable has an entry for each threshold based
         monitoring group in the mobile gateway."
    ::= { tmnxMobGatewayObjs 12 }

tmnxMobThresGroupEntry  OBJECT-TYPE
    SYNTAX      TmnxMobThresGroupEntry
    MAX-ACCESS  not-accessible
    STATUS      current
    DESCRIPTION
        "Each row entry represents a threshold based monitoring group in 
         a mobile gateway."
    INDEX { tmnxMobGwId,
            tmnxMobThresGrpId,
            tmnxMobThresSubGrpId
          }
    ::= { tmnxMobThresGroupTable 1 }

TmnxMobThresGroupEntry ::= SEQUENCE {
        tmnxMobThresGrpId              TmnxThresholdGroupType,
        tmnxMobThresSubGrpId           Unsigned32,
        tmnxMobThresGrpRowStatus       RowStatus,
        tmnxMobThresGrpLastChanged     TimeStamp,
        tmnxMobThresGrpAdminState      TmnxEnabledDisabled,
        tmnxMobThresGrpInterval        Unsigned32
    }

tmnxMobThresGrpId  OBJECT-TYPE
    SYNTAX      TmnxThresholdGroupType
    MAX-ACCESS  not-accessible
    STATUS      current
    DESCRIPTION
        "The value of tmnxMobThresGrpId specifies the identifier of threshold  
         based monitoring group in a mobile gateway."
    ::= { tmnxMobThresGroupEntry 1 }

tmnxMobThresSubGrpId  OBJECT-TYPE
    SYNTAX      Unsigned32 (1..8)
    MAX-ACCESS  not-accessible
    STATUS      current
    DESCRIPTION
        "The value of tmnxMobThresGrpId specifies the identifier of sub-group
         within the threshold based monitoring group in a mobile gateway."
    ::= { tmnxMobThresGroupEntry 2 }

tmnxMobThresGrpRowStatus  OBJECT-TYPE
    SYNTAX      RowStatus
    MAX-ACCESS  read-create
    STATUS      current
    DESCRIPTION
        "The value of tmnxMobThresGrpRowStatus specifies the row status
         of this entry."
    ::= { tmnxMobThresGroupEntry 3 }

tmnxMobThresGrpLastChanged  OBJECT-TYPE
    SYNTAX      TimeStamp
    MAX-ACCESS  read-only
    STATUS      current
    DESCRIPTION
        "The value of tmnxMobThresGrpLastChanged indicates the timestamp of
         the last change to this row in tmnxMobThresGroupTable."
    ::= { tmnxMobThresGroupEntry 4 }

tmnxMobThresGrpAdminState  OBJECT-TYPE
    SYNTAX      TmnxEnabledDisabled
    MAX-ACCESS  read-create
    STATUS      current
    DESCRIPTION
        "The value of tmnxMobThresGrpAdminState specified whether the mobile  
         gateway's admintrative state is enabled or disabled."
    DEFVAL { disabled }
    ::= { tmnxMobThresGroupEntry 5 }

tmnxMobThresGrpInterval  OBJECT-TYPE
    SYNTAX      Unsigned32    
    UNITS       "minutes"
    MAX-ACCESS  read-create
    STATUS      current
    DESCRIPTION
        "The value of tmnxMobThresGrpInterval specifies the polling interval
         of the threshold based monitoring for the group."
    DEFVAL { 5 }
    ::= { tmnxMobThresGroupEntry 6 }



--
--  Threshold based monitoring threshold configuration table
--

tmnxMobThresConfigLastChanged  OBJECT-TYPE
    SYNTAX      TimeStamp
    MAX-ACCESS  read-only
    STATUS      current
    DESCRIPTION
        "The value of tmnxMobThresConfigLastChanged indicates the sysUpTime
         at the time of the last modification to tmnxMobThresGroupTable by
         adding, deleting an entry or change to a writable object in the table.

         If no changes were made to the table since the last re-initialization
         of the local network management subsystem, then this object contains
         a zero value."
    ::= { tmnxMobGatewayGlobalObjs 12 }

tmnxMobThresConfigTable OBJECT-TYPE
    SYNTAX      SEQUENCE OF TmnxMobThresConfigEntry
    MAX-ACCESS  not-accessible
    STATUS      current
    DESCRIPTION
        "The tmnxMobThresConfigTable has an entry for the attributess of a  
         counter used for threshold based monitoring counter in the mobile 
         gateway."
    ::= { tmnxMobGatewayObjs 13 }

tmnxMobThresConfigEntry  OBJECT-TYPE
    SYNTAX      TmnxMobThresConfigEntry
    MAX-ACCESS  not-accessible
    STATUS      current
    DESCRIPTION
        "Each row entry represents the attributes of a counter which is used  
         for threshold based monitoring in a mobile gateway."
    INDEX { tmnxMobGwId,
            tmnxMobThresCfgGroupId,
            tmnxMobThresCfgSubGroupId,
            tmnxMobThresCfgCounterId
          }
    ::= { tmnxMobThresConfigTable 1 }

TmnxMobThresConfigEntry ::= SEQUENCE {
        tmnxMobThresCfgGroupId         TmnxThresholdGroupType,
        tmnxMobThresCfgSubGroupId      Unsigned32,
        tmnxMobThresCfgCounterId       INTEGER,
        tmnxMobThresCfgRowStatus       RowStatus,
        tmnxMobThresCfgLastChanged     TimeStamp,
        tmnxMobThresCfgAlarmIndex      Unsigned32,
        tmnxMobThresCfgHighThreshold   Integer32,
        tmnxMobThresCfgLowThreshold    Integer32,
        tmnxMobThresCfgCtrOID           OBJECT IDENTIFIER
    }

tmnxMobThresCfgGroupId  OBJECT-TYPE
    SYNTAX      TmnxThresholdGroupType
    MAX-ACCESS  read-only
    STATUS      current
    DESCRIPTION
        "The value of tmnxMobThresCfgGroupId indicates the identifier of   
         threshold based monitoring group in a mobile gateway."
    ::= { tmnxMobThresConfigEntry 1 }

tmnxMobThresCfgSubGroupId  OBJECT-TYPE
    SYNTAX      Unsigned32 (1..8)
    MAX-ACCESS  read-only
    STATUS      current
    DESCRIPTION
        "The value of tmnxMobThresCfgGroupId indicates the identifier of 
         sub-group within the threshold based monitoring group in a 
         mobile gateway."
    ::= { tmnxMobThresConfigEntry 2 }

tmnxMobThresCfgCounterId OBJECT-TYPE
    SYNTAX      INTEGER {
                    brMgmtLimitUEs (1),
                    brMgmtLimitBrs (2),
                    brMgmtLimitDefBrs (3),
                    brMgmtLimitDedBrs (4),
                    brMgmtLimitActBrs (5),
                    brMgmtLimitUePaged (6),
                    brMgmtCfsAttach (7),
                    brMgmtCfsDedBr (8),
                    brMgmtCfsSvrReq (9),
                    brMgmtCfsIntraReloc (10),
                    brMgmtCfsInterReloc (11),
                    brMgmtCfsIdleReloc (12),
                    brMgmtCffAttach (13),
                    brMgmtCffDedBr (14),
                    brMgmtCffPaging (15),
                    brMgmtCffHandOver (16),
                    brMgmtCffSvrReq (17),
                    brMgmtCffSvrUnavl (18),
                    brTrafficThrouputUL (19),
                    brTrafficThrouputDL (20),
                    brTrafficAspFail (21),
                    brTrafficBrBdvErr (22),
                    pathMgmtS5Fail (23),
                    pathMgmtS5Restart (24),
                    pathMgmtS5NoResp (25),
                    pathMgmtS11PrPath (26),
                    pathMgmtS11PrRstt (27),
                    pathMgmtS11NoResp (28),
                    pathMgmtRfPeerFail (29),
                    pathMgmtS1UENB (30),
                    pathMgmtS11MME (31),
                    pathMgmtS5Peer (32),
                    pathMgmtS8Peer (33),
                    pathMgmtGxFail (34),
                    pathMgmtRfFail (35),
                    mgIsmCpu (36),
                    mgIsmMem (37),
                    mgIsmUplink (38),
                    mgIsmDownlink (39)
                }
    MAX-ACCESS not-accessible
    STATUS     current
    DESCRIPTION
        "The value of tmnxMobThresCfgCounterId indicates the type of predefined
         counter type."
    ::= { tmnxMobThresConfigEntry 3 }

tmnxMobThresCfgRowStatus  OBJECT-TYPE
    SYNTAX      RowStatus
    MAX-ACCESS  read-create
    STATUS      current
    DESCRIPTION
        "The value of tmnxMobThresCfgRowStatus specifies the row status
         of this entry."
    ::= { tmnxMobThresConfigEntry 4 }

tmnxMobThresCfgLastChanged  OBJECT-TYPE
    SYNTAX      TimeStamp
    MAX-ACCESS  read-only
    STATUS      current
    DESCRIPTION
        "The value of tmnxMobThresCfgLastChanged indicates the timestamp of
         the last change to this row in tmnxMobThresGroupTable."
    ::= { tmnxMobThresConfigEntry 5 }

tmnxMobThresCfgAlarmIndex  OBJECT-TYPE
    SYNTAX      Unsigned32
    MAX-ACCESS  read-only
    STATUS      current
    DESCRIPTION
        "The value of tmnxMobThresCfgAlarmIndex indicates the alarm index for   
         this counter in RMON alarm table."
    ::= { tmnxMobThresConfigEntry 6 }

tmnxMobThresCfgHighThreshold  OBJECT-TYPE
    SYNTAX      Integer32
    MAX-ACCESS  read-create
    STATUS      current
    DESCRIPTION
        "The value of tmnxMobThresCfgHighThreshold specifies the high threshold    
         for the counter to be monitored."
    ::= { tmnxMobThresConfigEntry 7 }

tmnxMobThresCfgLowThreshold  OBJECT-TYPE
    SYNTAX      Integer32
    MAX-ACCESS  read-create
    STATUS      current
    DESCRIPTION
        "The value of tmnxMobThresCfgLowThreshold specifies the low threshold    
         for the counter to be monitored."
    ::= { tmnxMobThresConfigEntry 8 }

tmnxMobThresCfgCtrOID  OBJECT-TYPE
    SYNTAX      OBJECT IDENTIFIER
    MAX-ACCESS  read-only
    STATUS      current
    DESCRIPTION
        "The value of tmnxMobThresCfgCtrOID indicates the object identifier of 
         the counter to be monitored in a mobile gateway."

    ::= { tmnxMobThresConfigEntry 9 }


tmnxMobMgIsmThresTable  OBJECT-TYPE
    SYNTAX      SEQUENCE OF TmnxMobMgIsmThresEntry
    MAX-ACCESS  not-accessible
    STATUS      current
    DESCRIPTION
        "The tmnxMobMgIsmThresTable has an entry for the set of thresholds  
         for each system MG-ISM group in the mobile gateway."
    ::= { tmnxMobGatewayObjs 14 }

tmnxMobMgIsmThresEntry  OBJECT-TYPE
    SYNTAX      TmnxMobMgIsmThresEntry
    MAX-ACCESS  not-accessible
    STATUS      current
    DESCRIPTION
        "Each row entry represents a set of thresholds."
    INDEX { tmnxMobGwId,
            tmnxMobMgIsmThresGroupId }
    ::= { tmnxMobMgIsmThresTable 1 }

TmnxMobMgIsmThresEntry ::= SEQUENCE {
        tmnxMobMgIsmThresGroupId          Unsigned32,
        tmnxMobMgIsmThresLastChanged      TimeStamp,
        tmnxMobMgIsmThresCpu              Gauge32,
        tmnxMobMgIsmThresMem              Gauge32,
        tmnxMobMgIsmThresThrptUL          Gauge32,
        tmnxMobMgIsmThresThrptDL          Gauge32
    }

tmnxMobMgIsmThresGroupId  OBJECT-TYPE
    SYNTAX      Unsigned32 (1..8)
    MAX-ACCESS  not-accessible
    STATUS      current
    DESCRIPTION
        "The value of tmnxMobMgIsmThresGroupId uniquely identifies the Mobile 
         Gateway Integrated System Module (MG-ISM)."
    ::= { tmnxMobMgIsmThresEntry 1 }

tmnxMobMgIsmThresLastChanged  OBJECT-TYPE
    SYNTAX      TimeStamp
    MAX-ACCESS  read-only
    STATUS      current
    DESCRIPTION
        "The value of tmnxMobMgIsmThresLastChanged indicates the timestamp of
         the last change to this row in tmnxMobMgIsmThresTable."
    ::= { tmnxMobMgIsmThresEntry 2 }

tmnxMobMgIsmThresCpu  OBJECT-TYPE
    SYNTAX      Gauge32 (0..100)
    UNITS       "Percent"
    MAX-ACCESS  read-only
    STATUS      current
    DESCRIPTION
        "The value of tmnxMobMgIsmThresCpu indicates the CPU utilization 
         in this MG-ISM group."
    ::= { tmnxMobMgIsmThresEntry 3 }

tmnxMobMgIsmThresMem  OBJECT-TYPE
    SYNTAX      Gauge32 (0..100)
    UNITS       "Percent"
    MAX-ACCESS  read-only
    STATUS      current
    DESCRIPTION
        "The value of tmnxMobMgIsmThresMem indicates the memory utilization 
         in this MG-ISM group."
    ::= { tmnxMobMgIsmThresEntry 4 }

tmnxMobMgIsmThresThrptUL  OBJECT-TYPE
    SYNTAX      Gauge32
    UNITS       "megabytes"
    MAX-ACCESS  read-only
    STATUS      current
    DESCRIPTION
        "The value of tmnxMobMgIsmThresThrptUL indicates the uplink 
         traffic throughput in mega-bytes per polling period."
    ::= { tmnxMobMgIsmThresEntry 5 }  

tmnxMobMgIsmThresThrptDL  OBJECT-TYPE
    SYNTAX      Gauge32
    UNITS       "megabytes"
    MAX-ACCESS  read-only
    STATUS      current
    DESCRIPTION
        "The value of tmnxMobMgIsmThresThrptDL indicates the downlink 
         traffic throughput in mega-bytes per polling period."
    ::= { tmnxMobMgIsmThresEntry 6 }  

--
--  S5 Cause Codes Stats Table
--

tmnxMobGwS5CauseCodeTable  OBJECT-TYPE
    SYNTAX      SEQUENCE OF TmnxMobGwS5CauseCodeEntry
    MAX-ACCESS  not-accessible
    STATUS      current
    DESCRIPTION
        "The tmnxMobGwS5CauseCodeTable has an entry for each peer on the S5
         reference point."
    ::= { tmnxMobGatewayObjs 15 }

tmnxMobGwS5CauseCodeEntry  OBJECT-TYPE
    SYNTAX      TmnxMobGwS5CauseCodeEntry
    MAX-ACCESS  not-accessible
    STATUS      current
    DESCRIPTION
        "Each row entry represents a peer on the S5 reference point
         and contains cause code statistics for this peer on a card."
    AUGMENTS { tmnxMobGwS5StatEntry }
    ::= { tmnxMobGwS5CauseCodeTable 1 }

TmnxMobGwS5CauseCodeEntry ::= SEQUENCE {
        tmnxMobGwS5CcRxReqAccepted        Counter32,
        tmnxMobGwS5CcRxCtxNotFound        Counter32,
        tmnxMobGwS5CcRxInvalidLength      Counter32,
        tmnxMobGwS5CcRxMndIeIncorrect     Counter32,
        tmnxMobGwS5CcRxMandIeMissing      Counter32,
        tmnxMobGwS5CcRxReqRejected        Counter32,
        tmnxMobGwS5CcRxRemPeerNoResp      Counter32,
        tmnxMobGwS5CcRxNoResAvailable     Counter32,
        tmnxMobGwS5CcRxUsrAuthFailure     Counter32,
        tmnxMobGwS5CcRxOthers             Counter32,
        tmnxMobGwS5CcTxReqAccepted        Counter32,
        tmnxMobGwS5CcTxCtxNotFound        Counter32,
        tmnxMobGwS5CcTxInvalidLength      Counter32,
        tmnxMobGwS5CcTxMndIeIncorrect     Counter32,
        tmnxMobGwS5CcTxMandIeMissing      Counter32,
        tmnxMobGwS5CcTxReqRejected        Counter32,
        tmnxMobGwS5CcTxRemPeerNoResp      Counter32,
        tmnxMobGwS5CcTxNoResAvailable     Counter32,
        tmnxMobGwS5CcTxUsrAuthFailure     Counter32,
        tmnxMobGwS5CcTxOthers             Counter32
    }

tmnxMobGwS5CcRxReqAccepted  OBJECT-TYPE
    SYNTAX      Counter32
    MAX-ACCESS  read-only
    STATUS      current
    DESCRIPTION
        "The value of tmnxMobGwS5CcRxReqAccepted indicates the number of
         messages received on this peer with cause code set to request
         accepted."
    ::= { tmnxMobGwS5CauseCodeEntry 1 }

tmnxMobGwS5CcRxCtxNotFound  OBJECT-TYPE
    SYNTAX      Counter32
    MAX-ACCESS  read-only
    STATUS      current
    DESCRIPTION
        "The value of tmnxMobGwS5CcRxCtxNotFound indicates the number of
         messages received on this peer with cause code set to context not
         found."
    ::= { tmnxMobGwS5CauseCodeEntry 2 }

tmnxMobGwS5CcRxInvalidLength  OBJECT-TYPE
    SYNTAX      Counter32
    MAX-ACCESS  read-only
    STATUS      current
    DESCRIPTION
        "The value of tmnxMobGwS5CcRxInvalidLength indicates the number of
         messages received on this peer with cause code set to invalid length."
    ::= { tmnxMobGwS5CauseCodeEntry 3 }

tmnxMobGwS5CcRxMndIeIncorrect  OBJECT-TYPE
    SYNTAX      Counter32
    MAX-ACCESS  read-only
    STATUS      current
    DESCRIPTION
        "The value of tmnxMobGwS5CcRxMndIeIncorrect indicates the number of
         messages received on this peer with cause code set to mandatory 
         Information Elements (IE) incorrect."
    ::= { tmnxMobGwS5CauseCodeEntry 4 }

tmnxMobGwS5CcRxMandIeMissing  OBJECT-TYPE
    SYNTAX      Counter32
    MAX-ACCESS  read-only
    STATUS      current
    DESCRIPTION
        "The value of tmnxMobGwS5CcRxMandIeMissing indicates the number of
         messages received on this peer with cause code set to mandatory
         Information Elements (IE) missing."
    ::= { tmnxMobGwS5CauseCodeEntry 5 }

tmnxMobGwS5CcRxReqRejected  OBJECT-TYPE
    SYNTAX      Counter32
    MAX-ACCESS  read-only
    STATUS      current
    DESCRIPTION
        "The value of tmnxMobGwS5CcRxReqRejected indicates the number of
         messages received on this peer with cause code set to request
         rejected."
    ::= { tmnxMobGwS5CauseCodeEntry 6 }

tmnxMobGwS5CcRxRemPeerNoResp  OBJECT-TYPE
    SYNTAX      Counter32
    MAX-ACCESS  read-only
    STATUS      current
    DESCRIPTION
        "The value of tmnxMobGwS5CcRxRemPeerNoResp indicates the number of
         messages received on this peer with cause code set to remote peer
         not responding."
    ::= { tmnxMobGwS5CauseCodeEntry 7 }

tmnxMobGwS5CcRxNoResAvailable  OBJECT-TYPE
    SYNTAX      Counter32
    MAX-ACCESS  read-only
    STATUS      current
    DESCRIPTION
        "The value of tmnxMobGwS5CcRxNoResAvailable indicates the number of
         messages received on this peer with cause code set to no resources
         available."
    ::= { tmnxMobGwS5CauseCodeEntry 8 }

tmnxMobGwS5CcRxUsrAuthFailure  OBJECT-TYPE
    SYNTAX      Counter32
    MAX-ACCESS  read-only
    STATUS      current
    DESCRIPTION
        "The value of tmnxMobGwS5CcRxUsrAuthFailure indicates the number of
         messages received on this peer with cause code set to user
         authentication failed."
    ::= { tmnxMobGwS5CauseCodeEntry 9 }

tmnxMobGwS5CcRxOthers  OBJECT-TYPE
    SYNTAX      Counter32
    MAX-ACCESS  read-only
    STATUS      current
    DESCRIPTION
        "The value of tmnxMobGwS5CcRxOthers indicates the number of
         messages received on this peer with cause code set to other values."
    ::= { tmnxMobGwS5CauseCodeEntry 10 }

tmnxMobGwS5CcTxReqAccepted  OBJECT-TYPE
    SYNTAX      Counter32
    MAX-ACCESS  read-only
    STATUS      current
    DESCRIPTION
        "The value of tmnxMobGwS5CcTxReqAccepted indicates the number of
         messages transmitted from this peer with cause code set to request
         accepted."
    ::= { tmnxMobGwS5CauseCodeEntry 11 }

tmnxMobGwS5CcTxCtxNotFound  OBJECT-TYPE
    SYNTAX      Counter32
    MAX-ACCESS  read-only
    STATUS      current
    DESCRIPTION
        "The value of tmnxMobGwS5CcTxCtxNotFound indicates the number of
         messages transmitted from this peer with cause code set to context not
         found."
    ::= { tmnxMobGwS5CauseCodeEntry 12 }

tmnxMobGwS5CcTxInvalidLength  OBJECT-TYPE
    SYNTAX      Counter32
    MAX-ACCESS  read-only
    STATUS      current
    DESCRIPTION
        "The value of tmnxMobGwS5CcTxInvalidLength indicates the number of
         messages transmitted from this peer with cause code set to invalid
         length."
    ::= { tmnxMobGwS5CauseCodeEntry 13 }

tmnxMobGwS5CcTxMndIeIncorrect  OBJECT-TYPE
    SYNTAX      Counter32
    MAX-ACCESS  read-only
    STATUS      current
    DESCRIPTION
        "The value of tmnxMobGwS5CcTxMndIeIncorrect indicates the number of
         messages transmitted from this peer with cause code set to mandatory
         Information Elements (IE) incorrect."
    ::= { tmnxMobGwS5CauseCodeEntry 14 }

tmnxMobGwS5CcTxMandIeMissing  OBJECT-TYPE
    SYNTAX      Counter32
    MAX-ACCESS  read-only
    STATUS      current
    DESCRIPTION
        "The value of tmnxMobGwS5CcTxMandIeMissing indicates the number of
         messages transmitted from this peer with cause code set to mandatory
         Information Elements (IE) missing."
    ::= { tmnxMobGwS5CauseCodeEntry 15 }

tmnxMobGwS5CcTxReqRejected  OBJECT-TYPE
    SYNTAX      Counter32
    MAX-ACCESS  read-only
    STATUS      current
    DESCRIPTION
        "The value of tmnxMobGwS5CcTxReqRejected indicates the number of
         messages transmitted from this peer with cause code set to request
         rejected."
    ::= { tmnxMobGwS5CauseCodeEntry 16 }

tmnxMobGwS5CcTxRemPeerNoResp  OBJECT-TYPE
    SYNTAX      Counter32
    MAX-ACCESS  read-only
    STATUS      current
    DESCRIPTION
        "The value of tmnxMobGwS5CcTxRemPeerNoResp indicates the number of
         messages transmitted from this peer with cause code set to remote peer
         not responding."
    ::= { tmnxMobGwS5CauseCodeEntry 17 }

tmnxMobGwS5CcTxNoResAvailable  OBJECT-TYPE
    SYNTAX      Counter32
    MAX-ACCESS  read-only
    STATUS      current
    DESCRIPTION
        "The value of tmnxMobGwS5CcTxNoResAvailable indicates the number of
         messages transmitted from this peer with cause code set to no resources
         available."
    ::= { tmnxMobGwS5CauseCodeEntry 18 }

tmnxMobGwS5CcTxUsrAuthFailure  OBJECT-TYPE
    SYNTAX      Counter32
    MAX-ACCESS  read-only
    STATUS      current
    DESCRIPTION
        "The value of tmnxMobGwS5CcTxUsrAuthFailure indicates the number of
         messages transmitted from this peer with cause code set to user
         authentication failed."
    ::= { tmnxMobGwS5CauseCodeEntry 19 }

tmnxMobGwS5CcTxOthers  OBJECT-TYPE
    SYNTAX      Counter32
    MAX-ACCESS  read-only
    STATUS      current
    DESCRIPTION
        "The value of tmnxMobGwS5CcTxOthers indicates the number of
         messages transmitted from this peer with cause code set to other
         values."
    ::= { tmnxMobGwS5CauseCodeEntry 20 }

-- ----------------------------------------------
--     Notification Objects
-- ----------------------------------------------

tmnxMobGwNtfyGatewayId          OBJECT-TYPE
    SYNTAX       TmnxMobGwId
    MAX-ACCESS   accessible-for-notify
    STATUS       current
    DESCRIPTION
        "The value of tmnxMobGwNtfyGatewayId indicates the mobile gateway
         identifier."
    ::= { tmnxMobGatewayNotificationObjs 1 }

tmnxMobGwNtfyVrtrId             OBJECT-TYPE
    SYNTAX       TmnxVRtrID
    MAX-ACCESS   accessible-for-notify
    STATUS       current
    DESCRIPTION
        "The value of tmnxMobGwNtfyVrtrId indicates the virtual router
         instance."
    ::= { tmnxMobGatewayNotificationObjs 2 }

tmnxMobGwNtfyRefPointType       OBJECT-TYPE
    SYNTAX       INTEGER {
                           s1u  (1),
                           s5   (2),
                           s8   (3),
                           s11  (4),
                           gn   (5),
                           s2a  (6)
                         }
    MAX-ACCESS   accessible-for-notify
    STATUS       current
    DESCRIPTION
        "The value of tmnxMobGwNtfyRefPointType indicates the type of
         reference point."
    ::= { tmnxMobGatewayNotificationObjs 3 }

tmnxMobGwNtfyRefPointProtocol   OBJECT-TYPE
    SYNTAX       INTEGER {
                           gtp       (1),
                           pmip      (2)
                         }
    MAX-ACCESS   accessible-for-notify
    STATUS       current
    DESCRIPTION
        "The value of tmnxMobGwNtfyRefPointProtocol indicates the protocol
         used in a reference point connection."
    ::= { tmnxMobGatewayNotificationObjs 4 }

tmnxMobGwNtfyRfPtPeerAddrType   OBJECT-TYPE
    SYNTAX       InetAddressType
    MAX-ACCESS   accessible-for-notify
    STATUS       current
    DESCRIPTION
        "The value of tmnxMobGwNtfyRfPtPeerAddrType indicates the type of
         peer address represented by tmnxMobGwNtfyRfPtPeerAddr."
    ::= { tmnxMobGatewayNotificationObjs 5 }

tmnxMobGwNtfyRfPtPeerAddr       OBJECT-TYPE
    SYNTAX       InetAddress
    MAX-ACCESS   accessible-for-notify
    STATUS       current
    DESCRIPTION
        "The value of tmnxMobGwNtfyRfPtPeerAddr indicates the peer address of
         a reference point."
    ::= { tmnxMobGatewayNotificationObjs 6 }

tmnxMobGwNtfyRfPtPeerPort       OBJECT-TYPE
    SYNTAX       InetPortNumber
    MAX-ACCESS   accessible-for-notify
    STATUS       current
    DESCRIPTION
        "The value of tmnxMobGwNtfyRfPtPeerPort indicates the peer port
         number of a reference point."
    ::= { tmnxMobGatewayNotificationObjs 7 }

tmnxMobGwNtfyPathMgmtPeerState   OBJECT-TYPE
    SYNTAX       INTEGER {
                           added       (1),
                           deleted     (2),
                           pathUp      (3),
                           pathDown    (4),
                           pathRestart (5),
                           pathIdle    (6) 
                         }
    MAX-ACCESS   accessible-for-notify
    STATUS       current
    DESCRIPTION
        "The value of tmnxMobGwNtfyPathMgmtPeerState indicates the state of a
         reference point peer in path management. 

         Following is the mapping between tmnxMobGwNtfyPathMgmtPeerState and 
         TmnxMobPathMgmtState. 
         
         up         (1)  -    pathUp      (3)
         fault      (3)  -    pathDown    (4)
         idle       (4)  -    pathIdle    (6)
         restart    (5)  -    pathRestart (5)         
         everything else -    no mapping"
    ::= { tmnxMobGatewayNotificationObjs 8 }

tmnxMobGwNtfyDiaRefPointType       OBJECT-TYPE
    SYNTAX       INTEGER {
                           gx   (1),
                           rf   (2),
                           gy   (3),
                           s6b  (4)
                         }
    MAX-ACCESS   accessible-for-notify
    STATUS       current
    DESCRIPTION
        "The value of tmnxMobGwNtfyDiaRefPointType indicates the type of
         reference point for the diameter application."
    ::= { tmnxMobGatewayNotificationObjs 9 }

tmnxMobGwNtfyDiaPeerName  OBJECT-TYPE
    SYNTAX      TmnxMobProfName
    MAX-ACCESS  accessible-for-notify
    STATUS      current
    DESCRIPTION
        "The value of tmnxMobGwNtfyDiaPeerName specifies the unique value
         which identifies the diameter peer name."
    ::= { tmnxMobGatewayNotificationObjs 10 }

tmnxMobGwNtfyDiaPeerIndex  OBJECT-TYPE
    SYNTAX      Unsigned32
    MAX-ACCESS  accessible-for-notify
    STATUS      current
    DESCRIPTION
        "The value of tmnxMobGwNtfyDiaPeerIndex specifies the unique value
         which identifies this IP address entry."
    ::= { tmnxMobGatewayNotificationObjs 11 }

tmnxMobGwNtfyDiaPeerAddrType   OBJECT-TYPE
    SYNTAX       InetAddressType
    MAX-ACCESS   accessible-for-notify
    STATUS       current
    DESCRIPTION
        "The value of tmnxMobGwNtfyDiaPeerAddrType indicates the type of
         peer address represented by tmnxMobGwNtfyDiaPeerAddr."
    ::= { tmnxMobGatewayNotificationObjs 12 }

tmnxMobGwNtfyDiaPeerAddr          OBJECT-TYPE
    SYNTAX       InetAddress
    MAX-ACCESS   accessible-for-notify
    STATUS       current
    DESCRIPTION
        "The value of tmnxMobGwNtfyDiaPeerAddr indicates the Fully Qualified 
         Domain Name (FQDN) for the peer."
    ::= { tmnxMobGatewayNotificationObjs 13 }

tmnxMobGwNtfyDiaPeerPort       OBJECT-TYPE
    SYNTAX       InetPortNumber
    MAX-ACCESS   accessible-for-notify
    STATUS       current
    DESCRIPTION
        "The value of tmnxMobGwNtfyDiaPeerPort indicates the peer port
         number of a diameter reference point."
    ::= { tmnxMobGatewayNotificationObjs 14 }

tmnxMobGwNtfyDiameterPeerState   OBJECT-TYPE
    SYNTAX       INTEGER {
                           pathUp           (1),                           
                           pathDown         (2),
                           nwFailureDown    (3),
                           added            (4),
                           deleted          (5),
                           pathPartialUp    (6)
                         }
    MAX-ACCESS   accessible-for-notify
    STATUS       current
    DESCRIPTION
        "The value of tmnxMobGwNtfyDiameterPeerState indicates the state of a
         reference point peer in the diameter application.
         
         The value of 'pathUp' indicates that the connection with peer has been
         established.

         The value of 'pathDown' indicates that the connection with peer has
         been brought down by the gateway.

         The value of 'nwFailureDown' indicates that the connection with peer
         has been brought down due to network issues at remote side.

         The value of 'added' indicates that the peer has been added.

         The value of 'deleted' indicates that the peer has been deleted.

         The value of 'pathPartialUp' indicates that the connection with peer is
         partially established.

         Following is the mapping between tmnxMobGwNtfyDiameterPeerState and 
         TmnxMobDiaPathMgmtState. 

         active         (3)  -    pathUp(1)
         inactive       (2)  -    pathDown(2)
         shuttingDown   (1)  -    pathDown(2)
         shutdown       (0)  -    pathDown(2)"
    ::= { tmnxMobGatewayNotificationObjs 15 }

tmnxMobGwNtfyDiameterReasonCode   OBJECT-TYPE
    SYNTAX       INTEGER {
                           none                (1),  
                           unknown             (2),
                           adminDown           (3),                           
                           dwrTimeout          (4),
                           permFailureRecvd    (5),
                           dnsFailure          (6),  
                           dprRecvd            (7),
                           remoteDisconnect    (8),  
                           localDisconnect     (9),
                           peerAdded           (10),
                           peerDeleted         (11),
                           peerActive          (12)
                         }
    MAX-ACCESS   accessible-for-notify
    STATUS       current
    DESCRIPTION
        "The value of tmnxMobGwNtfyDiameterReasonCode indicates the reason  
         why the peer connection has been brought down.

         The value of 'none' indicates that the connection is active.

         The value of 'unknown' indicates that the reason is not known.

         The value of 'adminDown' indicates that the peer is not referenced by
         the mobile gateway in service.

         The value of 'dwrTimeout' indicates that Device Watchdog Request (DWR) 
         timed out.

         The value of 'permFailureRecvd' indicates that a permanent failure 
         is received.

         The value of 'dnsFailure' indicates that a Domain Name Server (DNS) 
         failure occurred.

         The value of 'dprRecvd' indicates that a Disconnect Peer Request (DPR) 
         has been received.

         The value of 'remoteDisconnect' indicates that the remote side has
         closed the connection.

         The value of 'localDisconnect' indicates that the local side has closed
         the connection.
         
         The value of 'peerAdded' indicates that a peer has been added.

         The value of 'peerDeleted' indicates that a peer has been deleted.

         The value of 'peerActive' indicates that a peer is active."
    ::= { tmnxMobGatewayNotificationObjs 16 }

tmnxMobGwNtfyChrgRefPointType       OBJECT-TYPE
    SYNTAX       INTEGER {
                           rf   (1),
                           ga   (2)
                         }
    MAX-ACCESS   accessible-for-notify
    STATUS       current
    DESCRIPTION
        "The value of tmnxMobGwNtfyDiaRefPointType indicates the type of
         reference point for the charging application."
    ::= { tmnxMobGatewayNotificationObjs 17 }

tmnxMobGwNtfyPriCdfDiaPeer  OBJECT-TYPE
    SYNTAX      TmnxMobProfName
    MAX-ACCESS  accessible-for-notify
    STATUS      current
    DESCRIPTION
        "The value of tmnxMobGwNtfyPriCdfDiaPeer specifies the primary Charging 
         Data Function (CDF) diameter peer profile."
    ::= { tmnxMobGatewayNotificationObjs 18 }

tmnxMobGwNtfySecCdfDiaPeer  OBJECT-TYPE
    SYNTAX      TmnxMobProfName
    MAX-ACCESS  accessible-for-notify
    STATUS      current
    DESCRIPTION
        "The value of tmnxMobGwNtfySecCdfDiaPeer specifies the secondary 
         Charging Data Function (CDF) diameter peer profile."
    ::= { tmnxMobGatewayNotificationObjs 19 }

tmnxMobGwNtfyCdfDiaPeer  OBJECT-TYPE
    SYNTAX      TmnxMobProfName
    MAX-ACCESS  accessible-for-notify
    STATUS      current
    DESCRIPTION
        "The value of tmnxMobGwNtfyCdfDiaPeer specifies the Charging Data 
         Function (CDF) diameter peer profile."
    ::= { tmnxMobGatewayNotificationObjs 20 }

tmnxMobGwNtfyFlashId       OBJECT-TYPE
    SYNTAX       INTEGER {
                           cf1   (1),
                           cf2   (2)
                         }
    MAX-ACCESS   accessible-for-notify
    STATUS       current
    DESCRIPTION
        "The value of tmnxMobGwNtfyFlashId indicates the compact flash on the 
         system."
    ::= { tmnxMobGatewayNotificationObjs 21 }

tmnxMobGwNtfyCfLimit  OBJECT-TYPE
    SYNTAX       Unsigned32
    UNITS        "megabytes"
    MAX-ACCESS   accessible-for-notify
    STATUS       current
    DESCRIPTION
        "The value of tmnxMobGwNtfyCfLimit specifies the limit (in megabytes) 
         for an amount of memory on the compact flash that can be used for the 
         Accounting Requests (ACR) storage."
    ::= { tmnxMobGatewayNotificationObjs 22 } 

tmnxMobGwNtfyAcrFailureType       OBJECT-TYPE
    SYNTAX       INTEGER {
                           fail2In10Sec   (1),
                           fail5In60Sec   (2)
                         }
    MAX-ACCESS   accessible-for-notify
    STATUS       current
    DESCRIPTION
        "The value of tmnxMobGwNtfyFlashId indicates  the Accounting Requests
         (ACR) transmission failure type for the peer.

         The value of 'fail2In10Sec' indicates that 2 ACR transmission failures
         occured in a 10 seconds interval. 

         The value of 'fail5In60Sec' indicates that 5 ACR transmission failures
         occured in a 60 seconds interval."
    ::= { tmnxMobGatewayNotificationObjs 23 }

tmnxMobGwNtfyGtpPriGrpName        OBJECT-TYPE
    SYNTAX      TmnxMobProfName 
    MAX-ACCESS  accessible-for-notify
    STATUS      current
    DESCRIPTION
        "The value of tmnxMobGwNtfyGtpPriGrpName indicates the unique name of
         this GPRS Tunneling Protocol (GTP) Prime Server Group."
    ::= { tmnxMobGatewayNotificationObjs 24 }

tmnxMobGwNtfyGtpPriServIndex     OBJECT-TYPE
    SYNTAX      Unsigned32
    MAX-ACCESS  accessible-for-notify
    STATUS      current
    DESCRIPTION
        "The value of tmnxMobGwNtfyGtpPriServIndex indicates the unique value
         which identifies this IP address entry for the GPRS Tunneling 
         Protocol (GTP) Prime Server."
    ::= { tmnxMobGatewayNotificationObjs 25 }

tmnxMobGwNtfyGtpPriServAddrType   OBJECT-TYPE
    SYNTAX      InetAddressType
    MAX-ACCESS  accessible-for-notify
    STATUS      current
    DESCRIPTION
        "The value of tmnxMobGwNtfyGtpPriServAddrType indicates the type of
         address represented by tmnxMobGwNtfyGtpPriServAddr."
    ::= { tmnxMobGatewayNotificationObjs 26 }

tmnxMobGwNtfyGtpPriServAddr      OBJECT-TYPE
    SYNTAX      InetAddress (SIZE (1..255))
    MAX-ACCESS  accessible-for-notify
    STATUS      current
    DESCRIPTION
        "The value of tmnxMobGwNtfyGtpPriServAddr indicates the IP address of
         the GPRS Tunneling Protocol (GTP) Prime Server. If the value of
         the corresponsding tmnxMobGwNtfyGtpPriServAddrType is 'dns', then the
         IP address for this Peer will be obtained via DNS A-Record query."
    ::= { tmnxMobGatewayNotificationObjs 27 }

tmnxMobGwNtfyGtpPriServPort      OBJECT-TYPE 
    SYNTAX      InetPortNumber
    MAX-ACCESS  accessible-for-notify
    STATUS      current
    DESCRIPTION
        "The value of tmnxMobGtpPriServerPort indicates the destination TCP 
         or UDP port number for GTP Prime Server."
    ::= { tmnxMobGatewayNotificationObjs 28 }

tmnxMobGwNtfyNewGtpPriServIndex     OBJECT-TYPE
    SYNTAX      Unsigned32
    MAX-ACCESS  accessible-for-notify
    STATUS      current
    DESCRIPTION
        "The value of tmnxMobGwNtfyNewGtpPriServIndex indicates the unique value
         which identifies this IP address entry for the GPRS Tunneling 
         Protocol (GTP) Prime Server."
    ::= { tmnxMobGatewayNotificationObjs 29 }

tmnxMobGwNtfyNewGtpPriSrvAdrType   OBJECT-TYPE
    SYNTAX      InetAddressType
    MAX-ACCESS  accessible-for-notify
    STATUS      current
    DESCRIPTION
        "The value of tmnxMobGwNtfyNewGtpPriSrvAdrType indicates the type of
         address represented by tmnxMobGwNtfyNewGtpPriServAddr."
    ::= { tmnxMobGatewayNotificationObjs 30 }

tmnxMobGwNtfyNewGtpPriServAddr      OBJECT-TYPE
    SYNTAX      InetAddress (SIZE (1..255))
    MAX-ACCESS  accessible-for-notify
    STATUS      current
    DESCRIPTION
        "The value of tmnxMobGwNtfyNewGtpPriServAddr indicates the IP address of
         the GPRS Tunneling Protocol (GTP) Prime Server. If the value of
         the corresponsding tmnxMobGwNtfyNewGtpPriSrvAdrType is 'dns', then the
         IP address for this Peer will be obtained via DNS A-Record query."
    ::= { tmnxMobGatewayNotificationObjs 31 }

tmnxMobGwNtfyNewGtpPriServPort      OBJECT-TYPE 
    SYNTAX      InetPortNumber
    MAX-ACCESS  accessible-for-notify
    STATUS      current
    DESCRIPTION
        "The value of tmnxMobGwNtfyNewGtpPriServPort indicates the destination
         TCP or UDP port number for GTP Prime Server."
    ::= { tmnxMobGatewayNotificationObjs 32 }

tmnxMobGwNtfyRadGrpName        OBJECT-TYPE
    SYNTAX      TmnxMobProfName 
    MAX-ACCESS  accessible-for-notify
    STATUS      current
    DESCRIPTION
        "The value of tmnxMobGwNtfyRadGrpName indicates the unique name of this
         Radius Group."
    ::= { tmnxMobGatewayNotificationObjs 33 }

tmnxMobGwNtfyRadPeerIndex     OBJECT-TYPE
    SYNTAX      Unsigned32
    MAX-ACCESS  accessible-for-notify
    STATUS      current
    DESCRIPTION
        "The value of tmnxMobGwNtfyRadPeerIndex indicates the unique value
         which identifies this IP address entry for the Radius Group Peer."
    ::= { tmnxMobGatewayNotificationObjs 34 }

tmnxMobGwNtfyRadPeerAddrType   OBJECT-TYPE
    SYNTAX      InetAddressType
    MAX-ACCESS  accessible-for-notify
    STATUS      current
    DESCRIPTION
        "The value of tmnxMobGwNtfyRadPeerAddrType indicates the type of
         address represented by tmnxMobGwNtfyRadPeerAddr."
    ::= { tmnxMobGatewayNotificationObjs 35 }

tmnxMobGwNtfyRadPeerAddr      OBJECT-TYPE
    SYNTAX      InetAddress (SIZE (1..255))
    MAX-ACCESS  accessible-for-notify
    STATUS      current
    DESCRIPTION
        "The value of tmnxMobGwNtfyRadPeerAddr indicates the IP address of
         the Radius Group Peer. If the value of
         the corresponsding tmnxMobGwNtfyRadPeerAddrType is 'dns', then the
         IP address for this peer will be obtained via DNS A-Record query."
    ::= { tmnxMobGatewayNotificationObjs 36 }

tmnxMobGwNtfyRadPeerAuthPort      OBJECT-TYPE 
    SYNTAX      InetPortNumber
    MAX-ACCESS  accessible-for-notify
    STATUS      current
    DESCRIPTION
        "The value of tmnxMobGwNtfyRadPeerAuthPort indicates the destination  
         authtication port number for the Radius Group Peer."
    ::= { tmnxMobGatewayNotificationObjs 37 }

tmnxMobGwNtfyGtpPriServerState   OBJECT-TYPE
    SYNTAX       INTEGER {
                           pathUp           (1),                           
                           pathDown         (2),
                           added            (3),
                           deleted          (4)
                         }
    MAX-ACCESS   accessible-for-notify
    STATUS       current
    DESCRIPTION
        "The value of tmnxMobGwNtfyGtpPriServerState indicates the state of 
         the GPRS Tunneling Protocol (GTP) Prime Server.
         
         The value of 'pathUp' indicates that the connection with server has
         been established.

         The value of 'pathDown' indicates that the connection with server has
         been brought down by the gateway.

         The value of 'added' indicates that the server has been added.

         The value of 'deleted' indicates that the server has been deleted."
    ::= { tmnxMobGatewayNotificationObjs 38 }

tmnxMobGwNtfyGtpPriSvrReasonCode   OBJECT-TYPE
    SYNTAX       INTEGER {
                           none                (1),  
                           unknown             (2),
                           shutdown            (3),                           
                           remoteDisc          (4),
                           localDisc           (5),
                           peerActive          (6),
                           peerIdle            (7)
                         }
    MAX-ACCESS   accessible-for-notify
    STATUS       current
    DESCRIPTION
        "The value of tmnxMobGwNtfyGtpPriSvrReasonCode indicates the reason  
         why the GPRS Tunneling Protocol (GTP) Prime Server connection has been
         brought down.

         The value of 'none' indicates that the connection is active.

         The value of 'unknown' indicates that the reason is not known.

         The value of 'shutdown' indicates that the peer is not referenced by
         the mobile gateway in service.

         The value of 'remoteDisconnect' indicates that the remote side has
         closed the connection.

         The value of 'localDisconnect' indicates that the local side has closed
         the connection after the dead-timer is expired.

         The value of 'peerActive' indicates that a peer is active.
  
         The value of 'peerActive' indicates that a peer is idle."
    ::= { tmnxMobGatewayNotificationObjs 39 }

tmnxMobGwNtfyGtpPriGrpState   OBJECT-TYPE
    SYNTAX       INTEGER {
                           up               (1),                           
                           down             (2)
                         }
    MAX-ACCESS   accessible-for-notify
    STATUS       current
    DESCRIPTION
        "The value of tmnxMobGwNtfyGtpPriGrpState indicates the state of the
         GPRS Tunneling Protocol (GTP) Prime Server Group.
         
         The value of 'up' indicates that the connection with GTP Prime Server
         Group has been established.

         The value of 'down' indicates that the connection with GTP Prime Server
         Group has been brought down by the gateway."
    ::= { tmnxMobGatewayNotificationObjs 40 }

tmnxMobGwNtfyGtpPriGrpReasonCode   OBJECT-TYPE
    SYNTAX       INTEGER {
                           remoteDisc          (1),
                           localDisc           (2)
                         }
    MAX-ACCESS   accessible-for-notify
    STATUS       current
    DESCRIPTION
        "The value of tmnxMobGwNtfyGtpPriGrpReasonCode indicates the reason  
         why the GPRS Tunneling Protocol (GTP) Prime Server Group has been
         brought down.

         The value of 'remoteDisconnect' indicates that the remote side has
         closed the connection.
         
         The value of 'localDisconnect' indicates that the local side has closed
         the connection after the dead-timer is expired."
    ::= { tmnxMobGatewayNotificationObjs 41 }

tmnxMobGwNtfySysGroupId  OBJECT-TYPE
    SYNTAX      Unsigned32 (1..8)
    MAX-ACCESS  accessible-for-notify
    STATUS      current
    DESCRIPTION
        "The value of tmnxMobGwNtfySysGroupId indiactes the mobile system
         group."
    ::= { tmnxMobGatewayNotificationObjs 42 }

tmnxMobGwNtfyWriteCdrAction   OBJECT-TYPE
    SYNTAX       INTEGER {
                           start           (1),                           
                           stop            (2)
                         }
    MAX-ACCESS   accessible-for-notify
    STATUS       current
    DESCRIPTION
        "The value of tmnxMobGwNtfyWriteCdrAction indicates action for writing 
         CDRs to compact flash.
         
         The value of 'start' indicates that the writing of Charging Data
         Requests(CDR) to compact flash has been started.

         The value of 'stop' indicates that the writing of CDRs to compact
         flash has been stoped."
    ::= { tmnxMobGatewayNotificationObjs 43 }

tmnxMobGwNtfyRadPeerAcctPort      OBJECT-TYPE 
    SYNTAX      InetPortNumber
    MAX-ACCESS  accessible-for-notify
    STATUS      current
    DESCRIPTION
        "The value of tmnxMobGwNtfyRadPeerAcctPort indicates the destination  
         accounting port number for the Radius Group Peer."
    ::= { tmnxMobGatewayNotificationObjs 44 }

tmnxMobGwNtfyRadPeerState      OBJECT-TYPE 
    SYNTAX       INTEGER {
                           up               (1),                           
                           down             (2)
                         }
    MAX-ACCESS  accessible-for-notify
    STATUS      current
    DESCRIPTION
        "The value of tmnxMobGwNtfyRadPeerState indicates operational state  
         of the Radius Group Peer."
    ::= { tmnxMobGatewayNotificationObjs 45 }

tmnxMobGwNtfyRadGrpState        OBJECT-TYPE
    SYNTAX       INTEGER {
                           up               (1),                           
                           down             (2)
                         }
    MAX-ACCESS  accessible-for-notify
    STATUS      current
    DESCRIPTION
        "The value of tmnxMobGwNtfyRadGrpState indicates the state of this 
         Radius Group."
    ::= { tmnxMobGatewayNotificationObjs 46 }

-- ----------------------------------------------
-- Notifications
-- ----------------------------------------------

tmnxMobGwPathMgmtPeerState      NOTIFICATION-TYPE
    OBJECTS {
             tmnxMobGwNtfyGatewayId,
             tmnxMobGwNtfyRefPointType,
             tmnxMobGwNtfyRefPointProtocol,
             tmnxMobGwNtfyVrtrId,
             tmnxMobGwNtfyRfPtPeerAddrType,
             tmnxMobGwNtfyRfPtPeerAddr,
             tmnxMobGwNtfyRfPtPeerPort,
             tmnxMobGwNtfyPathMgmtPeerState
            }
    STATUS      current
    DESCRIPTION
        "A tmnxMobGwPathMgmtPeerState notification is generated when there
         has been a change in the reference point peer state during path
         management."
    ::= { tmnxMobGatewayNotifications 1 }

tmnxMobGwDiameterPeerState      NOTIFICATION-TYPE
    OBJECTS {
             tmnxMobGwNtfyGatewayId,
             tmnxMobGwNtfyDiaRefPointType,
             tmnxMobGwNtfyVrtrId,
             tmnxMobGwNtfyDiaPeerName,
             tmnxMobGwNtfyDiaPeerIndex,
             tmnxMobGwNtfyDiaPeerAddrType,
             tmnxMobGwNtfyDiaPeerAddr,
             tmnxMobGwNtfyDiaPeerPort,
             tmnxMobGwNtfyDiameterPeerState,
             tmnxMobGwNtfyDiameterReasonCode
            }
    STATUS      current
    DESCRIPTION
        "A tmnxMobGwDiameterPeerState notification is generated when there
         has been a change in the reference point peer state for the diameter 
         application."
    ::= { tmnxMobGatewayNotifications 2 }

tmnxMobGwAcrFailuresAlarmMajor      NOTIFICATION-TYPE
    OBJECTS {
             tmnxMobGwNtfyGatewayId,
             tmnxMobGwNtfyChrgRefPointType,
             tmnxMobGwNtfyVrtrId,
             tmnxMobGwNtfyDiaPeerName,
             tmnxMobGwNtfyDiaPeerIndex,
             tmnxMobGwNtfyDiaPeerAddrType,
             tmnxMobGwNtfyDiaPeerAddr,
             tmnxMobGwNtfyDiaPeerPort,
             tmnxMobGwNtfyAcrFailureType
            }
    STATUS      current
    DESCRIPTION
        "A tmnxMobGwAcrFailuresAlarmMajor notification is generated when 2 
         ACR transmission failures occur in a 10 second interval or 5 
         ACR transmission failures occur in a 60 second interval to the peer. 

         [CAUSE] Charging Data Functions (CDF) peer is slow to respond to RF ACR
                 message requests or it is not responding to RF ACR message
                 requests but from a diameter connection perspective the peer
                 is still in service.
         
         [EFFECT] The gateway will choose a secondary CDF peer to send the RF
                  accounting messages for the failure attempts.
         
         [RECOVERY] Diagnose why the CDF peer is slow to respond or why it is
                    not responding to RF accounting message requests."
    ::= { tmnxMobGatewayNotifications 3 }

tmnxMobGwCdfDownAlarm      NOTIFICATION-TYPE
    OBJECTS {
             tmnxMobGwNtfyGatewayId,
             tmnxMobGwNtfyPriCdfDiaPeer,
             tmnxMobGwNtfySecCdfDiaPeer
            }
    STATUS      current
    DESCRIPTION
        "A tmnxMobGwCdfDownAlarm notification is generated when both 
         the primary and the secondary Charging Data Functions (CDFs) are down 
         for active Rf diameter sessions.

         [CAUSE] CDF peers are down or communication paths to the peers are
                 down.
         
         [EFFECT] RF accounting messages will be stored locally on compact
                  flash of the gateway.
         
         [RECOVERY] Recover CDF peers or communication links with the peers."
    ::= { tmnxMobGatewayNotifications 4 }

tmnxMobGwCdfDownAlarmCleared      NOTIFICATION-TYPE
    OBJECTS {
             tmnxMobGwNtfyGatewayId,
             tmnxMobGwNtfyCdfDiaPeer
            }
    STATUS      current
    DESCRIPTION
        "A tmnxMobGwCdfDownAlarmCleared notification is generated when one of  
         the primary and the secondary Charging Data Functions (CDFs) becomes up 
         for active Rf diameter sessions."
    ::= { tmnxMobGatewayNotifications 5 }

tmnxMobGwAcrFailuresAlarmClear      NOTIFICATION-TYPE
    OBJECTS {
             tmnxMobGwNtfyGatewayId,
             tmnxMobGwNtfyChrgRefPointType,
             tmnxMobGwNtfyVrtrId,
             tmnxMobGwNtfyDiaPeerName,
             tmnxMobGwNtfyDiaPeerIndex,
             tmnxMobGwNtfyDiaPeerAddrType,
             tmnxMobGwNtfyDiaPeerAddr,
             tmnxMobGwNtfyDiaPeerPort,
             tmnxMobGwNtfyAcrFailureType
            }
    STATUS      current
    DESCRIPTION
        "A tmnxMobGwAcrFailuresAlarmClear notification is generated after the
         tmnxMobGwAcrFailuresAlarmMajor notification when the first time less 
         then 2 Accounting Request (ACR) transmission failures occured in a 10
         seconds interval or the first time less then 5 ACR transmission 
         failures occured in a 60 seconds interval to the peer."
    ::= { tmnxMobGatewayNotifications 6 }

tmnxMobGwCfCapacityAlarmMinor      NOTIFICATION-TYPE
    OBJECTS {
             tmnxMobGwNtfyGatewayId,
             tmnxMobGwNtfyChrgRefPointType,
             tmnxMobGwNtfyFlashId,
             tmnxMobGwNtfyCfLimit
            }
    STATUS      current
    DESCRIPTION
        "A tmnxMobGwCfCapacityAlarmMinor notification is generated when compact 
         flash capacity reaches 85% limit.

         [CAUSE] Compact flash capacity is low because a CDF outage has occurred
                 and accounting messages are stored locally on the compact
                 flash of the gateway.
         
         [EFFECT] There is limited space to store accounting messages on the
                  compact flash of the gateway. Accounting messages will be lost
                  when the compact flash has no space left.
         
         [RECOVERY] Pull Accounting files from the gateway and them delete the
                    files from the compact flash."
    ::= { tmnxMobGatewayNotifications 7 }

tmnxMobGwCfCapacityAlmMnrClear      NOTIFICATION-TYPE
    OBJECTS {
             tmnxMobGwNtfyGatewayId,
             tmnxMobGwNtfyChrgRefPointType,
             tmnxMobGwNtfyFlashId,
             tmnxMobGwNtfyCfLimit
            }
    STATUS      current
    DESCRIPTION
        "A tmnxMobGwCfCapacityAlmMnrClear notification is generated when 
         compact flash capacity drops below 80% limit."
    ::= { tmnxMobGatewayNotifications 8 }

tmnxMobGwCfCapacityAlarmMajor      NOTIFICATION-TYPE
    OBJECTS {
             tmnxMobGwNtfyGatewayId,
             tmnxMobGwNtfyChrgRefPointType,
             tmnxMobGwNtfyFlashId,
             tmnxMobGwNtfyCfLimit
            }
    STATUS      current
    DESCRIPTION
        "A tmnxMobGwCfCapacityAlarmMajor notification is generated when compact 
         flash capacity reaches 95% limit. 

         [CAUSE] Compact flash capacity is low because a CDF outage has occurred
                 and accounting messages are stored locally on the compact
                 flash of the gateway.
         
         [EFFECT] There is limited space to store accounting messages on the
                  compact flash of the gateway. Accounting messages will be lost
                  when the compact flash has no space left.
         
         [RECOVERY] Pull Accounting files from the gateway and them delete the
                    files from the compact flash."
    ::= { tmnxMobGatewayNotifications 9 }

tmnxMobGwCfCapacityAlmMjrClear      NOTIFICATION-TYPE
    OBJECTS {
             tmnxMobGwNtfyGatewayId,
             tmnxMobGwNtfyChrgRefPointType,
             tmnxMobGwNtfyFlashId,
             tmnxMobGwNtfyCfLimit
            }
    STATUS      current
    DESCRIPTION
        "A tmnxMobGwCfCapacityAlmMjrClear notification is generated when 
         compact flash capacity drops below 90% limit."
    ::= { tmnxMobGatewayNotifications 10 }

tmnxMobGwSysGrpRedStateChange      NOTIFICATION-TYPE
    OBJECTS {
             tmnxMobGwSysGroupRedState
            }
    STATUS      current
    DESCRIPTION
        "A tmnxMobGwSysGrpRedStateChange notification is generated when the 
         the redundancy state of a group changes. 
 
         [CAUSE] A working card failure, changing the redundancy configuration,
                 or adding a protection card will trigger a change to the 
                 group's redundancy state.
 
         [EFFECT] When the value of tmnxMobGwSysGroupRedState changes from
                  'hot' to 'cold', a switchover has happened. No services are 
                  affected when the value of tmnxMobGwSysGroupRedState changes.
 
         [RECOVERY] After a switchover has happened, no backup card will be up.
                    The operator needs to bring a backup card online to avoid
                    any disruption to services in case of further failures."
    ::= { tmnxMobGatewayNotifications 11 }

tmnxMobGwSysGrpCardRedStChange      NOTIFICATION-TYPE
    OBJECTS {
             tmnxMobGwSysGroupCardRedState
            }
    STATUS      current
    DESCRIPTION
        "A tmnxMobGwSysGrpCardRedStChange notification is generated when the 
         the redundancy state of this card changes.

         [CAUSE] A card failure will change the card redudndancy state to 
                 'notValid'. When an active card goes down, standby card will 
                 become active which will trigger a state change to 'active'. 
                 When a 'standbyInProg' card becomes in sync with the active 
                 card, state will be changed to 'standby'.

         [EFFECT] When card goes down, it will not be able to provide any
                  mobile gateway services supported by the system.

         [RECOVERY] If the card goes down, operator's assitance is needed to 
                    get the card back online."
    ::= { tmnxMobGatewayNotifications 12 }

tmnxMobGwGtpPriServFailAlarm      NOTIFICATION-TYPE
    OBJECTS {
             tmnxMobGwNtfyGatewayId,
             tmnxMobGwNtfyVrtrId,
             tmnxMobGwNtfyGtpPriGrpName,
             tmnxMobGwNtfyGtpPriServIndex,
             tmnxMobGwNtfyGtpPriServAddrType,
             tmnxMobGwNtfyGtpPriServAddr,
             tmnxMobGwNtfyGtpPriServPort
            }
    STATUS      current
    DESCRIPTION
        "A tmnxMobGwGtpPriServFailAlarm notification is generated when GPRS 
         Tunneling Protocol (GTP) Prime Server failure is detected."
    ::= { tmnxMobGatewayNotifications 13 }

tmnxMobGwGtpPriServFailAlarmClrd      NOTIFICATION-TYPE
    OBJECTS {
             tmnxMobGwNtfyGatewayId,
             tmnxMobGwNtfyVrtrId,
             tmnxMobGwNtfyGtpPriGrpName,
             tmnxMobGwNtfyGtpPriServIndex,
             tmnxMobGwNtfyGtpPriServAddrType,
             tmnxMobGwNtfyGtpPriServAddr,
             tmnxMobGwNtfyGtpPriServPort
            }
    STATUS      current
    DESCRIPTION
        "A tmnxMobGwGtpPriServFailAlarm notification is generated when GPRS 
         Tunneling Protocol (GTP) Prime Server is recovered from the previous 
         failure."
    ::= { tmnxMobGatewayNotifications 14 }

tmnxMobGwGtpPriSrvSwitchoverSucc      NOTIFICATION-TYPE
    OBJECTS {
             tmnxMobGwNtfyGatewayId,
             tmnxMobGwNtfyVrtrId,
             tmnxMobGwNtfyGtpPriGrpName,
             tmnxMobGwNtfyGtpPriServIndex,
             tmnxMobGwNtfyGtpPriServAddrType,
             tmnxMobGwNtfyGtpPriServAddr,
             tmnxMobGwNtfyGtpPriServPort,
             tmnxMobGwNtfyNewGtpPriServIndex,
             tmnxMobGwNtfyNewGtpPriSrvAdrType,
             tmnxMobGwNtfyNewGtpPriServAddr,
             tmnxMobGwNtfyNewGtpPriServPort
            }
    STATUS      current
    DESCRIPTION
        "A tmnxMobGwGtpPriServFailAlarm notification is generated when a new
         GPRS Tunneling Protocol (GTP) Prime Server is selected after the
         failure of the active server."
    ::= { tmnxMobGatewayNotifications 15 }

tmnxMobGwGtpPriGrpFailAlarm      NOTIFICATION-TYPE
    OBJECTS {
             tmnxMobGwNtfyGatewayId,
             tmnxMobGwNtfyVrtrId,
             tmnxMobGwNtfyGtpPriGrpName
            }
    STATUS      current
    DESCRIPTION
        "A tmnxMobGwGtpPriGrpFailAlarm notification is generated when all GPRS 
         Tunneling Protocol (GTP) Prime Server have failed in the GTP Prime
         Server Group."
    ::= { tmnxMobGatewayNotifications 16 }

tmnxMobGwGtpPriGrpFailAlarmClrd      NOTIFICATION-TYPE
    OBJECTS {
             tmnxMobGwNtfyGatewayId,
             tmnxMobGwNtfyVrtrId,
             tmnxMobGwNtfyGtpPriGrpName
            }
    STATUS      current
    DESCRIPTION
        "A tmnxMobGwGtpPriGrpFailAlarmClrd notification is generated when 
         a previously failed GTP Prime Server Group has at least one
         operational GTP Prime Server."
    ::= { tmnxMobGatewayNotifications 17 }

tmnxMobGwRadPeerFailAlarm      NOTIFICATION-TYPE
    OBJECTS {
             tmnxMobGwNtfyGatewayId,
             tmnxMobGwNtfyVrtrId,
             tmnxMobGwNtfyRadGrpName,
             tmnxMobGwNtfyRadPeerAddrType,
             tmnxMobGwNtfyRadPeerAddr,
             tmnxMobGwNtfyRadPeerAuthPort,
             tmnxMobGwNtfyRadPeerAcctPort,
             tmnxMobGwNtfyRadPeerState
            }
    STATUS      current
    DESCRIPTION
        "A tmnxMobGwRadPeerFailAlarm notification is generated when the Radius
         Server failure is detected.

         [CAUSE] This happens when the operating state for radius server is 
         changed to 'down' state
    
         [EFFECT] When the radius server fails, radius messages may not be 
         sent to the radius-server
    
         [RECOVERY] If the radius server goes down, the radius server will 
         allow radius-messages to be sent to it when its operating state is 
         changed to 'up' state or after deadtimer expiring."
    ::= { tmnxMobGatewayNotifications 18 }

tmnxMobGwRadPeerFailAlarmClrd      NOTIFICATION-TYPE
    OBJECTS {
             tmnxMobGwNtfyGatewayId,
             tmnxMobGwNtfyVrtrId,
             tmnxMobGwNtfyRadGrpName,
             tmnxMobGwNtfyRadPeerAddrType,
             tmnxMobGwNtfyRadPeerAddr,
             tmnxMobGwNtfyRadPeerAuthPort,
             tmnxMobGwNtfyRadPeerAcctPort,
             tmnxMobGwNtfyRadPeerState
            }
    STATUS      current
    DESCRIPTION
        "A tmnxMobGwRadPeerFailAlarm notification is generated when the Radius
         Server is recovered from the previous failure.

        [CAUSE] The radius server is recovered from the previous failure
        and its Operating-State is changed to 'up' state. 
        
        [EFFECT] When the radius server is recovered from the previous failure, 
        and operation for the radius-server is back to normal.
        
        [RECOVERY] If the radius server is recovered from the previous failure, 
        no further action is needed. "
    ::= { tmnxMobGatewayNotifications 19 }

tmnxMobGwRadGrpFailAlarm      NOTIFICATION-TYPE
    OBJECTS {
             tmnxMobGwNtfyGatewayId,
             tmnxMobGwNtfyVrtrId,
             tmnxMobGwNtfyRadGrpName,
             tmnxMobGwNtfyRadGrpState
            }
    STATUS      current
    DESCRIPTION
        "A tmnxMobGwRadGrpFailAlarm notification is generated when all the 
         radius servers have failed in the radius server group.

         [CAUSE] This event will be generated when all the radius servers 
         for the group are in operating 'down' state. 
    
         [EFFECT] When the group of radius servers fails, radius messages 
         may not be sent to the group.
    
         [RECOVERY] The radius group will recover from this failure mode when 
         one of its server is going back to operating 'up' state."
    ::= { tmnxMobGatewayNotifications 20 }

tmnxMobGwRadGrpFailAlarmClrd      NOTIFICATION-TYPE
    OBJECTS {
             tmnxMobGwNtfyGatewayId,
             tmnxMobGwNtfyVrtrId,
             tmnxMobGwNtfyRadGrpName,
             tmnxMobGwNtfyRadGrpState
            }
    STATUS      current
    DESCRIPTION
        "A tmnxMobGwRadGrpFailAlarmClrd notification is generated when 
         a previously failed Radius Server Group has at least one
         operational Radius Server.

        [CAUSE] The radius server group is recovered from the previous failure
        and at least one of its servers has transitioned to operating 'up' 
        state.
        
        [EFFECT] When the radius server group is recovered from the previous 
        failure and operation for the radius-group is back to normal.
        
        [RECOVERY] If the radius group is recovered from the previous failure, 
        no further action is needed. "
    ::= { tmnxMobGatewayNotifications 21 }

tmnxMobLiDf2OperStateChange      NOTIFICATION-TYPE
    OBJECTS {
             tmnxMobLiDf2OperState
            }
    STATUS      current
    DESCRIPTION
        "A tmnxMobLiDf2OperStateChange notification is generated when the 
         current operational state of the Delivery Function 2 peer changes.
 
         [CAUSE] The df2-peer's operational state will change when the TCP
         connection's state to the df2-peer changes.
         
         [EFFECT] When the df2-peer's state is down, the Intercept Related
         Information (IRI) packets are not sent to the peer. When the  
         df2-peer's state is up, the IRI packets are sent to the peer. 
        
         [RECOVERY] If the df2-peer goes down, then the IRI packets being sent 
         to the peer will be buffered until it comes up. Then, all the packets 
         will be sent to the peer."
    ::= { tmnxMobGatewayNotifications 22 }

tmnxMobGwGtpPriServerState      NOTIFICATION-TYPE
    OBJECTS {
             tmnxMobGwNtfyGatewayId,
             vRtrID,
             tmnxMobGtpPriServerAddrType,
             tmnxMobGtpPriServerAddr,
             tmnxMobGtpPriServerPort,
             tmnxMobGwNtfyGtpPriServerState,
             tmnxMobGwNtfyGtpPriSvrReasonCode
            }
    STATUS      current
    DESCRIPTION
        "A tmnxMobGwGtpPriServerState notification is generated when there
         has been a change in the when GPRS Tunneling Protocol (GTP) Prime
         Server state for all mobile system groups.

         [CAUSE] When there is a change in GTP Prime Server State.
         
         [EFFECT] When the GTP Prime Server State is add, the server has been
         added to the system. When the state is delete, the server has been
         deleted from the system. When the state is down, Charging Data
         Record (CDR) packets are not sent to the peer. When the state is up,
         CDR packets can be sent to the peer. 
        
         [RECOVERY] If a GTP Prime server state is down, then Charging Data
         Request(CDR) packets will be sent to an alternate GTP Prime server.
         If no servers are available, CDR packets will be written to CDR files."
    ::= { tmnxMobGatewayNotifications 23 }

tmnxMobGwSysGrpGtpPriServerState      NOTIFICATION-TYPE
    OBJECTS {
             tmnxMobGwNtfyGatewayId,
             tmnxMobGwNtfySysGroupId,   
             vRtrID,
             tmnxMobGtpPriServerAddrType,
             tmnxMobGtpPriServerAddr,
             tmnxMobGtpPriServerPort,
             tmnxMobGwNtfyGtpPriServerState,
             tmnxMobGwNtfyGtpPriSvrReasonCode
            }
    STATUS      current
    DESCRIPTION
        "A tmnxMobGwSysGrpGtpPriServerState notification is generated when there
         has been a change in the when GPRS Tunneling Protocol (GTP) Prime
         Server state per mobile system group.

         [CAUSE] When there is a change in GTP Prime Server State.
         
         [EFFECT] When the GTP Prime Server State is add, the server has been
         added to the system. When the state is delete, the server has been
         deleted from the system. When the state is down, Charging Data
         Record (CDR) packets are not sent to the peer. When the state is up,
         CDR packets can be sent to the peer. 
        
         [RECOVERY] If a GTP Prime server state is down, then Charging Data
         Request(CDR) packets will be sent to an alternate GTP Prime server.
         If no servers are available, CDR packets will be written to CDR files."
    ::= { tmnxMobGatewayNotifications 24 }

tmnxMobGwGtpPriSrvGrpState      NOTIFICATION-TYPE
    OBJECTS {
             tmnxMobGwNtfyGatewayId,
             vRtrID,
             tmnxMobGwNtfyGtpPriGrpName,
             tmnxMobGwNtfyGtpPriGrpState,
             tmnxMobGwNtfyGtpPriGrpReasonCode
            }
    STATUS      current
    DESCRIPTION
        "A tmnxMobGwGtpPriSrvGrpState notification is generated when there
         has been a change in the when GPRS Tunneling Protocol (GTP) Prime
         Server state for all mobile system groups. 

         [CAUSE] When there is a change in GTP Prime Server Group State.
         
         [EFFECT] When the GTP Prime Server Group State is add, the group has
         been added to the system. When the state is delete, the group has been
         deleted from the system. When the state is down means all GTP Prime 
         Servers in the group are down, and Charging Data Record (CDR) packets
         are not sent to the group server. When the state is up, CDR packets can
         be sent to the group server. 
         
         [RECOVERY] If a GTP Prime server group state is down, CDR packets will
         be written to CDR files until at least one server becomes available."
    ::= { tmnxMobGatewayNotifications 25 }

tmnxMobGwSysGrpGtpPriSrvGrpState      NOTIFICATION-TYPE
    OBJECTS {
             tmnxMobGwNtfyGatewayId,
             tmnxMobGwNtfySysGroupId,   
             vRtrID,
             tmnxMobGwNtfyGtpPriGrpName,
             tmnxMobGwNtfyGtpPriGrpState,
             tmnxMobGwNtfyGtpPriGrpReasonCode
            }
    STATUS      current
    DESCRIPTION
        "A tmnxMobGwGtpPriSrvGrpState notification is generated when there
         has been a change in the when GPRS Tunneling Protocol (GTP) Prime
         Server state per mobile system group. 

         [CAUSE] When there is a change in GTP Prime Server Group State.
         
         [EFFECT] When the GTP Prime Server Group State is add, the group has
         been added to the system. When the state is delete, the group has been
         deleted from the system. When the state is down means all GTP Prime 
         Servers in the group are down, and Charging Data Record (CDR) packets
         are not sent to the group server. When the state is up, CDR packets can
         be sent to the group server. 
         
         [RECOVERY] If a GTP Prime server group state is down, CDR packets will
         be written to CDR files until at least one server becomes available."
    ::= { tmnxMobGatewayNotifications 26 }

tmnxMobGwSysGrpWriteCdrToCfAlarm      NOTIFICATION-TYPE
    OBJECTS {
             tmnxMobGwNtfyGatewayId,
             tmnxMobGwNtfySysGroupId,
             tmnxMobGwNtfyWriteCdrAction
            }
    STATUS      current
    DESCRIPTION
        "A tmnxMobGwSysGrpWriteCdrToCfAlarm notification is generated when the
         SGW or PGW starts to write Charging Data Record (CDR) packets to the
         local compact flash for the mobile system group.

         [CAUSE] When there is a change in action to write Charging Data
         Record (CDR) packets to compact flash.
         
         [EFFECT] When the action is start, the system has started writing CDR
         packets to files on compact flash. the system has stopped writing CDR
         packets to files on compact flash.
         
         [RECOVERY] Retrieve CDR files from compact flash."
    ::= { tmnxMobGatewayNotifications 27 }

tmnxMobGwSysGrpDiameterPeerState      NOTIFICATION-TYPE
    OBJECTS {
             tmnxMobGwNtfyGatewayId,
             tmnxMobGwNtfyDiaRefPointType,
             tmnxMobGwNtfySysGroupId,
             vRtrID,
             tmnxMobGwNtfyDiaPeerName,
             tmnxMobGwNtfyDiaPeerIndex,
             tmnxMobGwNtfyDiaPeerAddrType,
             tmnxMobGwNtfyDiaPeerAddr,
             tmnxMobGwNtfyDiaPeerPort,
             tmnxMobGwNtfyDiameterPeerState,
             tmnxMobGwNtfyDiameterReasonCode
            }
    STATUS      current
    DESCRIPTION
        "The tmnxMobGwSysGrpDiameterPeerState notification is generated when
         there has been a change in the state of a reference point peer in
         the diameter application per mobile system group.        
        
         [CAUSE] When there is a change in Diameter Peer State.
        
         [EFFECT] If the value of tmnxMobGwNtfyDiameterPeerState is 'pathDown'
         for the mobile system group, then the diameter application supported on
         that connection will not function between the given mobile system group
         and the given diameter peer.
        
         [RECOVERY] If the value of tmnxMobGwNtfyDiameterPeerState is 'pathDown'
         for a mobile system group, the operator may have to take an action to
         investigate and recover the connection between the mobile system
         group and the diameter peer."
    ::= { tmnxMobGatewayNotifications 28 }

-- ----------------------------------------------
-- Compliance Statements
-- ----------------------------------------------

tmnxMobGatewayV1v0Compliance  MODULE-COMPLIANCE
    STATUS      obsolete
    DESCRIPTION
        "The compliance statement for management of the mobile gateways on the
         Alcatel-Lucent 7750 Mobile Gateway systems R1.0."
    MODULE
        MANDATORY-GROUPS {
            tmnxMobGatewayGlobalGroup,
            tmnxMobGatewayCommonGroup,
            tmnxMobGatewaySystemGroup,
            tmnxMobGatewayRefPointGroup,
            tmnxMobGatewayNotifyObjsGroup,
            tmnxMobGatewayNotificationsGroup,
            tmnxMobGatewayLiGroup
            -- tmnxMobGatewayUnsupportedGroup  Not supported
        }
    ::= { tmnxMobGatewayCompliances 1 }

tmnxMobGatewayV3v0Compliance  MODULE-COMPLIANCE
    STATUS      obsolete
    DESCRIPTION
        "The compliance statement for management of the mobile gateways on the
         Alcatel-Lucent 7750 Mobile Gateway systems R3.0.

         This compliance module was made obsolete in the 3.1 R2 release"
    MODULE
        MANDATORY-GROUPS {
            tmnxMobGatewayGlobalGroup,
            tmnxMobGatewayCommonGroup,
            tmnxMobGatewaySystemGroup,
            tmnxMobGatewayRefPointGroup,
            tmnxMobGatewayNotifyObjsGroup,
            tmnxMobGatewayNotificationsGroup,
            tmnxMobGatewayLiGroup,
            tmnxMobGatewayNotifyV3Group,
            tmnxMobGatewayNotifyObjsV3Group,
            tmnxMobGatewayGlobalV3Group,
            tmnxMobGatewayThresV3v0Group,
            tmnxMobGatewayRefPointV3v5Group
            -- tmnxMobGatewayUnsupportedGroup Not supported
        }
    ::= { tmnxMobGatewayCompliances 2 }


tmnxMobGateway7xxxV10v0Compl  MODULE-COMPLIANCE
    STATUS      current
    DESCRIPTION
        "The compliance statement for management of the mobile gateways on the
         Alcatel-Lucent 7750 SROS R10.0."
    MODULE
        MANDATORY-GROUPS {
            tmnxMobGatewayCommonGroup,
            tmnxMobGatewayGlobalGroup,
            tmnxMobGatewayGlobalV3Group,    
            tmnxMobGatewayLiGroup,  
            tmnxMobGatewayRefPointGroupV31v2,
            tmnxMobGatewayRefPointV3v5Group,
            tmnxMobGatewaySystemGroup,
            tmnxMobGatewayThresV3v0Group,
            tmnxMobGatewayNotificationsGroup,
            tmnxMobGatewayNotifyV3Group,
            tmnxMobGatewayNotifyObjsV3Group,
            tmnxMobGatewayGlobalV3Group,
            tmnxMobGatewayThresV3v0Group,
            tmnxMobGatewayRefPointV3v5Group,
            tmnxMobGatewayRefPointGroupV31v2,
            tmnxMobGatewayUnsupportedGroup 
        }
    ::= { tmnxMobGatewayCompliances 3 }

-- ----------------------------------------------
-- Units of Conformance
-- ----------------------------------------------

tmnxMobGatewayGlobalGroup  OBJECT-GROUP
    OBJECTS {
                tmnxMobGwTableLastChanged,
                tmnxMobGwSysGroupTblLstChgd,
                tmnxMobGwSysGroupCardTblLstChgd,
                tmnxMobGwS5PeerTableLastChanged,
                tmnxMobGwRfPeerTableLastChngd,
                tmnxMobLiDfPeerTableLastChanged,
                tmnxMobLiTargetTableLastChanged
            }
    STATUS      current
    DESCRIPTION
        "The group of global objects supporting management of the mobile
         gateways on the Alcatel-Lucent 7750 Mobile Gateway systems."
    ::= { tmnxMobGatewayGroups 1 }

tmnxMobGatewayCommonGroup  OBJECT-GROUP
    OBJECTS {
                tmnxMobGwRowStatus,
                tmnxMobGwLastChanged,
                tmnxMobGwType,
                tmnxMobGwRestartCounter
            }
    STATUS      current
    DESCRIPTION
        "The group of objects supporting management of system groups for the
         mobile gateways on the Alcatel-Lucent 7750 Mobile Gateway systems."
    ::= { tmnxMobGatewayGroups 2 }

tmnxMobGatewaySystemGroup  OBJECT-GROUP
    OBJECTS {
                tmnxMobGwSysGroupRowStatus,
                tmnxMobGwSysGroupLastChanged,
                tmnxMobGwSysGroupOperState,
                tmnxMobGwSysGroupApp,
                tmnxMobGwSysGroupRed,
                tmnxMobGwSysGroupSysLimitName,
                tmnxMobGwSysGroupGateway,
                tmnxMobGwSysGroupCardRowStatus,
                tmnxMobGwSysGroupCardLastChanged,
                tmnxMobGwSysGroupCardRole,
                tmnxMobGwSysLimitName,
                tmnxMobGwSysGroupSwitchoverCount,
                tmnxMobGwSysGroupSwitchoverTime,
                tmnxMobGwSysGroupProtectDelay,
                tmnxMobGwSysGroupCardRedState,
                tmnxMobGwSysGroupRedState
            }
    STATUS      current
    DESCRIPTION
        "The group of objects supporting management of system groups for the
         mobile gateways on the Alcatel-Lucent 7750 Mobile Gateway systems."
    ::= { tmnxMobGatewayGroups 3 }

tmnxMobGatewayRefPointGroup  OBJECT-GROUP
    OBJECTS {
                tmnxMobGwS5PeerLastChanged,
                tmnxMobGwS5PeerCreateTime,
                tmnxMobGwS5PeerPathMgmtState,
                tmnxMobGwS5PeerGatewayId,
                tmnxMobGwS5PeerType,
                tmnxMobGwS5StatCreateSessnReq,
                tmnxMobGwS5StatCreateSessnResp,
                tmnxMobGwS5StatDeleteSessnReq,
                tmnxMobGwS5StatDeleteSessnResp,
                tmnxMobGwS5StatCreateBearerReq,
                tmnxMobGwS5StatCreateBearerRsp,
                tmnxMobGwS5StatDeleteBearerReq,
                tmnxMobGwS5StatDeleteBearerRsp,
                tmnxMobGwS5StatModifyBearerReq,
                tmnxMobGwS5StatModifyBearerRsp,
                tmnxMobGwS5StatRxEchoRequests,
                tmnxMobGwS5StatTxEchoResponses,
                tmnxMobGwS5StatTxEchoRequests,
                tmnxMobGwS5StatRxEchoResponses,
                tmnxMobGwS5StatRxMalformedPkts,
                tmnxMobGwS5StatRxUnknownPkts,
                tmnxMobGwS5StatRxMissingIePkts,
                tmnxMobGwS5StatPeerRestarts,
                tmnxMobGwS5StatPeerRestrtCount,
                tmnxMobGwS5StatPathMgmtFails,
                tmnxMobGwS5StatUpdateBearerReq,
                tmnxMobGwS5StatUpdateBearerRsp,
                tmnxMobGwRfPeerLastChanged,
                tmnxMobGwRfPeerCreateTime,
                tmnxMobGwRfPeerPathMgmtState,
                tmnxMobGwRfPeerDetailState,
                tmnxMobGwRfStatTxCer,
                tmnxMobGwRfStatRxCea,
                tmnxMobGwRfStatRxDpr,
                tmnxMobGwRfStatTxDpa,
                tmnxMobGwRfStatTxDwr,
                tmnxMobGwRfStatRxDwa,
                tmnxMobGwRfStatConnAttempts,
                tmnxMobGwRfStatConnFailures,
                tmnxMobGwRfStatRxTransportDisc,
                tmnxMobGwRfStatRxMsgUnexpectVer,
                tmnxMobGwRfStatRxMsgTooBig,
                tmnxMobGwRfStatRxMsgTooSmall,
                tmnxMobGwRfStatRxInvalidCea,
                tmnxMobGwRfStatRxMsgs,
                tmnxMobGwRfStatTxMsgs,
                tmnxMobGwRfStatTxRetransmitMsgs,
                tmnxMobGwRfStatTxAcrStart,
                tmnxMobGwRfStatTxAcrInterim,
                tmnxMobGwRfStatTxAcrStop,
                tmnxMobGwRfStatTxAcrStartFails,
                tmnxMobGwRfStatTxAcrInterimFail,
                tmnxMobGwRfStatTxAcrStopFails,
                tmnxMobGwRfStatBearers,
                tmnxMobGwRfStatDefBearers,
                tmnxMobGwRfStatDedctdBearers,
                tmnxMobGwRfStatRoamers,
                tmnxMobGwRfStatBearersIpv4,
                tmnxMobGwRfStatBearersIpv6,
                tmnxMobGwRfStatBearersIpv4v6,
                tmnxMobGwRfStatActiveBearers,
                tmnxMobGwRfStatIdleBearers,
                tmnxMobGwS5StatBearersIpv4,
                tmnxMobGwS5StatBearersIpv6,
                tmnxMobGwS5StatBearerIpv4v6,
                tmnxMobGwS5StatDedctdBearers,
                tmnxMobGwS5StatUlBytes,
                tmnxMobGwS5StatDlBytes,
                tmnxMobGwS5StatUlPackets,
                tmnxMobGwS5StatDlPackets,
                tmnxMobGwS5StatBearers,
                tmnxMobGwS5StatDefBearers,
                tmnxMobGwS5StatRoamers,
                tmnxMobGwS5StatActiveBearers,
                tmnxMobGwS5StatIdleBearers,
                tmnxMobGwS5StatModifyBearrCmd,
                tmnxMobGwS5StatModifyBearrFlr,
                tmnxMobGwS5StatDeleteBearrCmd,
                tmnxMobGwS5StatDeleteBearrFlr,
                tmnxMobGwS5StatBearrResCmd,
                tmnxMobGwS5StatBearrResFailInd,
                tmnxMobGwS5StatSuspNoticeReq,
                tmnxMobGwS5StatSuspNoticeAck,
                tmnxMobGwS5StatResumeNoticeReq,
                tmnxMobGwS5StatResumeNoticeAck,
                tmnxMobGwRfStatTxDpr,
                tmnxMobGwRfStatRxDpa,
                tmnxMobGwRfStatRxDwr,
                tmnxMobGwRfStatTxDwa
            }
    STATUS      obsolete
    DESCRIPTION
        "The group of objects supporting management of the mobile gateway
         reference point statistics on the Alcatel-Lucent 7750 Mobile Gateway 
         systems.

         This group was made obsolete in the 3.1 R2 release"
    ::= { tmnxMobGatewayGroups 4 }

tmnxMobGatewayNotifyObjsGroup        OBJECT-GROUP
    OBJECTS {
              tmnxMobGwNtfyGatewayId,
              tmnxMobGwNtfyVrtrId,
              tmnxMobGwNtfyRefPointType,
              tmnxMobGwNtfyRefPointProtocol,
              tmnxMobGwNtfyRfPtPeerAddrType,
              tmnxMobGwNtfyRfPtPeerAddr,
              tmnxMobGwNtfyRfPtPeerPort,
              tmnxMobGwNtfyPathMgmtPeerState,
              tmnxMobGwNtfyDiaRefPointType,
              tmnxMobGwNtfyDiaPeerName,
              tmnxMobGwNtfyDiaPeerIndex,
              tmnxMobGwNtfyDiaPeerAddrType,
              tmnxMobGwNtfyDiaPeerAddr,
              tmnxMobGwNtfyDiaPeerPort,
              tmnxMobGwNtfyDiameterPeerState,
              tmnxMobGwNtfyDiameterReasonCode,
              tmnxMobGwNtfyChrgRefPointType,
              tmnxMobGwNtfyPriCdfDiaPeer,
              tmnxMobGwNtfySecCdfDiaPeer,
              tmnxMobGwNtfyCdfDiaPeer,
              tmnxMobGwNtfyFlashId,
              tmnxMobGwNtfyCfLimit,
              tmnxMobGwNtfyAcrFailureType
            }
    STATUS        current
    DESCRIPTION
        "The group of objects supporting mobile gateway notifications on
         the Alcatel-Lucent 7750 Mobile Gateway systems."
    ::= { tmnxMobGatewayGroups 5 }

tmnxMobGatewayNotificationsGroup     NOTIFICATION-GROUP
    NOTIFICATIONS {
                    tmnxMobGwPathMgmtPeerState,
                    tmnxMobGwDiameterPeerState,
                    tmnxMobGwAcrFailuresAlarmMajor,
                    tmnxMobGwCdfDownAlarm,
                    tmnxMobGwCdfDownAlarmCleared,
                    tmnxMobGwAcrFailuresAlarmClear,
                    tmnxMobGwCfCapacityAlarmMinor,
                    tmnxMobGwCfCapacityAlmMnrClear,
                    tmnxMobGwCfCapacityAlarmMajor,
                    tmnxMobGwCfCapacityAlmMjrClear,
                    tmnxMobGwSysGrpRedStateChange,
                    tmnxMobGwSysGrpCardRedStChange
                  }
    STATUS        current
    DESCRIPTION
        "The group of notifications supporting management of mobile gateway
         on the Alcatel-Lucent 7750 Mobile Gateway systems."
    ::= { tmnxMobGatewayGroups 6 }

tmnxMobGatewayUnsupportedGroup  OBJECT-GROUP
    OBJECTS {
              tmnxMobGwDescription,
              tmnxMobGwSysGroupDescription,
              tmnxMobGwS5StatCreatePbu,
              tmnxMobGwS5StatCreatePba,
              tmnxMobGwS5StatDeletePbu,
              tmnxMobGwS5StatDeletePba,
              tmnxMobGwS5StatBri,
              tmnxMobGwS5StatBra
            }
    STATUS      current
    DESCRIPTION
        "This group of objects is not supported on the Alcatel-Lucent 7750 
         Mobile Gateway systems."
    ::= { tmnxMobGatewayGroups 7 }

tmnxMobGatewayLiGroup  OBJECT-GROUP
    OBJECTS {
                tmnxMobLiDfPeerRowStatus,
                tmnxMobLiDfPeerLastChanged,
                tmnxMobLiDf2PeerAddressType,
                tmnxMobLiDf2PeerAddress,
                tmnxMobLiDf2PeerPort,
                tmnxMobLiDf3PeerAddressType,
                tmnxMobLiDf3PeerAddress,
                tmnxMobLiDf3PeerPort,
                tmnxMobLiDf2OperState,
                tmnxMobLiDf2PeerPktsTx,
                tmnxMobLiTargetRowStatus,
                tmnxMobLiTargetLastChanged,
                tmnxMobLiTargetInterceptType,  
                tmnxMobLiTargetDfPeer,
                tmnxMobLiX3Transport,
                tmnxMobLiLocalInterfaceType,
                tmnxMobLiLocalInterface,
                tmnxMobLiTotalTargets,        
                tmnxMobLiTotalPeers,        
                tmnxMobLiTotalIRITargets,
                tmnxMobLiTotalIRICCTargets,
                tmnxMobLiDf3OperState,
                tmnxMobLiDf3PeerPktsTx,
                tmnxMobLiTotalTargetPerPeer,
                tmnxMobLiVprnId,
                tmnxMobTargetLiId,
                tmnxMobLiULICVersion,
                tmnxMobLiULIChangeReporting,
                tmnxMobLiOperatorId
            }
    STATUS      current
    DESCRIPTION
        "The group of objects supporting management of Lawful Interception (LI)
         groups for the mobile gateways on the Alcatel-Lucent 7750 Mobile
         Gateway systems."
    ::= { tmnxMobGatewayGroups 8 }

tmnxMobGatewayNotifyV3Group     NOTIFICATION-GROUP
    NOTIFICATIONS {
                    tmnxMobGwGtpPriServFailAlarm,
                    tmnxMobGwGtpPriServFailAlarmClrd,
                    tmnxMobGwGtpPriSrvSwitchoverSucc,
                    tmnxMobGwGtpPriGrpFailAlarm,
                    tmnxMobGwGtpPriGrpFailAlarmClrd,
                    tmnxMobGwRadGrpFailAlarm,
                    tmnxMobGwRadGrpFailAlarmClrd,
                    tmnxMobGwRadPeerFailAlarm,
                    tmnxMobGwRadPeerFailAlarmClrd,
                    tmnxMobLiDf2OperStateChange,
                    tmnxMobGwGtpPriServerState,
                    tmnxMobGwGtpPriSrvGrpState,
                    tmnxMobGwSysGrpGtpPriServerState,
                    tmnxMobGwSysGrpGtpPriSrvGrpState,
                    tmnxMobGwSysGrpWriteCdrToCfAlarm,
                    tmnxMobGwSysGrpDiameterPeerState
                  }
    STATUS        current
    DESCRIPTION
        "The group of notifications supporting management of mobile gateway
         on the Alcatel-Lucent 7750 Mobile Gateway systems in 3.0 release."
    ::= { tmnxMobGatewayGroups 9 }

tmnxMobGatewayNotifyObjsV3Group        OBJECT-GROUP
    OBJECTS {
              tmnxMobGwNtfyGtpPriGrpName,
              tmnxMobGwNtfyGtpPriServAddr,
              tmnxMobGwNtfyGtpPriServAddrType,
              tmnxMobGwNtfyGtpPriServIndex,
              tmnxMobGwNtfyGtpPriServPort,
              tmnxMobGwNtfyNewGtpPriServAddr,
              tmnxMobGwNtfyNewGtpPriServIndex,
              tmnxMobGwNtfyNewGtpPriServPort,
              tmnxMobGwNtfyNewGtpPriSrvAdrType,
              tmnxMobGwNtfyRadGrpName,
              tmnxMobGwNtfyRadPeerAddr,
              tmnxMobGwNtfyRadPeerAddrType,
              tmnxMobGwNtfyRadPeerIndex,
              tmnxMobGwNtfyRadPeerAuthPort,
              tmnxMobGwNtfyRadPeerAcctPort,
              tmnxMobGwNtfyRadPeerState,
              tmnxMobGwNtfyRadGrpState,
              tmnxMobGwNtfyGtpPriGrpReasonCode,
              tmnxMobGwNtfyGtpPriGrpState,
              tmnxMobGwNtfyGtpPriServerState,
              tmnxMobGwNtfyGtpPriSvrReasonCode,
              tmnxMobGwNtfySysGroupId,
              tmnxMobGwNtfyWriteCdrAction
            }
    STATUS        current
    DESCRIPTION
        "The group of objects supporting mobile gateway notifications on
         the Alcatel-Lucent 7750 Mobile Gateway systems in 3.0 release."
    ::= { tmnxMobGatewayGroups 10 }

tmnxMobGatewayGlobalV3Group  OBJECT-GROUP
    OBJECTS {
                tmnxMobThresGroupLastChgd,                
                tmnxMobThresConfigLastChanged
            }
    STATUS      current
    DESCRIPTION
        "The group of global objects supporting management of the mobile
         gateways on the Alcatel-Lucent 7750 Mobile Gateway systems in 3.0
         release."
    ::= { tmnxMobGatewayGroups 11 }

tmnxMobGatewayThresV3v0Group  OBJECT-GROUP
    OBJECTS {
              tmnxMobThresGrpRowStatus,
              tmnxMobThresGrpLastChanged,
              tmnxMobThresGrpAdminState,
              tmnxMobThresGrpInterval,
              tmnxMobThresCfgRowStatus,
              tmnxMobThresCfgLastChanged,
              tmnxMobThresCfgGroupId,
              tmnxMobThresCfgSubGroupId,
              tmnxMobThresCfgAlarmIndex,
              tmnxMobThresCfgHighThreshold,
              tmnxMobThresCfgLowThreshold,
              tmnxMobThresCfgCtrOID,
              tmnxMobMgIsmThresLastChanged,
              tmnxMobMgIsmThresCpu,
              tmnxMobMgIsmThresMem,
              tmnxMobMgIsmThresThrptUL,
              tmnxMobMgIsmThresThrptDL
    }
    STATUS      current
    DESCRIPTION
         "The group of objects supporting management of threshold based
          monitoring groups for Mobile Gateway in 3.0 release."
    ::= { tmnxMobGatewayGroups 12 }

tmnxMobGatewayRefPointV3v5Group  OBJECT-GROUP
    OBJECTS {
              tmnxMobGwS8PeerTableLastChanged,
              tmnxMobGwS8PeerLastChanged,
              tmnxMobGwS8PeerCreateTime,
              tmnxMobGwS8PeerPathMgmtState,
              tmnxMobGwS8PeerGatewayId,
              tmnxMobGwS8PeerType,
              tmnxMobGwS8StatCreateSessnReq,
              tmnxMobGwS8StatCreateSessnResp,
              tmnxMobGwS8StatDeleteSessnReq,
              tmnxMobGwS8StatDeleteSessnResp,
              tmnxMobGwS8StatCreateBearerReq,
              tmnxMobGwS8StatCreateBearerRsp,
              tmnxMobGwS8StatDeleteBearerReq,
              tmnxMobGwS8StatDeleteBearerRsp,
              tmnxMobGwS8StatModifyBearerReq,
              tmnxMobGwS8StatModifyBearerRsp,
              tmnxMobGwS8StatRxEchoRequests,
              tmnxMobGwS8StatTxEchoResponses,
              tmnxMobGwS8StatTxEchoRequests,
              tmnxMobGwS8StatRxEchoResponses,
              tmnxMobGwS8StatRxMalformedPkts,
              tmnxMobGwS8StatRxUnknownPkts,
              tmnxMobGwS8StatRxMissingIePkts,
              tmnxMobGwS8StatCreatePbu,
              tmnxMobGwS8StatCreatePba,
              tmnxMobGwS8StatDeletePbu,
              tmnxMobGwS8StatDeletePba,
              tmnxMobGwS8StatBri,
              tmnxMobGwS8StatBra,
              tmnxMobGwS8StatPeerRestarts,
              tmnxMobGwS8StatPeerRestrtCount,
              tmnxMobGwS8StatPathMgmtFails,
              tmnxMobGwS8StatUpdateBearerReq,
              tmnxMobGwS8StatUpdateBearerRsp,
              tmnxMobGwS8StatCreatSessnRspFl,
              tmnxMobGwS8StatDelSessnRspFail,
              tmnxMobGwS8StatCreatBearrRspFl,
              tmnxMobGwS8StatDelBearrRspFail,
              tmnxMobGwS8StatModBearrRspFail,
              tmnxMobGwS8StatUpdatBearrRspFl,
              tmnxMobGwS5StatCreateSessnRespFl,
              tmnxMobGwS5StatDeleteSessnRespFl,
              tmnxMobGwS5StatCreateBearerRspFl,
              tmnxMobGwS5StatDeleteBearerRspFl,
              tmnxMobGwS5StatModifyBearerRspFl,
              tmnxMobGwS5StatUpdateBearerRspFl,
              tmnxMobGwS5CcRxReqAccepted,
              tmnxMobGwS5CcRxCtxNotFound,
              tmnxMobGwS5CcRxInvalidLength,
              tmnxMobGwS5CcRxMndIeIncorrect,
              tmnxMobGwS5CcRxMandIeMissing,
              tmnxMobGwS5CcRxReqRejected,
              tmnxMobGwS5CcRxRemPeerNoResp,
              tmnxMobGwS5CcRxNoResAvailable,
              tmnxMobGwS5CcRxUsrAuthFailure,
              tmnxMobGwS5CcRxOthers,
              tmnxMobGwS5CcTxReqAccepted,
              tmnxMobGwS5CcTxCtxNotFound,
              tmnxMobGwS5CcTxInvalidLength,
              tmnxMobGwS5CcTxMndIeIncorrect,
              tmnxMobGwS5CcTxMandIeMissing,
              tmnxMobGwS5CcTxReqRejected,
              tmnxMobGwS5CcTxRemPeerNoResp,
              tmnxMobGwS5CcTxNoResAvailable,
              tmnxMobGwS5CcTxUsrAuthFailure,
              tmnxMobGwS5CcTxOthers
            }
    STATUS      current
    DESCRIPTION
        "The group of objects supporting management of the mobile gateway
         reference point statistics on the Alcatel-Lucent 7750 Mobile Gateway 
         systems in the 3.0 R5 release."
    ::= { tmnxMobGatewayGroups 13 }

tmnxMobGatewayObsoletedGroups OBJECT-GROUP
    OBJECTS{
                tmnxMobGwS5StatBearersIpv4,
                tmnxMobGwS5StatBearersIpv6,
                tmnxMobGwS5StatBearerIpv4v6,
                tmnxMobGwS5StatDedctdBearers,
                tmnxMobGwS5StatDefBearers,
                tmnxMobGwS5StatRoamers,
                tmnxMobGwS5StatActiveBearers,
                tmnxMobGwS5StatIdleBearers
           }
    STATUS current
    DESCRIPTION
        "The group of obsolete objects which are no longer supported in the 3.1
        release on the Mobile Gateway on the Alcatel-Lucent 7750 Mobile Gateway
        systems."
    ::={tmnxMobGatewayGroups 14}

tmnxMobGatewayRefPointGroupV31v2  OBJECT-GROUP
    OBJECTS {
                tmnxMobGwS5PeerLastChanged,
                tmnxMobGwS5PeerCreateTime,
                tmnxMobGwS5PeerPathMgmtState,
                tmnxMobGwS5PeerGatewayId,
                tmnxMobGwS5PeerType,
                tmnxMobGwS5StatCreateSessnReq,
                tmnxMobGwS5StatCreateSessnResp,
                tmnxMobGwS5StatDeleteSessnReq,
                tmnxMobGwS5StatDeleteSessnResp,
                tmnxMobGwS5StatCreateBearerReq,
                tmnxMobGwS5StatCreateBearerRsp,
                tmnxMobGwS5StatDeleteBearerReq,
                tmnxMobGwS5StatDeleteBearerRsp,
                tmnxMobGwS5StatModifyBearerReq,
                tmnxMobGwS5StatModifyBearerRsp,
                tmnxMobGwS5StatRxEchoRequests,
                tmnxMobGwS5StatTxEchoResponses,
                tmnxMobGwS5StatTxEchoRequests,
                tmnxMobGwS5StatRxEchoResponses,
                tmnxMobGwS5StatRxMalformedPkts,
                tmnxMobGwS5StatRxUnknownPkts,
                tmnxMobGwS5StatRxMissingIePkts,
                tmnxMobGwS5StatPeerRestarts,
                tmnxMobGwS5StatPeerRestrtCount,
                tmnxMobGwS5StatPathMgmtFails,
                tmnxMobGwS5StatUpdateBearerReq,
                tmnxMobGwS5StatUpdateBearerRsp,
                tmnxMobGwRfPeerLastChanged,
                tmnxMobGwRfPeerCreateTime,
                tmnxMobGwRfPeerPathMgmtState,
                tmnxMobGwRfPeerDetailState,
                tmnxMobGwRfStatTxCer,
                tmnxMobGwRfStatRxCea,
                tmnxMobGwRfStatRxDpr,
                tmnxMobGwRfStatTxDpa,
                tmnxMobGwRfStatTxDwr,
                tmnxMobGwRfStatRxDwa,
                tmnxMobGwRfStatConnAttempts,
                tmnxMobGwRfStatConnFailures,
                tmnxMobGwRfStatRxTransportDisc,
                tmnxMobGwRfStatRxMsgUnexpectVer,
                tmnxMobGwRfStatRxMsgTooBig,
                tmnxMobGwRfStatRxMsgTooSmall,
                tmnxMobGwRfStatRxInvalidCea,
                tmnxMobGwRfStatRxMsgs,
                tmnxMobGwRfStatTxMsgs,
                tmnxMobGwRfStatTxRetransmitMsgs,
                tmnxMobGwRfStatTxAcrStart,
                tmnxMobGwRfStatTxAcrInterim,
                tmnxMobGwRfStatTxAcrStop,
                tmnxMobGwRfStatTxAcrStartFails,
                tmnxMobGwRfStatTxAcrInterimFail,
                tmnxMobGwRfStatTxAcrStopFails,
                tmnxMobGwRfStatBearers,
                tmnxMobGwRfStatDefBearers,
                tmnxMobGwRfStatDedctdBearers,
                tmnxMobGwRfStatRoamers,
                tmnxMobGwRfStatBearersIpv4,
                tmnxMobGwRfStatBearersIpv6,
                tmnxMobGwRfStatBearersIpv4v6,
                tmnxMobGwRfStatActiveBearers,
                tmnxMobGwRfStatIdleBearers,
                tmnxMobGwS5StatUlBytes,
                tmnxMobGwS5StatDlBytes,
                tmnxMobGwS5StatUlPackets,
                tmnxMobGwS5StatDlPackets,
                tmnxMobGwS5StatBearers,
                tmnxMobGwS5StatModifyBearrCmd,
                tmnxMobGwS5StatModifyBearrFlr,
                tmnxMobGwS5StatDeleteBearrCmd,
                tmnxMobGwS5StatDeleteBearrFlr,
                tmnxMobGwS5StatBearrResCmd,
                tmnxMobGwS5StatBearrResFailInd,
                tmnxMobGwS5StatSuspNoticeReq,
                tmnxMobGwS5StatSuspNoticeAck,
                tmnxMobGwS5StatResumeNoticeReq,
                tmnxMobGwS5StatResumeNoticeAck,
                tmnxMobGwRfStatTxDpr,
                tmnxMobGwRfStatRxDpa,
                tmnxMobGwRfStatRxDwr,
                tmnxMobGwRfStatTxDwa
            }
    STATUS      current
    DESCRIPTION
        "The group of objects supporting management of the mobile gateway
         reference point statistics on the Alcatel-Lucent 7750 Mobile Gateway 
         systems in the 3.1 release."
    ::= { tmnxMobGatewayGroups 15 }

END
