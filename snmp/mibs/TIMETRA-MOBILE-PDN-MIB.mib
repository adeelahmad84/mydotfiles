--       TIMETRA MOBILE PDN
--       Management Information Base

TIMETRA-MOBILE-PDN-MIB DEFINITIONS ::= BEGIN

IMPORTS
   MODULE-IDENTITY, OBJECT-TYPE, Unsigned32, Counter32, Counter64, Gauge32
       FROM SNMPv2-SMI

   MODULE-COMPLIANCE, OBJECT-GROUP
       FROM SNMPv2-CONF

   RowStatus, TimeStamp, TruthValue, DisplayString
       FROM SNMPv2-TC

   InetAddress, InetAddressType, InetAddressPrefixLength, InetPortNumber
       FROM INET-ADDRESS-MIB

   InterfaceIndexOrZero
       FROM IF-MIB

   timetraSRMIBModules, tmnxSRObjs, tmnxSRConfs
       FROM TIMETRA-GLOBAL-MIB

   TmnxEnabledDisabled, TmnxVRtrID, TmnxAdminState, TmnxOperState,
   TItemDescription, TTcpUdpPort,TTcpUdpPortOperator, TNamedItemOrEmpty,
   TmnxEnabledDisabledOrInherit, TmnxCdrType, TmnxQosBytesHex, TNamedItem,
   TmnxCdrDiagnosticAction, TmnxBsxIsaAaGroupIndexOrZero
       FROM TIMETRA-TC-MIB

   TmnxMobProfName, TmnxMobProfNameOrEmpty, TmnxMobDiaRetryCount,
   TmnxMobDiaTransTimer, TmnxMobDiaPeerHost, TmnxMobNode,
   TmnxMobRtrAdvtInterval, TmnxMobRtrAdvtLifeTime, TmnxMobAddrScheme,
   TmnxMobApn, TmnxMobApnOrZero, TmnxMobChargingProfile, TmnxMobAuthType,
   TmnxMobAuthUserName, TmnxMobProfMbrRate, TmnxMobServerState,
   TmnxMobChargingBearerType, TmnxMobChargingLevel, TmnxMobImsi, TmnxMobMsisdn,
   TmnxMobImei, TmnxMobNai, TmnxMobMcc, TmnxMobMnc, TmnxMobUeState,
   TmnxMobUeRat, TmnxMobPdnType, TmnxMobPdnSessionState,
   TmnxMobPdnSessionEvent, TmnxMobPgwSigProtocol, TmnxMobBearerId,
   TmnxMobBearerType, TmnxMobQci, TmnxMobArp, TmnxMobSdf, TmnxMobSdfRuleName,
   TmnxMobSdfFilterDirection, TmnxMobSdfFilterProtocol,
   TmnxMobSdfFilter, TmnxMobSdfFilterNum,
   TmnxMobRfAcctLevel, TmnxMobIpCanType, TmnxMobStaticPolPrecedence,
   TmnxMobDiaPathMgmtState, TmnxMobDiaDetailPathMgmtState,
   TmnxMobDualStackPref, TmnxMobPeerType, TmnxMobGwId, TmnxMobPathMgmtState,
   TmnxMobChargingProfileOrInherit, TmnxMobUeSubType, TmnxMobQciValueOrZero, 
   TmnxMobArpValueOrZero, TmnxMobUeId, TmnxMobUeIdType, TmnxMobImsiStr, 
   TmnxMobRatingGrpState, TmnxMobPdnRefPointType, TmnxMobPresenceState, 
   TmnxMobPdnGyChrgTriggerType, TmnxMobAccessType, TmnxMobUeStrPrefix
       FROM TIMETRA-TC-MG-MIB

   tmnxChassisIndex, tmnxCardSlotNum, TmnxSlotNumOrZero
       FROM TIMETRA-CHASSIS-MIB

   vRtrID, vRtrIpPoolName
       FROM TIMETRA-VRTR-MIB

   tmnxMobGwId
       FROM TIMETRA-MOBILE-GATEWAY-MIB

   tmnxMobProfPolBaseName, tmnxMobProfDiaPeerName, tmnxMobProfDiaPeerListIndex,
   tmnxMobGtpPriGrpName, tmnxMobGtpPriServerIndex, tmnxMobProfRadGrpName, 
   tmnxMobProfRadPeerIndex, tmnxMobProfChgUnitRatingGroup,
   tmnxMobProfChgUnitServIdentifier
       FROM TIMETRA-MOBILE-PROFILE-MIB

   TmnxBsxAaGrpPartIndex
       FROM TIMETRA-BSX-NG-MIB

   ;

timetraMobPdnMIBModule    MODULE-IDENTITY
    LAST-UPDATED    "0912230000Z"
    ORGANIZATION    "Alcatel-Lucent"
    CONTACT-INFO
    "Alcatel-Lucent 7xxx Support
    Web: http://www.alcatel.com/comps/pages/carrier_support.jhtml"
    DESCRIPTION
    "This document is the SNMP MIB module to manage and provision
    the Packet Data Network Gateway (PGW).

    Copyright 2008-2014 Alcatel-Lucent. All rights reserved.
    Reproduction of this document is authorized on the condition that
    the foregoing copyright notice is included.

    This SNMP MIB module (Specification) embodies Alcatel-Lucent's
    proprietary intellectual property. Alcatel-Lucent retains all title and
    ownership in the Specification, including any revisions.

    Alcatel-Lucent grants all interested parties a non-exclusive
    license to use and distribute an unmodified copy of this
    Specification in connection with management of Alcatel-Lucent products,
    and without fee, provided this copyright notice and license appear
    on all copies.

    This Specification is supplied 'as is', and Alcatel-Lucent
    makes no warranty, either express or implied, as to the use,
    operation, condition, or performance of the Specification."

--
--  Revision History
--

    REVISION        "200912230000Z"
    DESCRIPTION     "Rev MG-1.0             23 Dec 2009 00:00
                     MG-1.0 release of the TIMETRA-MOBILE-PDN-MIB."

    ::= { timetraSRMIBModules 71 }

-- ----------------------------------------------------------------------------
--  Alcatel-Lucent 7xxx series MOBILE-PDN MIB structure
-- ----------------------------------------------------------------------------
tmnxMobPdn                OBJECT IDENTIFIER ::= { tmnxSRObjs 71 }
    tmnxMobPdnConfObjs          OBJECT IDENTIFIER ::= { tmnxMobPdn 1 }
    tmnxMobPdnStatObjs          OBJECT IDENTIFIER ::= { tmnxMobPdn 2 }
    tmnxMobPdnGlobalObjs        OBJECT IDENTIFIER ::= { tmnxMobPdn 3 }

tmnxMobPdnConformance     OBJECT IDENTIFIER ::= { tmnxSRConfs 71 }
    tmnxMobPdnCompliances       OBJECT IDENTIFIER ::=
                                            { tmnxMobPdnConformance 1 }
    tmnxMobPdnGroups            OBJECT IDENTIFIER ::=
                                            { tmnxMobPdnConformance 2 }

-- --------------------------
--  Mib objects
-- --------------------------

--
--  PDN gateway table
--

tmnxMobPdnTableLastChanged     OBJECT-TYPE
    SYNTAX      TimeStamp
    MAX-ACCESS  read-only
    STATUS      current
    DESCRIPTION
        "The value of tmnxMobPdnTableLastChanged indicates the sysUpTime at
         the time of the last modification to tmnxMobPdnTable by adding,
         deleting an entry or change to a writable object in the table.

         If no changes were made to the table since the last re-initialization
         of the local network management subsystem, then this object contains
         a zero value."
    ::= { tmnxMobPdnGlobalObjs 1 }

tmnxMobPdnTable  OBJECT-TYPE
    SYNTAX      SEQUENCE OF TmnxMobPdnEntry
    MAX-ACCESS  not-accessible
    STATUS      current
    DESCRIPTION
        "The tmnxMobPdnTable has an entry for each Packet Data Network
         Gateway (PGW) configured in the system."
    ::= { tmnxMobPdnConfObjs 1 }

tmnxMobPdnEntry  OBJECT-TYPE
    SYNTAX      TmnxMobPdnEntry
    MAX-ACCESS  not-accessible
    STATUS      current
    DESCRIPTION
        "Each row entry represents a Packet Data Network Gateway (PGW). An
         entry in this table is created by the agent itself when an entry is
         created in the tmnxMobGwTable with the value of tmnxMobGwType set
         to 'pgw'."
    INDEX { tmnxMobGwId }
    ::= { tmnxMobPdnTable 1 }

TmnxMobPdnEntry ::= SEQUENCE {
        tmnxMobPdnLastChanged              TimeStamp,
        tmnxMobPdnAdminState               TmnxAdminState,
        tmnxMobPdnOperState                TmnxOperState,
        tmnxMobPdnGracefulShutTimeout      Unsigned32,
        tmnxMobPdnMobNode                  TmnxMobNode,
        tmnxMobPdnPccDynamicState          TmnxEnabledDisabled,
        tmnxMobPdnPccPrecedenceBoundary    TmnxMobStaticPolPrecedence,
        tmnxMobPdnUplinkQciPolName         TmnxMobProfName,
        tmnxMobPdnDownlinkQciPolName       TmnxMobProfName,
        tmnxMobPdnHomePlmnList             TmnxMobProfNameOrEmpty,
        tmnxMobPdnVisitingPlmnList         TmnxMobProfNameOrEmpty,
        tmnxMobPdnBearerGtpuUdpChecksum    TmnxEnabledDisabled,
        tmnxMobPdnBearerGtpuSeqNumber      TmnxEnabledDisabled,
        tmnxMobPdnChargingProfHome         TmnxMobChargingProfile,
        tmnxMobPdnChargingProfVisiting     TmnxMobChargingProfile,
        tmnxMobPdnChargingProfRoaming      TmnxMobChargingProfile,
        tmnxMobPdnChrgCcIgnoreAny          TmnxEnabledDisabled,
        tmnxMobPdnChrgCcIgnoreHome         TmnxEnabledDisabled,
        tmnxMobPdnChrgCcIgnoreVisiting     TmnxEnabledDisabled,
        tmnxMobPdnChrgCcIgnoreRoaming      TmnxEnabledDisabled,
        tmnxMobPdnUmtsQosPolName           TmnxMobProfNameOrEmpty,
        tmnxMobPdnChrgCcReject             TruthValue,
        tmnxMobPdnChrgNodeId               DisplayString,
        tmnxMobPdnAaGroupIndex             TmnxBsxIsaAaGroupIndexOrZero,
        tmnxMobPdnAaGrpPartIndex           TmnxBsxAaGrpPartIndex,
        tmnxMobPdnCdrType                  TmnxCdrType,
        tmnxMobPdnHttpRedirect             TmnxMobProfNameOrEmpty,
        tmnxMobPdnDefAppProfile            TNamedItemOrEmpty,
        tmnxMobPdnChargingAvpDiag          TmnxCdrDiagnosticAction
    }

tmnxMobPdnLastChanged  OBJECT-TYPE
    SYNTAX      TimeStamp
    MAX-ACCESS  read-only
    STATUS      current
    DESCRIPTION
        "The value of tmnxMobPdnLastChanged indicates the timestamp of the last
         change to this row in tmnxMobPdnTable."
    ::= { tmnxMobPdnEntry 1 }

tmnxMobPdnAdminState  OBJECT-TYPE
    SYNTAX      TmnxAdminState
    MAX-ACCESS  read-write
    STATUS      current
    DESCRIPTION
        "The value of tmnxMobPdnAdminState specifies the desired administrative
         state of this Packet Data Network Gateway (PGW)."
    DEFVAL { outOfService }
    ::= { tmnxMobPdnEntry 2 }

tmnxMobPdnOperState  OBJECT-TYPE
    SYNTAX      TmnxOperState
    MAX-ACCESS  read-only
    STATUS      current
    DESCRIPTION
        "The value of tmnxMobPdnOperState indicates the current operational
         status of this Packet Data Network Gateway (PGW)."
    ::= { tmnxMobPdnEntry 3 }

tmnxMobPdnGracefulShutTimeout  OBJECT-TYPE
    SYNTAX      Unsigned32 (15..60)
    UNITS       "minutes"
    MAX-ACCESS  read-write
    STATUS      current
    DESCRIPTION
        "The value of tmnxMobPdnGracefulShutTimeout specifies the graceful
         shutdown time, in minutes. For graceful system shutdown, the existing
         request or connections are allowed to complete while no new
         requests or connections are accepted.

         This procedure is used to take the system to maintenance mode."
    DEFVAL { 30 }
    ::= { tmnxMobPdnEntry 4 }

tmnxMobPdnMobNode  OBJECT-TYPE
    SYNTAX      TmnxMobNode
    MAX-ACCESS  read-write
    STATUS      current
    DESCRIPTION
        "The value of tmnxMobPdnMobNode specifies the Packet Data Network
         Gateway (PGW) name."
    DEFVAL { ''H }
    ::= { tmnxMobPdnEntry 5 }

tmnxMobPdnPccDynamicState  OBJECT-TYPE
    SYNTAX      TmnxEnabledDisabled
    MAX-ACCESS  read-write
    STATUS      current
    DESCRIPTION
        "The value of tmnxMobPdnPccDynamicState specifies if interaction with
         Policy and Charging Rules Function (PCRF) is enabled for bearer
         creation or not. Policy and Charging Control (PCC) rules are pushed
         from PCRF for dedicated bearer creation."
    DEFVAL { disabled }
    ::= { tmnxMobPdnEntry 6 }

tmnxMobPdnPccPrecedenceBoundary  OBJECT-TYPE
    SYNTAX      TmnxMobStaticPolPrecedence
    MAX-ACCESS  read-write
    STATUS      current
    DESCRIPTION
        "The value of tmnxMobPdnPccPrecedenceBoundary specifies the boundary 
         value between dynamic and static Policy and Charging Control (PCC) rule
         precedence ranges."
    DEFVAL { 257 }
    ::= { tmnxMobPdnEntry 7 }

tmnxMobPdnUplinkQciPolName  OBJECT-TYPE
    SYNTAX      TmnxMobProfName
    MAX-ACCESS  read-write
    STATUS      current
    DESCRIPTION
        "The value of tmnxMobPdnUplinkQciPolName specifies the QoS Class
         Identifier (QCI) policy profile name for uplink direction.

         If a corresponding QCI policy profile does not exist in
         TIMETRA-MOBILE-PROFILE-MIB::tmnxMobProfQciPolTable,
         an 'inconsistentValue' error will be returned."
    DEFVAL { "default" }
    ::= { tmnxMobPdnEntry 8 }

tmnxMobPdnDownlinkQciPolName  OBJECT-TYPE
    SYNTAX      TmnxMobProfName
    MAX-ACCESS  read-write
    STATUS      current
    DESCRIPTION
        "The value of tmnxMobPdnDownlinkQciPolName specifies the QoS Class
         Identifier (QCI) policy profile name for downlink direction.

         If a corresponding QCI policy profile does not exist in
         TIMETRA-MOBILE-PROFILE-MIB::tmnxMobProfQciPolTable,
         an 'inconsistentValue' error will be returned."
    DEFVAL { "default" }
    ::= { tmnxMobPdnEntry 9 }

tmnxMobPdnHomePlmnList  OBJECT-TYPE
    SYNTAX      TmnxMobProfNameOrEmpty
    MAX-ACCESS  read-write
    STATUS      current
    DESCRIPTION
        "The value of tmnxMobPdnHomePlmnList specifies the Home Public Land
         Mobile Network (H-PLMN). H-PLMN is the PLMN the customer belongs to.
         A PLMN list consists of a list of Mobile Country Code (MCC) and Mobile
         Network Code (MNC) ids.

         If a corresponding PLMN does not exist in
         TIMETRA-MOBILE-PROFILE-MIB::tmnxMobProfPlmnListTable,
         an 'inconsistentValue' error will be returned."
    DEFVAL { ''H }
    ::= { tmnxMobPdnEntry 10 }

tmnxMobPdnVisitingPlmnList  OBJECT-TYPE
    SYNTAX      TmnxMobProfNameOrEmpty
    MAX-ACCESS  read-write
    STATUS      current
    DESCRIPTION
        "The value of tmnxMobPdnVisitingPlmnList specifies the Visiting Public
         Land Mobile Network (V-PLMN). A PLMN list consists of a list of
         Mobile Country Code (MCC) and Mobile Network Code (MNC) ids.

         If a corresponding PLMN does not exist in
         TIMETRA-MOBILE-PROFILE-MIB::tmnxMobProfPlmnListTable,
         an 'inconsistentValue' error will be returned."
    DEFVAL { ''H }
    ::= { tmnxMobPdnEntry 11 }

tmnxMobPdnBearerGtpuUdpChecksum  OBJECT-TYPE
    SYNTAX      TmnxEnabledDisabled
    MAX-ACCESS  read-write
    STATUS      current
    DESCRIPTION
        "The value of tmnxMobPdnBearerGtpuUdpChecksum specifies whether
         or not to validate the UDP checksum of GPRS Tunneling
         Protocol-User plane (GTP-U) packets.

         If the value of this object is set to 'enabled', the UDP
         checksum of the received GTP-U packets is verified and the
         packets which fail checksum verification are rejected.
         If the value of this object is set to 'disabled',
         the UDP checksum of the received GTP-U packets is not
         verified."
    DEFVAL { disabled }
    ::= { tmnxMobPdnEntry 12 }

tmnxMobPdnBearerGtpuSeqNumber  OBJECT-TYPE
    SYNTAX      TmnxEnabledDisabled
    MAX-ACCESS  read-write
    STATUS      current
    DESCRIPTION
        "The value of tmnxMobPdnBearerGtpuSeqNumber specifies whether
         or not to ignore the sequence number in the GPRS Tunneling
         Protocol-User plane (GTP-U) header.

         If the value of this object is set to 'enabled',
         GTP-U packets are reassembled based on the sequence number and
         complete packet are forwarded onto S5 or S8 interface. If the value
         of this object is set to 'disabled', the sequence number is
         ignored and complete packet is forwarded onto S5 or S8 interface."
    DEFVAL { disabled }
    ::= { tmnxMobPdnEntry 13 }

tmnxMobPdnChargingProfHome  OBJECT-TYPE
    SYNTAX      TmnxMobChargingProfile
    MAX-ACCESS  read-write
    STATUS      current
    DESCRIPTION
        "The value of tmnxMobPdnChargingProfHome specifies the charging 
         trigger rules applied for home subscribers.
         
         If a corresponding charging profile does not exist in
         TIMETRA-MOBILE-PROFILE-MIB::tmnxMobProfPgwChargingTable, 
         an 'inconsistentValue' error will be returned."
    DEFVAL { 0 }
    ::= { tmnxMobPdnEntry 15 }

tmnxMobPdnChargingProfVisiting  OBJECT-TYPE
    SYNTAX      TmnxMobChargingProfile
    MAX-ACCESS  read-write
    STATUS      current
    DESCRIPTION
        "The value of tmnxMobPdnChargingProfVisiting specifies the charging 
         trigger rules applied for visiting subscribers.
         
         If a corresponding charging profile does not exist in
         TIMETRA-MOBILE-PROFILE-MIB::tmnxMobProfPgwChargingTable, 
         an 'inconsistentValue' error will be returned."
    DEFVAL { 0 }
    ::= { tmnxMobPdnEntry 16 }

tmnxMobPdnChargingProfRoaming  OBJECT-TYPE
    SYNTAX      TmnxMobChargingProfile
    MAX-ACCESS  read-write
    STATUS      current
    DESCRIPTION
        "The value of tmnxMobPdnChargingProfRoaming specifies the charging 
         trigger rules applied for roaming subscribers.
         
         If a corresponding charging profile does not exist in
         TIMETRA-MOBILE-PROFILE-MIB::tmnxMobProfPgwChargingTable, 
         an 'inconsistentValue' error will be returned."
    DEFVAL { 0 }
    ::= { tmnxMobPdnEntry 17 }

tmnxMobPdnChrgCcIgnoreAny  OBJECT-TYPE
    SYNTAX      TmnxEnabledDisabled
    MAX-ACCESS  read-write
    STATUS      current
    DESCRIPTION
        "The value of tmnxMobPdnChrgCcIgnoreAny specifies to ignore 
         HSS or MME supplied charging characteristics for any subscriber. 
         Corresponding default profile is selected when the received charging 
         characteristics is ignored."
    DEFVAL { disabled }
    ::= { tmnxMobPdnEntry 18 }

tmnxMobPdnChrgCcIgnoreHome  OBJECT-TYPE
    SYNTAX      TmnxEnabledDisabled
    MAX-ACCESS  read-write
    STATUS      current
    DESCRIPTION
        "The value of tmnxMobPdnChrgCcIgnoreHome specifies to ignore HSS or MME 
         supplied charging characteristics for home scenarios. Corresponding 
         default profile is selected when the received charging characteristics
         is ignored."
    DEFVAL { disabled }
    ::= { tmnxMobPdnEntry 19 }

tmnxMobPdnChrgCcIgnoreVisiting  OBJECT-TYPE
    SYNTAX      TmnxEnabledDisabled
    MAX-ACCESS  read-write
    STATUS      current
    DESCRIPTION
        "The value of tmnxMobPdnChrgCcIgnoreVisiting specifies to ignore 
         HSS or MME supplied charging characteristics for visiting scenarios. 
         Corresponding default profile is selected when the received charging 
         characteristics is ignored."
    DEFVAL { disabled }
    ::= { tmnxMobPdnEntry 20 }

tmnxMobPdnChrgCcIgnoreRoaming  OBJECT-TYPE
    SYNTAX      TmnxEnabledDisabled
    MAX-ACCESS  read-write
    STATUS      current
    DESCRIPTION
        "The value of tmnxMobPdnChrgCcIgnoreRoaming specifies to ignore 
         HSS or MME supplied charging characteristics for roaming scenarios. 
         Corresponding default profile is selected when the received charging 
         characteristics is ignored."
    DEFVAL { disabled }
    ::= { tmnxMobPdnEntry 21 }

tmnxMobPdnUmtsQosPolName  OBJECT-TYPE
    SYNTAX      TmnxMobProfNameOrEmpty 
    MAX-ACCESS  read-write
    STATUS      current
    DESCRIPTION
        "The value of tmnxMobPdnUmtsQosPolName specifies the name of Universal
         Mobile Telecommunications System (UMTS) Quality of Service (QoS)
         Policy.

         If a corresponding UMTS QoS policy profile does not exist in
         TIMETRA-MOBILE-PROFILE-MIB::tmnxMobUmtsQosPolTable,
         an 'inconsistentValue' error will be returned. 

         If the mapping between pre-Rel-8 QoS parameter value pairs and QoS 
         Class Identifier (QCI) values is not 1-to-1 for this UMTS Qos Policy,
         an 'inconsistentValue' error will be returned."
    DEFVAL { ''H }
    ::= { tmnxMobPdnEntry 22 }

tmnxMobPdnChrgCcReject  OBJECT-TYPE
    SYNTAX      TruthValue
    MAX-ACCESS  read-write
    STATUS      current
    DESCRIPTION
        "The value of tmnxMobPdnChrgCcReject specifies to reject HSS or MME
         supplied charging characteristics for a subscriber. 
         Corresponding default charging profile is selected when the value of 
         this object is set to 'false'.

         The value of tmnxMobPdnChrgCcReject is applicable only when the HSS
         or MME supplied charging characteristics are not ignored."        
    DEFVAL { false }
    ::= { tmnxMobPdnEntry 23 }

tmnxMobPdnChrgNodeId  OBJECT-TYPE
    SYNTAX      DisplayString (SIZE (0..20))
    MAX-ACCESS  read-write
    STATUS      current
    DESCRIPTION
        "The value of tmnxMobPdnChrgNodeId specifies an operator configurable 
         identifier for the node which is used over the Rf reference point or
         the Ga reference point.

         When a node-id is used in Charging Data Records (CDR) sent through a Ga 
         reference point, only the first 18 characters are used.
        
         The value of tmnxMobPdnChrgNodeId for the Rf reference point is 
         applicable only when the value of tmnxMobPdnRfNodeId is not specified."
    DEFVAL { ''H }
    ::= { tmnxMobPdnEntry 24 }    

tmnxMobPdnAaGroupIndex    OBJECT-TYPE
    SYNTAX      TmnxBsxIsaAaGroupIndexOrZero
    MAX-ACCESS  read-write
    STATUS      current
    DESCRIPTION
        "The value of tmnxMobPdnAaGroupIndex specifies the
         group number of this group of BSX MDAs at the gateway level.

         The corresponding row for the AA group must have already been created
         in the TIMETRA-BSX-NG-MIB::tmnxBsxIsaAaGrpTable.
         
         The value of zero indicates that no BSX MDA group is specified."
    DEFVAL { 0 }
    ::= { tmnxMobPdnEntry 25 }

tmnxMobPdnAaGrpPartIndex    OBJECT-TYPE
    SYNTAX      TmnxBsxAaGrpPartIndex
    MAX-ACCESS  read-write
    STATUS      current
    DESCRIPTION
        "The value of tmnxMobPdnAaGrpPartIndex specifies the
         partition index within an AA group at the gateway level.

         The corresponding row for the partition index must have already been
         created in the 
         TIMETRA-BSX-NG-MIB::tmnxBsxAaGrpPartTable.
         
         The value of zero indicates that no Application Assurance partition is
         specified."
    DEFVAL { 0 }
    ::= { tmnxMobPdnEntry 26 }

tmnxMobPdnCdrType    OBJECT-TYPE
    SYNTAX      TmnxCdrType
    MAX-ACCESS  read-write
    STATUS      current
    DESCRIPTION
        "The value of tmnxMobPdnCdrType specifies the type of 
         Charging Data Records (CDRs) in the system."
    DEFVAL { pgwCdr }
    ::= { tmnxMobPdnEntry 27 }

tmnxMobPdnHttpRedirect  OBJECT-TYPE
    SYNTAX      TmnxMobProfNameOrEmpty 
    MAX-ACCESS  read-write
    STATUS      current
    DESCRIPTION
        "The value of tmnxMobPdnHttpRedirect specifies the http redirect 
         rule on this Packet data network Gateway (PGW)"
    DEFVAL { ''H }
    ::= { tmnxMobPdnEntry 28 }

tmnxMobPdnDefAppProfile OBJECT-TYPE
    SYNTAX        TNamedItemOrEmpty
    MAX-ACCESS    read-write
    STATUS        current
    DESCRIPTION 
        "The value of tmnxMobPdnDefAppProfile specifies the value of default
         application profile being applied at the Packet Data Network Gateway
         (PGW)."
    DEFVAL { ''H }
    ::= { tmnxMobPdnEntry 29 }

tmnxMobPdnChargingAvpDiag    OBJECT-TYPE
    SYNTAX      TmnxCdrDiagnosticAction
    MAX-ACCESS  read-write
    STATUS      current
    DESCRIPTION
        "The value of tmnxMobPdnChargingAvpDiag specifies whether the 
         Diagnostics should be included or excluded in the Charging Data
         Record (CDR)."
    DEFVAL { included }
    ::= { tmnxMobPdnEntry 30 }

--
--  Signaling table
--

tmnxMobPdnSigTableLastChanged  OBJECT-TYPE
    SYNTAX      TimeStamp
    MAX-ACCESS  read-only
    STATUS      current
    DESCRIPTION
        "The value of tmnxMobPdnSigTableLastChanged indicates the sysUpTime at
         the time of the last modification to tmnxMobPdnSigTable by adding,
         deleting an entry or change to a writable object in the table.

         If no changes were made to the table since the last re-initialization
         of the local network management subsystem, then this object contains
         a zero value."
    ::= { tmnxMobPdnGlobalObjs 2 }

tmnxMobPdnSigTable  OBJECT-TYPE
    SYNTAX      SEQUENCE OF TmnxMobPdnSigEntry
    MAX-ACCESS  not-accessible
    STATUS      current
    DESCRIPTION
        "The tmnxMobPdnSigTable provides an extension of the tmnxMobPdnTable
         for signaling configuration."
    ::= { tmnxMobPdnConfObjs 2 }

tmnxMobPdnSigEntry  OBJECT-TYPE
    SYNTAX      TmnxMobPdnSigEntry
    MAX-ACCESS  not-accessible
    STATUS      current
    DESCRIPTION
        "Each row entry represents additional columns for signaling
         configuration for a Packet Data Network Gateway (PGW)."
    AUGMENTS { tmnxMobPdnEntry }
    ::= { tmnxMobPdnSigTable 1 }

TmnxMobPdnSigEntry ::= SEQUENCE {
        tmnxMobPdnSigLastChanged         TimeStamp,
        tmnxMobPdnSigGtpcProfile         TmnxMobProfName,
        tmnxMobPdnSigGtpuProfile         TmnxMobProfName,
        tmnxMobPdnSigPmipv6Profile       TmnxMobProfName,
        tmnxMobPdnSigPmipv6RtrAdIntvl    TmnxMobRtrAdvtInterval,
        tmnxMobPdnSigPmipv6RtrAdLife     TmnxMobRtrAdvtLifeTime,
        tmnxMobPdnSigPmipv6AddrScheme    TmnxMobAddrScheme,
        tmnxMobPdnSigDiaProfile          TmnxMobProfName,
        tmnxMobPdnSigDiaOriginRealm      TmnxMobDiaPeerHost,
        tmnxMobPdnSigDiaOriginHost       TmnxMobDiaPeerHost,
        tmnxMobPdnSigDefaultIfVRtrId     TmnxVRtrID,
        tmnxMobPdnSigDefaultIfIndex      InterfaceIndexOrZero,
        tmnxMobPdnSigMIP6AgntInfType     INTEGER,
        tmnxMobPdnSigMIP6AgntInfFqdnType InetAddressType,
        tmnxMobPdnSigMIP6AgntInfFqdn     InetAddress,
        tmnxMobPdnSigMIP6AgntInfRealm    TmnxMobDiaPeerHost
    }

tmnxMobPdnSigLastChanged  OBJECT-TYPE
    SYNTAX      TimeStamp
    MAX-ACCESS  read-only
    STATUS      current
    DESCRIPTION
        "The value of tmnxMobPdnSigLastChanged indicates the timestamp of
         the last change to this row in tmnxMobPdnSigTable."
    ::= { tmnxMobPdnSigEntry 1 }

tmnxMobPdnSigGtpcProfile  OBJECT-TYPE
    SYNTAX      TmnxMobProfName
    MAX-ACCESS  read-write
    STATUS      current
    DESCRIPTION
        "The value of tmnxMobPdnSigGtpcProfile specifies the GPRS Tunneling
         Protocol-Control plane (GTP-C) profile name. The GTP-C profile provides
         GTP-C signaling related configuration.

         If a corresponding GTP profile does not exist in
         TIMETRA-MOBILE-PROFILE-MIB::tmnxMobProfGtpTable,
         an 'inconsistentValue' error will be returned."
    DEFVAL { "default" }
    ::= { tmnxMobPdnSigEntry 2 }

tmnxMobPdnSigGtpuProfile  OBJECT-TYPE
    SYNTAX      TmnxMobProfName
    MAX-ACCESS  read-write
    STATUS      current
    DESCRIPTION
        "The value of tmnxMobPdnSigGtpuProfile specifies the GPRS Tunneling
         Protocol-User plane (GTP-U) profile name. The GTP-U profile provides
         GTP-U signaling related configuration.

         If a corresponding GTP profile does not exist in
         TIMETRA-MOBILE-PROFILE-MIB::tmnxMobProfGtpTable,
         an 'inconsistentValue' error will be returned."
    DEFVAL { "default" }
    ::= { tmnxMobPdnSigEntry 3 }

tmnxMobPdnSigPmipv6Profile  OBJECT-TYPE
    SYNTAX      TmnxMobProfName
    MAX-ACCESS  read-write
    STATUS      current
    DESCRIPTION
        "The value of tmnxMobPdnSigPmipv6Profile specifies the Proxy Mobile
         IPv6 (PMIPv6) profile name. The PMIPv6 profile provides protocol
         related information applicable to PMIPv6 peers.

         If a corresponding PMIPv6 profile does not exist in
         TIMETRA-MOBILE-PROFILE-MIB::tmnxMobProfPmipv6Table,
         an 'inconsistentValue' error will be returned."
    DEFVAL { "default" }
    ::= { tmnxMobPdnSigEntry 4 }

tmnxMobPdnSigPmipv6RtrAdIntvl  OBJECT-TYPE
    SYNTAX      TmnxMobRtrAdvtInterval
    UNITS       "minutes"
    MAX-ACCESS  read-write
    STATUS      current
    DESCRIPTION
        "The value of tmnxMobPdnSigPmipv6RtrAdIntvl specifies the router
         advertisement interval. The Packet Data Network Gateway (PGW)
         advertises IPv6 prefixes to the User Equipments (UEs) at router
         advertisement interval."
    DEFVAL { 30 }
    ::= { tmnxMobPdnSigEntry 5 }

tmnxMobPdnSigPmipv6RtrAdLife  OBJECT-TYPE
    SYNTAX      TmnxMobRtrAdvtLifeTime
    UNITS       "hours"
    MAX-ACCESS  read-write
    STATUS      current
    DESCRIPTION
        "The value of tmnxMobPdnSigPmipv6RtrAdLife specifies the router
         advertisement life time. It specifies the validity of the IPv6 prefix
         advertised from the Packet Data Network Gateway (PGW) to the User
         Equipments (UEs)."
    DEFVAL { 12 }
    ::= { tmnxMobPdnSigEntry 6 }

tmnxMobPdnSigPmipv6AddrScheme  OBJECT-TYPE
    SYNTAX      TmnxMobAddrScheme
    MAX-ACCESS  read-write
    STATUS      current
    DESCRIPTION
        "The value of tmnxMobPdnSigPmipv6AddrScheme specifies the addressing
         scheme. If the value is set to 'stateful', the User Equipment (UE) uses
         DHCPv6 to get IPv6 address. If the value is set to 'stateless', the UE
         uses ICMPv6 to get IPv6 address."
    DEFVAL { stateless }
    ::= { tmnxMobPdnSigEntry 7 }

tmnxMobPdnSigDiaProfile  OBJECT-TYPE
    SYNTAX      TmnxMobProfName
    MAX-ACCESS  read-write
    STATUS      current
    DESCRIPTION
        "The value of tmnxMobPdnSigDiaProfile specifies the diameter profile
         name. Diameter profile provides diameter connection related
         information.

         If a corresponding diameter profile does not exist in
         TIMETRA-MOBILE-PROFILE-MIB::tmnxMobProfDiaTable,
         an 'inconsistentValue' error will be returned."
    DEFVAL { "default" }
    ::= { tmnxMobPdnSigEntry 8 }

tmnxMobPdnSigDiaOriginRealm  OBJECT-TYPE
    SYNTAX      TmnxMobDiaPeerHost
    MAX-ACCESS  read-write
    STATUS      current
    DESCRIPTION
        "The value of tmnxMobPdnSigDiaOriginRealm specifies the originating
         realm or domain name of a Diameter node. The Originating Realm is
         included in messages exchanged with a Diameter peer."
    DEFVAL { ''H }
    ::= { tmnxMobPdnSigEntry 9 }

tmnxMobPdnSigDiaOriginHost  OBJECT-TYPE
    SYNTAX      TmnxMobDiaPeerHost
    MAX-ACCESS  read-write
    STATUS      current
    DESCRIPTION
        "The value of tmnxMobPdnSigDiaOriginHost specifies the originating
         host name of a Diameter node. The originating host information is sent
         in requests to a Diameter peer."
    DEFVAL { ''H }
    ::= { tmnxMobPdnSigEntry 10 }

tmnxMobPdnSigDefaultIfVRtrId  OBJECT-TYPE
    SYNTAX      TmnxVRtrID
    MAX-ACCESS  read-write
    STATUS      current
    DESCRIPTION
        "The value of tmnxMobPdnSigDefaultIfVRtrId specifies the virtual
         router to which the default signaling interface specified by
         tmnxMobPdnSigDefaultIfIndex belongs."
    DEFVAL { 1 }
    ::= { tmnxMobPdnSigEntry 11 }

tmnxMobPdnSigDefaultIfIndex  OBJECT-TYPE
    SYNTAX      InterfaceIndexOrZero
    MAX-ACCESS  read-write
    STATUS      current
    DESCRIPTION
        "The value of tmnxMobPdnSigDefaultIfIndex specifies the interface
         index of the default interface used by the signaling protocols.
         When the value of this object is set to 0, no default interface has
         been assigned."
    DEFVAL { 0 }
    ::= { tmnxMobPdnSigEntry 12 }

tmnxMobPdnSigMIP6AgntInfType   OBJECT-TYPE
    SYNTAX     INTEGER
                {
                        ipAddr  (1),
                        fqdn    (2)
                }
    MAX-ACCESS  read-write
    STATUS      current
    DESCRIPTION
        "The value of tmnxMobPdnSigMIP6AgntInfType indicates if the s6b reference point
         uses Fully Qualified Domain Name (FQDN) or use the IP address of the Packet Data
         Network Gateway (PGW) signaling endpoint."
    DEFVAL { ipAddr }
    ::= { tmnxMobPdnSigEntry 13 }

tmnxMobPdnSigMIP6AgntInfFqdnType  OBJECT-TYPE
    SYNTAX      InetAddressType
    MAX-ACCESS  read-write
    STATUS      current
    DESCRIPTION 
        "The value of tmnxMobPdnSigMIP6AgntInfFqdnType specifies the type of
         address represented by tmnxMobPdnSigMIP6AgntInfFqdn."
     DEFVAL  { unknown }
    ::= { tmnxMobPdnSigEntry 14 }

tmnxMobPdnSigMIP6AgntInfFqdn  OBJECT-TYPE 
    SYNTAX       InetAddress
    MAX-ACCESS   read-write
    STATUS       current
    DESCRIPTION
        "The value of tmnxMobPdnSigMIP6AgntInfFqdn specifies the value of Fully
         Qualified Domain Name (FQDN) used by the Packet Data Network Gateway (PGW)
         s6b reference point during User Equipment (UE) attach procedure.

         This object is restricted to hold only a Fully Qualified Domain Name (FQDN)
         value."
     DEFVAL { ''H }
    ::= { tmnxMobPdnSigEntry 15 }

tmnxMobPdnSigMIP6AgntInfRealm  OBJECT-TYPE        
    SYNTAX      TmnxMobDiaPeerHost
    MAX-ACCESS  read-write
    STATUS      current
    DESCRIPTION
        "The value of tmnxMobPdnSigMIP6AgntInfRealm specifies the destination or
         the domain name of the Packet Data Network Gateway (PGW) Fully Qualified
         Domain Name (FQDN). This value will be included in the  diameter
         authentication messages."
    DEFVAL { ''H }
    ::= { tmnxMobPdnSigEntry 16 }

--
--  Gx table
--

tmnxMobPdnGxTableLastChanged  OBJECT-TYPE
    SYNTAX      TimeStamp
    MAX-ACCESS  read-only
    STATUS      current
    DESCRIPTION
        "The value of tmnxMobPdnGxTableLastChanged indicates the sysUpTime at
         the time of the last modification to tmnxMobPdnGxTable by adding,
         deleting an entry or change to a writable object in the table.

         If no changes were made to the table since the last re-initialization
         of the local network management subsystem, then this object contains
         a zero value."
    ::= { tmnxMobPdnGlobalObjs 3 }

tmnxMobPdnGxTable  OBJECT-TYPE
    SYNTAX      SEQUENCE OF TmnxMobPdnGxEntry
    MAX-ACCESS  not-accessible
    STATUS      current
    DESCRIPTION
        "The tmnxMobPdnGxTable provides an extension of the tmnxMobPdnTable
         for Gx reference point configuration."
    ::= { tmnxMobPdnConfObjs 3 }

tmnxMobPdnGxEntry  OBJECT-TYPE
    SYNTAX      TmnxMobPdnGxEntry
    MAX-ACCESS  not-accessible
    STATUS      current
    DESCRIPTION
        "Each row entry represents additional columns for Gx reference point
         configuration for a Packet Data Network Gateway (PGW)."
    AUGMENTS { tmnxMobPdnEntry }
    ::= { tmnxMobPdnGxTable 1 }

TmnxMobPdnGxEntry ::= SEQUENCE {
        tmnxMobPdnGxLastChanged           TimeStamp,
        tmnxMobPdnGxDiaIfVRtrId           TmnxVRtrID,
        tmnxMobPdnGxDiaIfIndex            InterfaceIndexOrZero,
        tmnxMobPdnGxDiaTransTimer         TmnxMobDiaTransTimer,
        tmnxMobPdnGxDiaRetryCount         TmnxMobDiaRetryCount,
        tmnxMobPdnGxDefPriDiaPeer         TmnxMobProfNameOrEmpty,
        tmnxMobPdnGxDefSecDiaPeer         TmnxMobProfNameOrEmpty
    }

tmnxMobPdnGxLastChanged  OBJECT-TYPE
    SYNTAX      TimeStamp
    MAX-ACCESS  read-only
    STATUS      current
    DESCRIPTION
        "The value of tmnxMobPdnGxLastChanged indicates the timestamp of
         the last change to this row in tmnxMobPdnGxTable."
    ::= { tmnxMobPdnGxEntry 1 }

tmnxMobPdnGxDiaIfVRtrId  OBJECT-TYPE
    SYNTAX      TmnxVRtrID
    MAX-ACCESS  read-write
    STATUS      current
    DESCRIPTION
        "The value of tmnxMobPdnGxDiaIfVRtrId specifies the virtual
         router to which the interface specified by tmnxMobPdnGxDiaIfIndex
         belongs."
    DEFVAL { 1 }
    ::= { tmnxMobPdnGxEntry 2 }

tmnxMobPdnGxDiaIfIndex  OBJECT-TYPE
    SYNTAX      InterfaceIndexOrZero
    MAX-ACCESS  read-write
    STATUS      current
    DESCRIPTION
        "The value of tmnxMobPdnGxDiaIfIndex specifies the interface
         index of the local interface used for the diameter connection.
         When the value of this object is set to 0, no interface has
         been assigned."
    DEFVAL { 0 }
    ::= { tmnxMobPdnGxEntry 3 }

tmnxMobPdnGxDiaTransTimer  OBJECT-TYPE
    SYNTAX      TmnxMobDiaTransTimer
    MAX-ACCESS  read-write
    STATUS      current
    DESCRIPTION
        "The value of tmnxMobPdnGxDiaTransTimer specifies the maximum
         amount of time the node waits for a diameter peer to respond before
         trying another peer."
    DEFVAL { 5 }
    ::= { tmnxMobPdnGxEntry 4 }

tmnxMobPdnGxDiaRetryCount  OBJECT-TYPE
    SYNTAX      TmnxMobDiaRetryCount
    UNITS       "seconds"
    MAX-ACCESS  read-write
    STATUS      current
    DESCRIPTION
        "The value of tmnxMobPdnGxDiaRetryCount specifies the number of times
         the same message is re-tried before declaring a failed attempt."
    DEFVAL { 3 }
    ::= { tmnxMobPdnGxEntry 5 }

tmnxMobPdnGxDefPriDiaPeer  OBJECT-TYPE
    SYNTAX      TmnxMobProfNameOrEmpty
    MAX-ACCESS  read-write
    STATUS      current
    DESCRIPTION
        "The value of tmnxMobPdnGxDefPriDiaPeer specifies the default primary
         diameter peer profile name.

         If a corresponding diameter peer profile does not exist in
         TIMETRA-MOBILE-PROFILE-MIB::tmnxMobProfDiaPeerTable,
         an 'inconsistentValue' error will be returned."
    DEFVAL { ''H }
    ::= { tmnxMobPdnGxEntry 6 }

tmnxMobPdnGxDefSecDiaPeer  OBJECT-TYPE
    SYNTAX      TmnxMobProfNameOrEmpty
    MAX-ACCESS  read-write
    STATUS      current
    DESCRIPTION
        "The value of tmnxMobPdnGxDefSecDiaPeer specifies the default
         secondary diameter peer profile name.

         If a corresponding diameter peer profile does not exist in
         TIMETRA-MOBILE-PROFILE-MIB::tmnxMobProfDiaPeerTable,
         an 'inconsistentValue' error will be returned."
    DEFVAL { ''H }
    ::= { tmnxMobPdnGxEntry 7 }

--
--  S5 table
--

tmnxMobPdnS5TableLastChanged  OBJECT-TYPE
    SYNTAX      TimeStamp
    MAX-ACCESS  read-only
    STATUS      current
    DESCRIPTION
        "The value of tmnxMobPdnS5TableLastChanged indicates the sysUpTime at
         the time of the last modification to tmnxMobPdnS5Table by adding,
         deleting an entry or change to a writable object in the table.

         If no changes were made to the table since the last re-initialization
         of the local network management subsystem, then this object contains
         a zero value."
    ::= { tmnxMobPdnGlobalObjs 4 }

tmnxMobPdnS5Table  OBJECT-TYPE
    SYNTAX      SEQUENCE OF TmnxMobPdnS5Entry
    MAX-ACCESS  not-accessible
    STATUS      current
    DESCRIPTION
        "The tmnxMobPdnS5Table provides an extension of the tmnxMobPdnTable
         for S5 reference point configuration."
    ::= { tmnxMobPdnConfObjs 4 }

tmnxMobPdnS5Entry  OBJECT-TYPE
    SYNTAX      TmnxMobPdnS5Entry
    MAX-ACCESS  not-accessible
    STATUS      current
    DESCRIPTION
        "Each row entry represents additional columns for S5 reference point
         configuration for a Packet Data Network Gateway (PGW)."
    AUGMENTS { tmnxMobPdnEntry }
    ::= { tmnxMobPdnS5Table 1 }

TmnxMobPdnS5Entry ::= SEQUENCE {
        tmnxMobPdnS5LastChanged        TimeStamp,
        tmnxMobPdnS5PeerList           TmnxMobProfNameOrEmpty,
        tmnxMobPdnS5GtpcIfVRtrId       TmnxVRtrID,
        tmnxMobPdnS5GtpcIfIndex        InterfaceIndexOrZero,
        tmnxMobPdnS5GtpuIfVRtrId       TmnxVRtrID,
        tmnxMobPdnS5GtpuIfIndex        InterfaceIndexOrZero,
        tmnxMobPdnS5GtpcProfile        TmnxMobProfNameOrEmpty,
        tmnxMobPdnS5GtpuProfile        TmnxMobProfNameOrEmpty,
        tmnxMobPdnS5DualStackPref      TmnxMobDualStackPref
    }

tmnxMobPdnS5LastChanged  OBJECT-TYPE
    SYNTAX      TimeStamp
    MAX-ACCESS  read-only
    STATUS      current
    DESCRIPTION
        "The value of tmnxMobPdnS5LastChanged indicates the timestamp of
         the last change to this row in tmnxMobPdnS5Table."
    ::= { tmnxMobPdnS5Entry 1 }

tmnxMobPdnS5PeerList  OBJECT-TYPE
    SYNTAX      TmnxMobProfNameOrEmpty
    MAX-ACCESS  read-write
    STATUS      current
    DESCRIPTION
        "The value of tmnxMobPdnS5PeerList specifies the peer list name.

         If a corresponding  peer does not exist in
         TIMETRA-MOBILE-PROFILE-MIB::tmnxMobProfPeerListTable,
         an 'inconsistentValue' error will be returned."
    DEFVAL { ''H }
    ::= { tmnxMobPdnS5Entry 2 }

tmnxMobPdnS5GtpcIfVRtrId  OBJECT-TYPE
    SYNTAX      TmnxVRtrID
    MAX-ACCESS  read-write
    STATUS      current
    DESCRIPTION
        "The value of tmnxMobPdnS5GtpcIfVRtrId specifies the virtual
         router to which the interface specified by tmnxMobPdnS5GtpcIfIndex
         belongs."
    DEFVAL { 1 }
    ::= { tmnxMobPdnS5Entry 3 }

tmnxMobPdnS5GtpcIfIndex  OBJECT-TYPE
    SYNTAX      InterfaceIndexOrZero
    MAX-ACCESS  read-write
    STATUS      current
    DESCRIPTION
        "The value of tmnxMobPdnS5GtpcIfIndex specifies the interface
         index of the local interface used for the General Packet Radio
         Services Tunneling Protocol for Control Plane (GTP-C) signaling.
         When the value of this object is set to 0, no interface has
         been assigned.    
    
         If value of this object is not set then the value of  
         tmnxMobServSigDefaultIfIndex is used."
    DEFVAL { 0 }
    ::= { tmnxMobPdnS5Entry 4 }

tmnxMobPdnS5GtpuIfVRtrId  OBJECT-TYPE
    SYNTAX      TmnxVRtrID
    MAX-ACCESS  read-write
    STATUS      current
    DESCRIPTION
        "The value of tmnxMobPdnS5GtpuIfVRtrId specifies the virtual
         router to which the interface specified by tmnxMobPdnS5GtpuIfIndex
         belongs."
    DEFVAL { 1 }
    ::= { tmnxMobPdnS5Entry 5 }

tmnxMobPdnS5GtpuIfIndex  OBJECT-TYPE
    SYNTAX      InterfaceIndexOrZero
    MAX-ACCESS  read-write
    STATUS      current
    DESCRIPTION
        "The value of tmnxMobPdnS5GtpuIfIndex specifies the interface
         index of the local interface used for the General Packet Radio
         Services Tunneling Protocol for User Plane (GTP-U) signaling.
         When the value of this object is set to 0, no interface has
         been assigned.
         
         If value of this object is not set then the value of  
         tmnxMobServSigDefaultIfIndex is used."
    DEFVAL { 0 }
    ::= { tmnxMobPdnS5Entry 6 }

tmnxMobPdnS5GtpcProfile  OBJECT-TYPE
    SYNTAX      TmnxMobProfNameOrEmpty
    MAX-ACCESS  read-write
    STATUS      current
    DESCRIPTION
        "The value of tmnxMobPdnS5GtpcProfile specifies the GPRS Tunneling
         Protocol-Control plane (GTP-C) profile name. The GTP-C profile provides
         GTP-C signaling related configuration.

         If a corresponding GTP profile does not exist in
         TIMETRA-MOBILE-PROFILE-MIB::tmnxMobProfGtpTable,
         an 'inconsistentValue' error will be returned."
    DEFVAL { ''H }
    ::= { tmnxMobPdnS5Entry 7 }

tmnxMobPdnS5GtpuProfile  OBJECT-TYPE
    SYNTAX      TmnxMobProfNameOrEmpty
    MAX-ACCESS  read-write
    STATUS      current
    DESCRIPTION
        "The value of tmnxMobPdnS5GtpuProfile specifies the GPRS Tunneling
         Protocol-User plane (GTP-U) profile name. The GTP-U profile provides
         GTP-U signaling related configuration.

         If a corresponding GTP profile does not exist in
         TIMETRA-MOBILE-PROFILE-MIB::tmnxMobProfGtpTable,
         an 'inconsistentValue' error will be returned."
    DEFVAL { ''H }
    ::= { tmnxMobPdnS5Entry 8 }

tmnxMobPdnS5DualStackPref  OBJECT-TYPE
    SYNTAX      TmnxMobDualStackPref
    MAX-ACCESS  read-write
    STATUS      current
    DESCRIPTION
        "The value of tmnxMobPdnS5DualStackPref specifies the preference in a
         dual stack when both IPv4 and IPv6 addresses are configured for the
         S5 interface."
    DEFVAL { useCplane }
    ::= { tmnxMobPdnS5Entry 9 }

--
--  S8 table
--

tmnxMobPdnS8TableLastChanged  OBJECT-TYPE
    SYNTAX      TimeStamp
    MAX-ACCESS  read-only
    STATUS      current
    DESCRIPTION
        "The value of tmnxMobPdnS8TableLastChanged indicates the sysUpTime at
         the time of the last modification to tmnxMobPdnS8Table by adding,
         deleting an entry or change to a writable object in the table.

         If no changes were made to the table since the last re-initialization
         of the local network management subsystem, then this object contains
         a zero value."
    ::= { tmnxMobPdnGlobalObjs 5 }

tmnxMobPdnS8Table  OBJECT-TYPE
    SYNTAX      SEQUENCE OF TmnxMobPdnS8Entry
    MAX-ACCESS  not-accessible
    STATUS      current
    DESCRIPTION
        "The tmnxMobPdnS8Table provides an extension of the tmnxMobPdnTable
         for S8 reference point configuration."
    ::= { tmnxMobPdnConfObjs 5 }

tmnxMobPdnS8Entry  OBJECT-TYPE
    SYNTAX      TmnxMobPdnS8Entry
    MAX-ACCESS  not-accessible
    STATUS      current
    DESCRIPTION
        "Each row entry represents additional columns for S8 reference point
         configuration for a Packet Data Network Gateway (PGW)."
    AUGMENTS { tmnxMobPdnEntry }
    ::= { tmnxMobPdnS8Table 1 }

TmnxMobPdnS8Entry ::= SEQUENCE {
        tmnxMobPdnS8LastChanged        TimeStamp,
        tmnxMobPdnS8PeerList           TmnxMobProfNameOrEmpty,
        tmnxMobPdnS8GtpcIfVRtrId       TmnxVRtrID,
        tmnxMobPdnS8GtpcIfIndex        InterfaceIndexOrZero,
        tmnxMobPdnS8GtpuIfVRtrId       TmnxVRtrID,
        tmnxMobPdnS8GtpuIfIndex        InterfaceIndexOrZero,
        tmnxMobPdnS8GtpcProfile        TmnxMobProfNameOrEmpty,
        tmnxMobPdnS8GtpuProfile        TmnxMobProfNameOrEmpty,
        tmnxMobPdnS8DualStackPref      TmnxMobDualStackPref
    }

tmnxMobPdnS8LastChanged  OBJECT-TYPE
    SYNTAX      TimeStamp
    MAX-ACCESS  read-only
    STATUS      current
    DESCRIPTION
        "The value of tmnxMobPdnS8LastChanged indicates the timestamp of
         the last change to this row in tmnxMobPdnS8Table."
    ::= { tmnxMobPdnS8Entry 1 }

tmnxMobPdnS8PeerList  OBJECT-TYPE
    SYNTAX      TmnxMobProfNameOrEmpty
    MAX-ACCESS  read-write
    STATUS      current
    DESCRIPTION
        "The value of tmnxMobPdnS8PeerList specifies the peer list name.

         If a corresponding  peer does not exist in
         TIMETRA-MOBILE-PROFILE-MIB::tmnxMobProfPeerListTable,
         an 'inconsistentValue' error will be returned."
    DEFVAL { ''H }
    ::= { tmnxMobPdnS8Entry 2 }

tmnxMobPdnS8GtpcIfVRtrId  OBJECT-TYPE
    SYNTAX      TmnxVRtrID
    MAX-ACCESS  read-write
    STATUS      current
    DESCRIPTION
        "The value of tmnxMobPdnS8GtpcIfVRtrId specifies the virtual
         router to which the interface specified by tmnxMobPdnS8GtpcIfIndex
         belongs."
    DEFVAL { 1 }
    ::= { tmnxMobPdnS8Entry 3 }

tmnxMobPdnS8GtpcIfIndex  OBJECT-TYPE
    SYNTAX      InterfaceIndexOrZero
    MAX-ACCESS  read-write
    STATUS      current
    DESCRIPTION
        "The value of tmnxMobPdnS8GtpcIfIndex specifies the interface
         index of the local interface used for the General Packet Radio
         Services Tunneling Protocol for Control Plane (GTP-C) signaling.
         When the value of this object is set to 0, no interface has
         been assigned."
    DEFVAL { 0 }
    ::= { tmnxMobPdnS8Entry 4 }

tmnxMobPdnS8GtpuIfVRtrId  OBJECT-TYPE
    SYNTAX      TmnxVRtrID
    MAX-ACCESS  read-write
    STATUS      current
    DESCRIPTION
        "The value of tmnxMobPdnS8GtpuIfVRtrId specifies the virtual
         router to which the interface specified by tmnxMobPdnS8GtpuIfIndex
         belongs."
    DEFVAL { 1 }
    ::= { tmnxMobPdnS8Entry 5 }

tmnxMobPdnS8GtpuIfIndex  OBJECT-TYPE
    SYNTAX      InterfaceIndexOrZero
    MAX-ACCESS  read-write
    STATUS      current
    DESCRIPTION
        "The value of tmnxMobPdnS8GtpuIfIndex specifies the interface
         index of the local interface used for the General Packet Radio
         Services Tunneling Protocol for User Plane (GTP-U) signaling.
         When the value of this object is set to 0, no interface has
         been assigned."
    DEFVAL { 0 }
    ::= { tmnxMobPdnS8Entry 6 }

tmnxMobPdnS8GtpcProfile  OBJECT-TYPE
    SYNTAX      TmnxMobProfNameOrEmpty
    MAX-ACCESS  read-write
    STATUS      current
    DESCRIPTION
        "The value of tmnxMobPdnS8GtpcProfile specifies the GPRS Tunneling
         Protocol-Control plane (GTP-C) profile name. The GTP-C profile provides
         GTP-C signaling related configuration.

         If a corresponding GTP profile does not exist in
         TIMETRA-MOBILE-PROFILE-MIB::tmnxMobProfGtpTable,
         an 'inconsistentValue' error will be returned."
    DEFVAL { ''H }
    ::= { tmnxMobPdnS8Entry 7 }

tmnxMobPdnS8GtpuProfile  OBJECT-TYPE
    SYNTAX      TmnxMobProfNameOrEmpty
    MAX-ACCESS  read-write
    STATUS      current
    DESCRIPTION
        "The value of tmnxMobPdnS8GtpuProfile specifies the GPRS Tunneling
         Protocol-User plane (GTP-U) profile name. The GTP-U profile provides
         GTP-U signaling related configuration.

         If a corresponding GTP profile does not exist in
         TIMETRA-MOBILE-PROFILE-MIB::tmnxMobProfGtpTable,
         an 'inconsistentValue' error will be returned."
    DEFVAL { ''H }
    ::= { tmnxMobPdnS8Entry 8 }

tmnxMobPdnS8DualStackPref  OBJECT-TYPE
    SYNTAX      TmnxMobDualStackPref
    MAX-ACCESS  read-write
    STATUS      current
    DESCRIPTION
        "The value of tmnxMobPdnS8DualStackPref specifies the preference in a
         dual stack when both IPv4 and IPv6 addresses are configured for the
         S8 interface."
    DEFVAL { useCplane }
    ::= { tmnxMobPdnS8Entry 9 }

--
--  S2a table
--

tmnxMobPdnS2aTableLastChanged  OBJECT-TYPE
    SYNTAX      TimeStamp
    MAX-ACCESS  read-only
    STATUS      current
    DESCRIPTION
        "The value of tmnxMobPdnS2aTableLastChanged indicates the sysUpTime at
         the time of the last modification to tmnxMobPdnS2aTable by adding,
         deleting an entry or change to a writable object in the table.

         If no changes were made to the table since the last re-initialization
         of the local network management subsystem, then this object contains
         a zero value."
    ::= { tmnxMobPdnGlobalObjs 6 }

tmnxMobPdnS2aTable  OBJECT-TYPE
    SYNTAX      SEQUENCE OF TmnxMobPdnS2aEntry
    MAX-ACCESS  not-accessible
    STATUS      current
    DESCRIPTION
        "The tmnxMobPdnS2aTable provides an extension of the tmnxMobPdnTable
         for S2a reference point configuration."
    ::= { tmnxMobPdnConfObjs 6 }

tmnxMobPdnS2aEntry  OBJECT-TYPE
    SYNTAX      TmnxMobPdnS2aEntry
    MAX-ACCESS  not-accessible
    STATUS      current
    DESCRIPTION
        "Each row entry represents additional columns for S2a reference point
         configuration for a Packet Data Network Gateway (PGW)."
    AUGMENTS { tmnxMobPdnEntry }
    ::= { tmnxMobPdnS2aTable 1 }

TmnxMobPdnS2aEntry ::= SEQUENCE {
        tmnxMobPdnS2aLastChanged             TimeStamp,
        tmnxMobPdnS2aPeerList                TmnxMobProfNameOrEmpty,
        tmnxMobPdnS2aIfPmipv6RtrId           TmnxVRtrID,
        tmnxMobPdnS2aIfPmipv6Interface       InterfaceIndexOrZero,
        tmnxMobPdnS2aIfPmipv6Profile         TmnxMobProfNameOrEmpty
    }

tmnxMobPdnS2aLastChanged  OBJECT-TYPE
    SYNTAX      TimeStamp
    MAX-ACCESS  read-only
    STATUS      current
    DESCRIPTION
        "The value of tmnxMobPdnS2aLastChanged indicates the timestamp of
         the last change to this row in tmnxMobPdnS2aTable."
    ::= { tmnxMobPdnS2aEntry 1 }

tmnxMobPdnS2aPeerList  OBJECT-TYPE
    SYNTAX      TmnxMobProfNameOrEmpty
    MAX-ACCESS  read-write
    STATUS      current
    DESCRIPTION
        "The value of tmnxMobPdnS2aPeerList specifies the peer list name.

         If a corresponding  peer does not exist in
         TIMETRA-MOBILE-PROFILE-MIB::tmnxMobProfPeerListTable,
         an 'inconsistentValue' error will be returned."
    DEFVAL { ''H }
    ::= { tmnxMobPdnS2aEntry 2 }

tmnxMobPdnS2aIfPmipv6RtrId  OBJECT-TYPE
    SYNTAX      TmnxVRtrID
    MAX-ACCESS  read-write
    STATUS      current
    DESCRIPTION
        "The value of tmnxMobPdnS2aIfPmipv6RtrId specifies the virtual
         router to which the interface specified by tmnxMobPdnS2aIfPmipv6Interface
         belongs."
    DEFVAL { 1 }
    ::= { tmnxMobPdnS2aEntry 3 }

tmnxMobPdnS2aIfPmipv6Interface OBJECT-TYPE
    SYNTAX      InterfaceIndexOrZero
    MAX-ACCESS  read-write
    STATUS      current
    DESCRIPTION
        "The value of tmnxMobPdnS2aIfPmipv6Interface specifies the interface
         index of the local interface used for the Proxy Mobile IPv6 (PMIPv6)
         signaling. When the value of this object is set to 0, no interface has
         been assigned."
    DEFVAL { 0 }
    ::= { tmnxMobPdnS2aEntry 4 }

tmnxMobPdnS2aIfPmipv6Profile  OBJECT-TYPE
    SYNTAX      TmnxMobProfNameOrEmpty
    MAX-ACCESS  read-write
    STATUS      current
    DESCRIPTION
        "The value of tmnxMobPdnS2aIfPmipv6Profile specifies the Proxy Mobile
         IPv6 (PMIPv6) profile name. The PMIPv6 profile provides protocol
         related information applicable to PMIPv6 peers.

         If a corresponding PMIPv6 profile does not exist in
         TIMETRA-MOBILE-PROFILE-MIB::tmnxMobProfPmipv6Table,
         an 'inconsistentValue' error will be returned."
    DEFVAL { ''H }
    ::= { tmnxMobPdnS2aEntry 5 }

--
--  Rf table
--

tmnxMobPdnRfTableLastChanged  OBJECT-TYPE
    SYNTAX      TimeStamp
    MAX-ACCESS  read-only
    STATUS      current
    DESCRIPTION
        "The value of tmnxMobPdnRfTableLastChanged indicates the sysUpTime at
         the time of the last modification to tmnxMobPdnRfTable by
         adding, deleting an entry or change to a writable object in the table.

         If no changes were made to the table since the last re-initialization
         of the local network management subsystem, then this object contains
         a zero value."
    ::= { tmnxMobPdnGlobalObjs 7 }

tmnxMobPdnRfTable  OBJECT-TYPE
    SYNTAX      SEQUENCE OF TmnxMobPdnRfEntry
    MAX-ACCESS  not-accessible
    STATUS      current
    DESCRIPTION
        "The tmnxMobPdnRfTable provides an extension of the tmnxMobPdnTable
         for Rating Function (RF) configuration."
    ::= { tmnxMobPdnConfObjs 7 }

tmnxMobPdnRfEntry  OBJECT-TYPE
    SYNTAX      TmnxMobPdnRfEntry
    MAX-ACCESS  not-accessible
    STATUS      current
    DESCRIPTION
        "Each row entry represents additional columns for Rating Function (RF)
         configuration for the Packet Data Network Gateway (PGW)."
    AUGMENTS { tmnxMobPdnEntry }
    ::= { tmnxMobPdnRfTable 1 }

TmnxMobPdnRfEntry ::= SEQUENCE {
        tmnxMobPdnRfLastChanged             TimeStamp,
        tmnxMobPdnRfVRtrId                  TmnxVRtrID,
        tmnxMobPdnRfIfIndex                 InterfaceIndexOrZero,
        tmnxMobPdnRfPriDiaPeer              TmnxMobProfNameOrEmpty,
        tmnxMobPdnRfSecDiaPeer              TmnxMobProfNameOrEmpty,
        tmnxMobPdnRfAcctIntmInterval        Unsigned32,
        tmnxMobPdnRfApplTxTimer             Unsigned32,
        tmnxMobPdnRfRetryCount              TmnxMobDiaRetryCount,
        tmnxMobPdnRfChargingGroupID         TmnxEnabledDisabled,
        tmnxMobPdnRfOperatorString          TNamedItemOrEmpty,          
        tmnxMobPdnRfAcctLevel               TmnxMobRfAcctLevel,
        tmnxMobPdnRfNodeId                  DisplayString,
        tmnxMobPdnRfOcFilePrivateInfo       TNamedItemOrEmpty,
        tmnxMobPdnRfOcFileExtension         DisplayString,
        tmnxMobPdnRfOcFileClosureSize       Unsigned32,
        tmnxMobPdnRfOcFileClsLifeTime       Unsigned32,
        tmnxMobPdnRfOcFileClsMaxAcrs        Unsigned32,
        tmnxMobPdnRfOcFileObsoleteTime      Unsigned32,
        tmnxMobPdnRfOcPrimaryCf             INTEGER,
        tmnxMobPdnRfOcCf1State              TruthValue,
        tmnxMobPdnRfOcCf1Limit              Unsigned32,
        tmnxMobPdnRfOcCf2State              TruthValue,
        tmnxMobPdnRfOcCf2Limit              Unsigned32,
        tmnxMobPdnRfSuppVendorAvps          TmnxEnabledDisabled
    }

tmnxMobPdnRfLastChanged  OBJECT-TYPE
    SYNTAX      TimeStamp
    MAX-ACCESS  read-only
    STATUS      current
    DESCRIPTION
        "The value of tmnxMobPdnRfLastChanged indicates the timestamp of
         the last change to this row in tmnxMobPdnRfTable."
    ::= { tmnxMobPdnRfEntry 1 }

tmnxMobPdnRfVRtrId  OBJECT-TYPE
    SYNTAX      TmnxVRtrID
    MAX-ACCESS  read-write
    STATUS      current
    DESCRIPTION
        "The value of tmnxMobPdnRfVRtrId specifies the virtual
         router to which the interface specified by tmnxMobPdnRfVRtrId
         belongs."
    DEFVAL { 1 }
    ::= { tmnxMobPdnRfEntry 2 }

tmnxMobPdnRfIfIndex  OBJECT-TYPE
    SYNTAX      InterfaceIndexOrZero
    MAX-ACCESS  read-write
    STATUS      current
    DESCRIPTION
        "The value of tmnxMobPdnRfIfIndex specifies the interface index of
         the local interface used by diameter applications."
    DEFVAL { 0 }
    ::= { tmnxMobPdnRfEntry 3 }

tmnxMobPdnRfPriDiaPeer  OBJECT-TYPE
    SYNTAX      TmnxMobProfNameOrEmpty
    MAX-ACCESS  read-write
    STATUS      current
    DESCRIPTION
        "The value of tmnxMobPdnRfPriDiaPeer specifies the diameter peer 
         profile to be used for the primary Charging Data Function (CDF) at the 
         Gateway level.

         If a corresponding diameter peer profile does not exist in
         TIMETRA-MOBILE-PROFILE-MIB::tmnxMobProfDiaPeerTable,
         an 'inconsistentValue' error will be returned."
    DEFVAL { ''H }
    ::= { tmnxMobPdnRfEntry 4 }

tmnxMobPdnRfSecDiaPeer  OBJECT-TYPE
    SYNTAX      TmnxMobProfNameOrEmpty
    MAX-ACCESS  read-write
    STATUS      current
    DESCRIPTION
        "The value of tmnxMobPdnRfSecDiaPeer specifies the diameter peer 
         profile to be used for the secondary Charging Data Function (CDF) at
         the Gateway level.

         If a corresponding diameter peer profile does not exist in
         TIMETRA-MOBILE-PROFILE-MIB::tmnxMobProfDiaPeerTable,
         an 'inconsistentValue' error will be returned."
    DEFVAL { ''H }
    ::= { tmnxMobPdnRfEntry 5 }

tmnxMobPdnRfAcctIntmInterval  OBJECT-TYPE
    SYNTAX      Unsigned32 (1..86400)
    UNITS       "seconds"
    MAX-ACCESS  read-write
    STATUS      current
    DESCRIPTION
        "The value of tmnxMobPdnRfAcctIntmInterval specifies the accounting 
         interim interval to send interim accounting information to the 
         Charging Data Function (CDF) at the Gateway level."
    DEFVAL { 1800 }
    ::= { tmnxMobPdnRfEntry 6 }

tmnxMobPdnRfApplTxTimer  OBJECT-TYPE
    SYNTAX      Unsigned32 (1..30)
    UNITS       "seconds"
    MAX-ACCESS  read-write
    STATUS      current
    DESCRIPTION
        "The value of tmnxMobPdnRfApplTxTimer specifies the application 
         transaction timer for Accounting Requests (ACR) and 
         Accounting Answers (ACA)."
    DEFVAL { 5 }
    ::= { tmnxMobPdnRfEntry 7 }

tmnxMobPdnRfRetryCount  OBJECT-TYPE
    SYNTAX      TmnxMobDiaRetryCount
    UNITS       "seconds"
    MAX-ACCESS  read-write
    STATUS      current
    DESCRIPTION
        "The value of tmnxMobPdnRfRetryCount specifies the retry count for 
         Accounting Requests (ACR) messages. An Accounting Requests (ACR) 
         message will be retransmitted for the number of times specified, 
         when an Accounting Answers (ACA) is not received from the Charging Data
         Function (CDF) server."
    DEFVAL { 3 }
    ::= { tmnxMobPdnRfEntry 8 }

tmnxMobPdnRfChargingGroupID  OBJECT-TYPE
    SYNTAX      TmnxEnabledDisabled
    MAX-ACCESS  read-write
    STATUS      current
    DESCRIPTION
        "The value of tmnxMobPdnRfChargingGroupID specifies whether the 
         inclusion of Charging-Group-ID AVP in Accounting Requests (ACR) 
         message is enabled or not."
    DEFVAL { disabled }
    ::= { tmnxMobPdnRfEntry 9 }

tmnxMobPdnRfOperatorString  OBJECT-TYPE
    SYNTAX      TNamedItemOrEmpty
    MAX-ACCESS  read-write
    STATUS      current
    DESCRIPTION
        "The value of tmnxMobPdnRfOperatorString specifies string to be 
         included in operator-string AVP (non-standard) of an Accounting 
         Requests (ACR) message."
    DEFVAL { ''H }
    ::= { tmnxMobPdnRfEntry 10 }

tmnxMobPdnRfAcctLevel  OBJECT-TYPE
    SYNTAX      TmnxMobRfAcctLevel
    MAX-ACCESS  read-write
    STATUS      current
    DESCRIPTION
        "The value of tmnxMobPdnRfAcctLevel specifies whether PDN-level 
         accounting or QCI-level accounting is applicable. When PDN-level 
         accounting is specified, diameter charging sessions to the Charging 
         Data Function (CDF) are setup on a per Packet Data Network (PDN) 
         connection basis. When QCI-level accounting is specified, diameter 
         charging sessions to the Charging Data Function (CDF) are setup on a 
         per bearer basis."
    DEFVAL { qciLevel }
    ::= { tmnxMobPdnRfEntry 11 }

tmnxMobPdnRfNodeId  OBJECT-TYPE
    SYNTAX      DisplayString (SIZE (0..20))
    MAX-ACCESS  read-write
    STATUS      current
    DESCRIPTION
        "The value of tmnxMobPdnRfNodeId specifies an operator 
         configurable identifier for the node which is used over the Rating 
         Function (RF) interface."
    DEFVAL { ''H }
    ::= { tmnxMobPdnRfEntry 12 }

tmnxMobPdnRfOcFilePrivateInfo  OBJECT-TYPE
    SYNTAX      TNamedItemOrEmpty
    MAX-ACCESS  read-write
    STATUS      current
    DESCRIPTION
        "The value of tmnxMobPdnRfOcFilePrivateInfo specifies an operator 
         configurable file private information field that is used in the file 
         name."
    DEFVAL { ''H }
    ::= { tmnxMobPdnRfEntry 13 }

tmnxMobPdnRfOcFileExtension  OBJECT-TYPE
    SYNTAX      DisplayString (SIZE (0..8))
    MAX-ACCESS  read-write
    STATUS      current
    DESCRIPTION
        "The value of tmnxMobPdnRfOcFileExtension specifies an operator 
         configurable file extension field that is used in the file name."
    DEFVAL { ''H }
    ::= { tmnxMobPdnRfEntry 14 }

tmnxMobPdnRfOcFileClosureSize  OBJECT-TYPE
    SYNTAX      Unsigned32 (1..100)
    UNITS       "megabytes"
    MAX-ACCESS  read-write
    STATUS      current
    DESCRIPTION
        "The value of tmnxMobPdnRfOcFileClosureSize specifies an operator 
         configurable file closure size limit."
    DEFVAL { 5 }
    ::= { tmnxMobPdnRfEntry 15 }

tmnxMobPdnRfOcFileClsLifeTime  OBJECT-TYPE
    SYNTAX      Unsigned32 (1..24)
    UNITS       "hours"
    MAX-ACCESS  read-write
    STATUS      current
    DESCRIPTION
        "The value of tmnxMobPdnRfOcFileClsLifeTime specifies an operator 
         configurable file closure lifetime. The file is closed after the 
         specified duration."
    DEFVAL { 1 }
    ::= { tmnxMobPdnRfEntry 16 }

tmnxMobPdnRfOcFileClsMaxAcrs  OBJECT-TYPE
    SYNTAX      Unsigned32 (100..5000)
    MAX-ACCESS  read-write
    STATUS      current
    DESCRIPTION
        "The value of tmnxMobPdnRfOcFileClsMaxAcrs specifies an operator 
         configurable limit for the number of Accounting Requests (ACR) that 
         are stored in a file. The file is closed after the specified limit is
         reached."
    DEFVAL { 1000 }
    ::= { tmnxMobPdnRfEntry 17 }

tmnxMobPdnRfOcFileObsoleteTime  OBJECT-TYPE
    SYNTAX      Unsigned32 (1..31)
    UNITS       "days"
    MAX-ACCESS  read-write
    STATUS      current
    DESCRIPTION
        "The value of tmnxMobPdnRfOcFileObsoleteTime specifies an operator 
         configurable file duration, after which the file is deleted."
    DEFVAL { 7 }
    ::= { tmnxMobPdnRfEntry 18 }

tmnxMobPdnRfOcPrimaryCf  OBJECT-TYPE
    SYNTAX      INTEGER {
                         cf1    (1),
                         cf2    (2),
                         none   (3) 
                        }
    MAX-ACCESS  read-write
    STATUS      current
    DESCRIPTION
        "The value of tmnxMobPdnRfOcPrimaryCf specifies which compact flash
         will be used as a primary storage for the Accounting Requests (ACR)
         storage. 
 
         If the user tries to set the 'cf1' and if the 'cf1' is not available 
         then 'cf2' will be set as primary storage. If the user tries to set 
         the 'cf2' and if 'cf2' is not available then cf1 will be set as 
         primary storage. If both of the compact flash are not available then 
         value 'none' will be set."
    DEFVAL { cf1 }
    ::= { tmnxMobPdnRfEntry 19 }

tmnxMobPdnRfOcCf1State  OBJECT-TYPE
    SYNTAX      TruthValue
    MAX-ACCESS  read-write
    STATUS      current
    DESCRIPTION
        "The value of tmnxMobPdnRfOcCf1State specifies whether the first 
         compact flash is enabled to be used for the Accounting Requests (ACR)
         storage. 
 
         If the compact flash is not available then it will be disabled."
    DEFVAL { false }
    ::= { tmnxMobPdnRfEntry 20 }

tmnxMobPdnRfOcCf1Limit  OBJECT-TYPE
    SYNTAX      Unsigned32
    UNITS       "megabytes"
    MAX-ACCESS  read-write
    STATUS      current
    DESCRIPTION
        "The value of tmnxMobPdnRfOcCf1Limit specifies the limit 
         (in megabytes) for an amount of memory on the first compact flash that
         can be used for the Accounting Requests (ACR) storage. Once the 
         threshold has been reached, the system can no longer support accurate
         charging.
 
         If the compact flash is not available then tmnxMobPdnRfOcCf1Limit 
         will be set to 0.   
 
         If tmnxMobPdnRfOcCf1State is enabled and the value of 
         tmnxMobPdnRfOcCf1Limit is 0, then maximum available memory on the 
         second compact flash can be used for the ACR storage."
    DEFVAL { 0 }
    ::= { tmnxMobPdnRfEntry 21 }

tmnxMobPdnRfOcCf2State  OBJECT-TYPE
    SYNTAX      TruthValue
    MAX-ACCESS  read-write
    STATUS      current
    DESCRIPTION
        "The value of tmnxMobPdnRfOcCf2State specifies whether 
         the second compact flash is enabled to be used for the Accounting 
         Requests (ACR) storage.

         If the compact flash is not available then it will be disabled."
    DEFVAL { false }
    ::= { tmnxMobPdnRfEntry 22 }

tmnxMobPdnRfOcCf2Limit  OBJECT-TYPE
    SYNTAX      Unsigned32
    UNITS       "megabytes"
    MAX-ACCESS  read-write
    STATUS      current
    DESCRIPTION
        "The value of tmnxMobPdnRfOcCf2Limit specifies the limit 
         (in megabytes) for an amount of memory on the second compact flash that
         can be used for the Accounting Requests (ACR) storage. Once the 
         threshold has been reached, the system can no longer support accurate
         charging.
         
         If the compact flash is not available then tmnxMobPdnRfOcCf2Limit 
         will be set to 0.   
         
         If tmnxMobPdnRfOcCf2State is enabled and the value of 
         tmnxMobPdnRfOcCf2Limit is 0, then maximum available memory on the 
         second compact flash can be used for the ACR storage."
    DEFVAL { 0 }
    ::= { tmnxMobPdnRfEntry 23 }

tmnxMobPdnRfSuppVendorAvps  OBJECT-TYPE
    SYNTAX      TmnxEnabledDisabled
    MAX-ACCESS  read-write
    STATUS      current
    DESCRIPTION
        "The value of tmnxMobPdnRfSuppVendorAvps specifies whether the 
         supported vendor IDs to be advertised for Capabilities Exchange
         negotiation. When it is disabled 3GPP standard defined Attribute Value
         Pair (AVPs) are supported."
    DEFVAL { disabled }
    ::= { tmnxMobPdnRfEntry 24 }

--
--  Gateway static base policy table
--

tmnxMobPdnPccBasePolTableLstChgd  OBJECT-TYPE
    SYNTAX      TimeStamp
    MAX-ACCESS  read-only
    STATUS      current
    DESCRIPTION
        "The value of tmnxMobPdnPccBasePolTableLstChgd indicates the sysUpTime 
         at the time of the last modification to tmnxMobPdnPccBasePolTable by
         adding, deleting an entry or change to a writable object in the table.

         If no changes were made to the table since the last re-initialization
         of the local network management subsystem, then this object contains
         a zero value."
    ::= { tmnxMobPdnGlobalObjs 8 }

tmnxMobPdnPccBasePolTable  OBJECT-TYPE
    SYNTAX      SEQUENCE OF TmnxMobPdnPccBasePolEntry
    MAX-ACCESS  not-accessible
    STATUS      current
    DESCRIPTION
        "The tmnxMobPdnPccBasePolTable has an entry for each static policy base 
         profile configured for Packet Data Network Gateway (PGW).

         A maximum of 1 static policy base profiles can be configured for 
         each gateway."
    ::= { tmnxMobPdnConfObjs 8 }

tmnxMobPdnPccBasePolEntry  OBJECT-TYPE
    SYNTAX      TmnxMobPdnPccBasePolEntry
    MAX-ACCESS  not-accessible
    STATUS      current
    DESCRIPTION
        "Each row entry represents a static policy base profile in an Access 
         Point Name (APN). Entries can be created and deleted by the user."
    INDEX { tmnxMobGwId,
            tmnxMobPdnPccIpCanType,
            tmnxMobProfPolBaseName
          }
    ::= { tmnxMobPdnPccBasePolTable 1 }

TmnxMobPdnPccBasePolEntry ::= SEQUENCE {
        tmnxMobPdnPccIpCanType         TmnxMobIpCanType,
        tmnxMobPdnPccBasePolRowStatus  RowStatus
    }

tmnxMobPdnPccIpCanType  OBJECT-TYPE
    SYNTAX      TmnxMobIpCanType
    MAX-ACCESS  not-accessible
    STATUS      current
    DESCRIPTION
        "The value of tmnxMobPdnPccIpCanType specifies the type of Internet 
         Protocol Connectivity Access Network (IP-CAN) session."
    ::= { tmnxMobPdnPccBasePolEntry 1 }

tmnxMobPdnPccBasePolRowStatus  OBJECT-TYPE
    SYNTAX      RowStatus
    MAX-ACCESS  read-create
    STATUS      current
    DESCRIPTION
        "The value of tmnxMobPdnPccBasePolRowStatus specifies the row status of
         this entry. It is used for creation and deletion of this static policy 
         base profile for a gateway.

         If a corresponding base policy does not exist in
         TIMETRA-MOBILE-PROFILE-MIB::tmnxMobProfPolBaseTable,
         an 'inconsistentName' error will be returned.

         If the precedence value, specified by 
         TIMETRA-MOBILE-PROFILE-MIB::tmnxMobProfPolBasePrecedence, is equal to
         the precedence value of a base profile associated in this APN, then
         an 'inconsistentValue' error will be returned."
    ::= { tmnxMobPdnPccBasePolEntry 2 }

--
--  APN table
--

tmnxMobPdnApnTableLastChanged  OBJECT-TYPE
    SYNTAX      TimeStamp
    MAX-ACCESS  read-only
    STATUS      current
    DESCRIPTION
        "The value of tmnxMobPdnApnTableLastChanged indicates the sysUpTime at
         the time of the last modification to tmnxMobPdnApnTable by
         adding, deleting an entry or change to a writable object in the table.

         If no changes were made to the table since the last re-initialization
         of the local network management subsystem, then this object contains
         a zero value."
    ::= { tmnxMobPdnGlobalObjs 9 }

tmnxMobPdnApnTable  OBJECT-TYPE
    SYNTAX      SEQUENCE OF TmnxMobPdnApnEntry
    MAX-ACCESS  not-accessible
    STATUS      current
    DESCRIPTION
        "The tmnxMobPdnApnTable has an entry for each Access Point Name (APN).
         An APN identifies an external network that is accessible from a
         terminal."
    ::= { tmnxMobPdnConfObjs 9 }

tmnxMobPdnApnEntry  OBJECT-TYPE
    SYNTAX      TmnxMobPdnApnEntry
    MAX-ACCESS  not-accessible
    STATUS      current
    DESCRIPTION
        "Each row entry represents an Access Point Name (APN). Entries can be
         created and deleted by the user."
    INDEX { tmnxMobGwId,
            tmnxMobPdnApnName
          }
    ::= { tmnxMobPdnApnTable 1 }

TmnxMobPdnApnEntry ::= SEQUENCE {
        tmnxMobPdnApnName                   TmnxMobApn,
        tmnxMobPdnApnRowStatus              RowStatus,
        tmnxMobPdnApnLastChanged            TimeStamp,
        tmnxMobPdnApnDescription            TItemDescription,
        tmnxMobPdnApnAdminState             TmnxAdminState,
        tmnxMobPdnApnOperState              TmnxOperState,
        tmnxMobPdnApnGracefulShutTimeout    Unsigned32,
        tmnxMobPdnApnType                   INTEGER,
        tmnxMobPdnApnVRtrId                 TmnxVRtrID,
        tmnxMobPdnApnVirtualApnName         TmnxMobApnOrZero,
        tmnxMobPdnApnPdnTypeIpv4            TruthValue,
        tmnxMobPdnApnPdnTypeIpv6            TruthValue,
        tmnxMobPdnApnPdnTypeIpv4v6          TruthValue,
        tmnxMobPdnApnPdnAllocType           INTEGER,
        tmnxMobPdnApnPdnRestrictionType     INTEGER,
        tmnxMobPdnApnAllowMultiplePdns      TruthValue,
        tmnxMobPdnApnSelectSubscribed       TruthValue,
        tmnxMobPdnApnSelectMsProvided       TruthValue,
        tmnxMobPdnApnSelectNwProvided       TruthValue,
        tmnxMobPdnApnIpAllocLocalPool       TruthValue,
        tmnxMobPdnApnIpAllocHssStatic       TruthValue,
        tmnxMobPdnApnIpAllocAaa             TruthValue,
        tmnxMobPdnApnIpAllocDhcpProxy       TruthValue,
        tmnxMobPdnApnIpAllocDhcpRelay       TruthValue,
        tmnxMobPdnApnIpAllocDhcpServer      TruthValue,
        tmnxMobPdnApnPcrfDynamicPcc         TmnxEnabledDisabledOrInherit,
        tmnxMobPdnApnPcrfPriDiameterPeer    TmnxMobProfNameOrEmpty,
        tmnxMobPdnApnPcrfSecDiameterPeer    TmnxMobProfNameOrEmpty,
        tmnxMobPdnApnUplinkQciPolName       TmnxMobProfNameOrEmpty,
        tmnxMobPdnApnDownlinkQciPolName     TmnxMobProfNameOrEmpty,
        tmnxMobPdnApnAggrRateUplink         TmnxMobProfMbrRate,
        tmnxMobPdnApnAggrRateDownlink       TmnxMobProfMbrRate,
        tmnxMobPdnApnIdleTimeout            Unsigned32,
        tmnxMobPdnApnSessionTimeout         Unsigned32,
        tmnxMobPdnApnRejectForeignSub       TruthValue,
        tmnxMobPdnApnBlockedPlmnList        TmnxMobProfNameOrEmpty,
        tmnxMobPdnApnUliReporting           TruthValue,
        tmnxMobPdnApnUmtsQosPolName         TmnxMobProfNameOrEmpty,
        tmnxMobPdnApnPcrfDynPccFHSession    TmnxEnabledDisabled
    }

tmnxMobPdnApnName  OBJECT-TYPE
    SYNTAX      TmnxMobApn
    MAX-ACCESS  not-accessible
    STATUS      current
    DESCRIPTION
        "The value of tmnxMobPdnApnName specifies the Access Point Name (APN)."
    ::= { tmnxMobPdnApnEntry 1 }

tmnxMobPdnApnRowStatus  OBJECT-TYPE
    SYNTAX      RowStatus
    MAX-ACCESS  read-create
    STATUS      current
    DESCRIPTION
        "The value of tmnxMobPdnApnRowStatus specifies the row status of
         this entry. It is used for creation and deletion of this Access Point
         Name (APN)."
    ::= { tmnxMobPdnApnEntry 2 }

tmnxMobPdnApnLastChanged  OBJECT-TYPE
    SYNTAX      TimeStamp
    MAX-ACCESS  read-only
    STATUS      current
    DESCRIPTION
        "The value of tmnxMobPdnApnLastChanged indicates the timestamp of
         the last change to this row in tmnxMobPdnApnTable."
    ::= { tmnxMobPdnApnEntry 3 }

tmnxMobPdnApnDescription  OBJECT-TYPE
    SYNTAX      TItemDescription
    MAX-ACCESS  read-create
    STATUS      current
    DESCRIPTION
        "The value of tmnxMobPdnApnDescription specifies the description
         string for this Access Point Name (APN). It can consist of any 
         printable, seven-bit ASCII characters up to 80 characters in length."
    DEFVAL { ''H }
    ::= { tmnxMobPdnApnEntry 4 }

tmnxMobPdnApnAdminState  OBJECT-TYPE
    SYNTAX      TmnxAdminState
    MAX-ACCESS  read-create
    STATUS      current
    DESCRIPTION
        "The value of tmnxMobPdnApnAdminState specifies the desired 
         administrative state of this Access Point Name (APN). When the value
         of this object is set ot 'outOfService', then the Packet Data 
         Network (PDN) sessions are not accepted."
    DEFVAL { inService }
    ::= { tmnxMobPdnApnEntry 5 }

tmnxMobPdnApnOperState  OBJECT-TYPE
    SYNTAX      TmnxOperState
    MAX-ACCESS  read-only
    STATUS      current
    DESCRIPTION
        "The value of tmnxMobPdnApnOperState indicates the current operational
         status of this Access Point Name (APN)."
    ::= { tmnxMobPdnApnEntry 6 }

tmnxMobPdnApnGracefulShutTimeout  OBJECT-TYPE
    SYNTAX      Unsigned32 (15..60)
    UNITS       "minutes"
    MAX-ACCESS  read-create
    STATUS      current
    DESCRIPTION
        "The value of tmnxMobPdnApnGracefulShutTimeout specifies the graceful
         shutdown time. For graceful system shutdown, the existing
         request or connections are allowed to complete while no new
         requests or connections are accepted.

         This procedure is used to take the system to maintenance mode."
    DEFVAL { 30 }
    ::= { tmnxMobPdnApnEntry 7 }

tmnxMobPdnApnType  OBJECT-TYPE
    SYNTAX      INTEGER {
                         real     (1),
                         virtual  (2)   
                        }
    MAX-ACCESS  read-create
    STATUS      current
    DESCRIPTION
        "The value of tmnxMobPdnApnType specifies the type of this Access Point 
         Name (APN). A virtual APN reduces the amount of the required APN 
         provisioning by consolidating access to all real APNs through a single 
         virtual APN at the Packet Data Network Gateway (PGW)."
    DEFVAL { real }
    ::= { tmnxMobPdnApnEntry 8 }

tmnxMobPdnApnVRtrId  OBJECT-TYPE
    SYNTAX      TmnxVRtrID
    MAX-ACCESS  read-create
    STATUS      current
    DESCRIPTION
        "The value of tmnxMobPdnApnVRtrId specifies the virtual router to which 
         this Access Point Name (APN) belongs. All subscribers belonging to this 
         APN are mapped to this virtual router instance and hence they all 
         access the common services."
    DEFVAL { 1 }
    ::= { tmnxMobPdnApnEntry 9 }

tmnxMobPdnApnVirtualApnName  OBJECT-TYPE
    SYNTAX      TmnxMobApnOrZero
    MAX-ACCESS  read-create
    STATUS      current
    DESCRIPTION
        "The value of tmnxMobPdnApnVirtualApnName specifies the name of the 
         virtual Access Point Name (APN) to which this real APN is mapped.

         The value of this object can be set only if the value of
         tmnxMobPdnApnType is set to 'real'."
    DEFVAL { ''H }
    ::= { tmnxMobPdnApnEntry 10 }

tmnxMobPdnApnPdnTypeIpv4  OBJECT-TYPE
    SYNTAX      TruthValue
    MAX-ACCESS  read-create
    STATUS      current
    DESCRIPTION
        "The value of tmnxMobPdnApnPdnTypeIpv4 specifies if IPv4 Pakcet Data 
         Network (PDN) sessions are supported by this Access Point Name (APN)."
    DEFVAL { true }
    ::= { tmnxMobPdnApnEntry 11 }
    
tmnxMobPdnApnPdnTypeIpv6  OBJECT-TYPE
    SYNTAX      TruthValue
    MAX-ACCESS  read-create
    STATUS      current
    DESCRIPTION
        "The value of tmnxMobPdnApnPdnTypeIpv6 specifies if IPv6 Pakcet Data 
         Network (PDN) sessions are supported by this Access Point Name (APN)."
    DEFVAL { false }
    ::= { tmnxMobPdnApnEntry 12 }
        
tmnxMobPdnApnPdnTypeIpv4v6  OBJECT-TYPE
    SYNTAX      TruthValue
    MAX-ACCESS  read-create
    STATUS      current
    DESCRIPTION
        "The value of tmnxMobPdnApnPdnTypeIpv4v6 specifies if IPv4v6 Pakcet Data 
         Network (PDN) sessions are supported by this Access Point Name (APN)."
    DEFVAL { false }
    ::= { tmnxMobPdnApnEntry 13 }

tmnxMobPdnApnPdnAllocType  OBJECT-TYPE
    SYNTAX      INTEGER {
                         ietf          (1),
                         ranSignaling  (2)   
                        }
    MAX-ACCESS  read-create
    STATUS      current
    DESCRIPTION
        "The value of tmnxMobPdnApnPdnAllocType specifies if the User 
         Equipment (UE) gets the IP address via RAN signaling or via its DHCP 
         client functionality after the default bearer is established."
    DEFVAL { ranSignaling }
    ::= { tmnxMobPdnApnEntry 14 }

tmnxMobPdnApnPdnRestrictionType  OBJECT-TYPE
    SYNTAX      INTEGER {
                         any       (0),
                         public1   (1),
                         public2   (2),
                         private1  (3),
                         private2  (4)
                        }
    MAX-ACCESS  read-create
    STATUS      current
    DESCRIPTION
        "The value of tmnxMobPdnApnPdnRestrictionType specifies the level of 
         restriction imposed on Evolved Packet System (EPS) bearer contexts 
         created to the associated Access Point Name (APN). The value of this 
         object is used to determine, on a per User Equipment (UE) basis, 
         whether it is allowed to establish EPS bearers to other APNs."
    DEFVAL { any }
    ::= { tmnxMobPdnApnEntry 15 }
    
tmnxMobPdnApnAllowMultiplePdns  OBJECT-TYPE
    SYNTAX      TruthValue
    MAX-ACCESS  read-create
    STATUS      current
    DESCRIPTION
        "The value of tmnxMobPdnApnAllowMultiplePdns specifies if multiple
         Packet Data Network (PDN) types for the same Access Point Name (APN) 
         are allowed."
    DEFVAL { false }
    ::= { tmnxMobPdnApnEntry 16 }

tmnxMobPdnApnSelectSubscribed  OBJECT-TYPE
    SYNTAX      TruthValue
    MAX-ACCESS  read-create
    STATUS      current
    DESCRIPTION
        "The value of tmnxMobPdnApnSelectSubscribed specifies if the subscribed 
         verified selection mode is allowed or not. Selection mode 
         verification will be used to ensure a Mobile Station's (MS) 
         subscription to use this APN. This setting must mach the corresponding 
         setting on the SGSN/MME. If the two settings are not identical, the 
         PGW/GGSN rejects the session with a cause code user authentication 
         failed."
    DEFVAL { true }
    ::= { tmnxMobPdnApnEntry 17 }
    
tmnxMobPdnApnSelectMsProvided  OBJECT-TYPE
    SYNTAX      TruthValue
    MAX-ACCESS  read-create
    STATUS      current
    DESCRIPTION
        "The value of tmnxMobPdnApnSelectMsProvided specifies if the Mobile 
         Station (MS) provided Access Point Name (APN) selection mode is 
         allowed or not. Selection mode verification will be used to ensure a 
         MS's subscription to use this APN. This setting must mach the 
         corresponding setting on the SGSN/MME. If the two settings are not 
         identical, the PGW/GGSN rejects the session with a cause code user 
         authentication failed."
    DEFVAL { false }
    ::= { tmnxMobPdnApnEntry 18 }
        
tmnxMobPdnApnSelectNwProvided  OBJECT-TYPE
    SYNTAX      TruthValue
    MAX-ACCESS  read-create
    STATUS      current
    DESCRIPTION
        "The value of tmnxMobPdnApnSelectNwProvided specifies if the 
         network provided provided Access Point Name (APN) selection mode is 
         allowed or not. Selection mode verification will be used to ensure a 
         Mobile Station's (MS) subscription to use this APN. This setting must 
         mach the corresponding setting on the SGSN/MME. If the two settings 
         are not identical, the PGW/GGSN rejects the session with a cause code 
         user authentication failed."
    DEFVAL { false }
    ::= { tmnxMobPdnApnEntry 19 }

tmnxMobPdnApnIpAllocLocalPool  OBJECT-TYPE
    SYNTAX      TruthValue
    MAX-ACCESS  read-create
    STATUS      current
    DESCRIPTION
        "The value of tmnxMobPdnApnIpAllocLocalPool specifies if the IP address 
         for a User Equipment (UE) can be assigned from the configured local 
         pools."
    DEFVAL { true }
    ::= { tmnxMobPdnApnEntry 20 }
    
tmnxMobPdnApnIpAllocHssStatic  OBJECT-TYPE
    SYNTAX      TruthValue
    MAX-ACCESS  read-create
    STATUS      current
    DESCRIPTION
        "The value of tmnxMobPdnApnIpAllocHssStatic specifies if the IP address 
         for a User Equipment (UE) is the static IP address assigned by Home 
         Subscriber Server (HSS) to Mobility Management Entity (MME) and sent to 
         Packet Data Network Gateway (PGW) during Create Session Request."
    DEFVAL { false }
    ::= { tmnxMobPdnApnEntry 21 }
    
tmnxMobPdnApnIpAllocAaa  OBJECT-TYPE
    SYNTAX      TruthValue
    MAX-ACCESS  read-create
    STATUS      current
    DESCRIPTION
        "The value of tmnxMobPdnApnIpAllocAaa specifies if the IP address 
         for a User Equipment (UE) can be assigned using radius or diameter
         server using Framed-IP and Framed-Pool-Name."
    DEFVAL { false }
    ::= { tmnxMobPdnApnEntry 22 }
    
tmnxMobPdnApnIpAllocDhcpProxy  OBJECT-TYPE
    SYNTAX      TruthValue
    MAX-ACCESS  read-create
    STATUS      current
    DESCRIPTION
        "The value of tmnxMobPdnApnIpAllocDhcpProxy specifies if a DHCP request 
         can be sent by the Packet Data Network Gateway (PGW) as part of the 
         User Equipment (UE) attach procedure to external DHCP server for UE IP 
         address allocation."
    DEFVAL { false }
    ::= { tmnxMobPdnApnEntry 23 }
    
tmnxMobPdnApnIpAllocDhcpRelay  OBJECT-TYPE
    SYNTAX      TruthValue
    MAX-ACCESS  read-create
    STATUS      current
    DESCRIPTION
        "The value of tmnxMobPdnApnIpAllocDhcpRelay specifies if the DHCP 
         requests from User Equipment (UE) can be sent to external DHCP server 
         for IP address allocation after Attach procedure is completed."
    DEFVAL { false }
    ::= { tmnxMobPdnApnEntry 24 }

tmnxMobPdnApnIpAllocDhcpServer  OBJECT-TYPE
    SYNTAX      TruthValue
    MAX-ACCESS  read-create
    STATUS      current
    DESCRIPTION
        "The value of tmnxMobPdnApnIpAllocDhcpServer specifies if the DHCP 
         requests from User Equipment (UE) can be sent to internal DHCP server 
         in the Packet Data Network Gateway (PGW) for IP address allocation."
    DEFVAL { false }
    ::= { tmnxMobPdnApnEntry 25 }

tmnxMobPdnApnPcrfDynamicPcc  OBJECT-TYPE
    SYNTAX      TmnxEnabledDisabledOrInherit
    MAX-ACCESS  read-create
    STATUS      current
    DESCRIPTION
        "The value of tmnxMobPdnApnPcrfDynamicPcc specifies whether to enable
         the interaction with Policy and Charging Rules Function (PCRF)
         for bearer creation. When dynamic-pcc is enabled,
         Policy and Charging Control (PCC) rules are sent from
         PCRF for dedicated bearer creation.
    
         When the value of tmnxMobPdnApnPcrfDynamicPcc is 'inherit', the value 
         is inherited from the value of tmnxMobPdnPccDynamicState which 
         specifies if interaction with Policy and Charging Rules Function (PCRF)
         is enabled for bearer creation or not at the gateway level."
    DEFVAL { disabled }
    ::= { tmnxMobPdnApnEntry 26 }

tmnxMobPdnApnPcrfPriDiameterPeer  OBJECT-TYPE
    SYNTAX      TmnxMobProfNameOrEmpty
    MAX-ACCESS  read-create
    STATUS      current
    DESCRIPTION
        "The value of tmnxMobPdnApnPcrfPriDiameterPeer specifies the 
         default primary diameter peer profile name.

         If a corresponding diameter peer profile does not exist in
         TIMETRA-MOBILE-PROFILE-MIB::tmnxMobProfDiaPeerTable,
         an 'inconsistentValue' error will be returned."
    DEFVAL { ''H }
    ::= { tmnxMobPdnApnEntry 27 }

tmnxMobPdnApnPcrfSecDiameterPeer  OBJECT-TYPE
    SYNTAX      TmnxMobProfNameOrEmpty
    MAX-ACCESS  read-create
    STATUS      current
    DESCRIPTION
        "The value of tmnxMobPdnApnPcrfSecDiameterPeer specifies the 
         default primary diameter peer profile name.

         If a corresponding diameter peer profile does not exist in
         TIMETRA-MOBILE-PROFILE-MIB::tmnxMobProfDiaPeerTable,
         an 'inconsistentValue' error will be returned."
    DEFVAL { ''H }
    ::= { tmnxMobPdnApnEntry 28 }

tmnxMobPdnApnUplinkQciPolName  OBJECT-TYPE
    SYNTAX      TmnxMobProfNameOrEmpty
    MAX-ACCESS  read-create
    STATUS      current
    DESCRIPTION
        "The value of tmnxMobPdnApnUplinkQciPolName specifies the QoS Class
         Identifier (QCI) policy profile name for uplink direction.

         If a corresponding QCI policy profile does not exist in
         TIMETRA-MOBILE-PROFILE-MIB::tmnxMobProfQciPolTable,
         an 'inconsistentValue' error will be returned."
    DEFVAL { ''H }
    ::= { tmnxMobPdnApnEntry 29 }

tmnxMobPdnApnDownlinkQciPolName  OBJECT-TYPE
    SYNTAX      TmnxMobProfNameOrEmpty
    MAX-ACCESS  read-create
    STATUS      current
    DESCRIPTION
        "The value of tmnxMobPdnApnDownlinkQciPolName specifies the QoS Class
         Identifier (QCI) policy profile name for downlink direction.

         If a corresponding QCI policy profile does not exist in
         TIMETRA-MOBILE-PROFILE-MIB::tmnxMobProfQciPolTable,
         an 'inconsistentValue' error will be returned."
    DEFVAL { ''H }
    ::= { tmnxMobPdnApnEntry 30 }

tmnxMobPdnApnAggrRateUplink  OBJECT-TYPE
    SYNTAX      TmnxMobProfMbrRate
    UNITS       "kbps"
    MAX-ACCESS  read-create
    STATUS      current
    DESCRIPTION
        "The value of tmnxMobPdnApnAggrRateUplink specifies the uplink aggregate 
         maximum bit rate per Packet Data Network (PDN) for all non Guaranteed 
         Bit Rate (GBR) bearers for a given UE."
    DEFVAL { 0 }
    ::= { tmnxMobPdnApnEntry 31 }

tmnxMobPdnApnAggrRateDownlink  OBJECT-TYPE
    SYNTAX      TmnxMobProfMbrRate
    UNITS       "kbps"
    MAX-ACCESS  read-create
    STATUS      current
    DESCRIPTION
        "The value of tmnxMobPdnApnAggrRateDownlink specifies the downlink 
         aggregate maximum bit rate per Packet Data Network (PDN) for all non 
         Guaranteed Bit Rate (GBR) bearers for a given UE."
    DEFVAL { 0 }
    ::= { tmnxMobPdnApnEntry 32 }

tmnxMobPdnApnIdleTimeout  OBJECT-TYPE
    SYNTAX      Unsigned32 (0 | 300..3600)
    UNITS       "seconds"
    MAX-ACCESS  read-create
    STATUS      current
    DESCRIPTION
        "The value of tmnxMobPdnApnIdleTimeout specifies the amount of time, 
         in seconds, a bearer must be idle before it is released. Default bearer 
         cannot be released if dedicated bearer has not reached it's idle
         timeout value.

         If the value of this object is set to '0', then idle timout is 
         disabled."
    DEFVAL { 0 }
    ::= { tmnxMobPdnApnEntry 33 }

tmnxMobPdnApnSessionTimeout  OBJECT-TYPE
    SYNTAX      Unsigned32 (0 | 1800..86400)
    UNITS       "seconds"
    MAX-ACCESS  read-create
    STATUS      current
    DESCRIPTION
        "The value of tmnxMobPdnApnSessionTimeout specifies the timeout value, 
         in seconds, of a session. When a session timeout happens, all the 
         bearers related to the Packet Data Network (PDN) session will be 
         deleted.
         
         If the value of this object is set to '0', then idle timout is 
         disabled."
    DEFVAL { 86400 }
    ::= { tmnxMobPdnApnEntry 34 }

tmnxMobPdnApnRejectForeignSub  OBJECT-TYPE
    SYNTAX      TruthValue
    MAX-ACCESS  read-create
    STATUS      current
    DESCRIPTION
        "The value of tmnxMobPdnApnRejectForeignSub specifies if subscribers 
         from the home Public Land Mobile Network (PLMN) only should be allowed.

         If the value of this object is set to 'true', then subscribers 
         not in the home Public Land Mobile Network (PLMN) will be rejected."
    DEFVAL { false }
    ::= { tmnxMobPdnApnEntry 35 }

tmnxMobPdnApnBlockedPlmnList  OBJECT-TYPE
    SYNTAX      TmnxMobProfNameOrEmpty
    MAX-ACCESS  read-create
    STATUS      current
    DESCRIPTION
        "The value of tmnxMobPdnApnBlockedPlmnList specifies the list of 
         Public Land Mobile Networks (PLMNs) blocked on this
         Access Point Name (APN).
         
        If a corresponding PLMN list does not exist in
        TIMETRA-MOBILE-PROFILE-MIB::tmnxMobProfPlmnListTable,
        an 'inconsistentValue' error will be returned."
    DEFVAL { ''H }
    ::= { tmnxMobPdnApnEntry 36 }

tmnxMobPdnApnUliReporting  OBJECT-TYPE
    SYNTAX      TruthValue
    MAX-ACCESS  read-create
    STATUS      current
    DESCRIPTION
        "The value of tmnxMobPdnApnUliReporting specifies if a User Equipment's 
         (UE) User Location Info (ULI) change notification to a Packet Data 
         Network Gateway (PGW) from Mobility Management Entity (MME) is enabled 
         or not."
    DEFVAL { false }
    ::= { tmnxMobPdnApnEntry 37 }

tmnxMobPdnApnUmtsQosPolName  OBJECT-TYPE
    SYNTAX      TmnxMobProfNameOrEmpty 
    MAX-ACCESS  read-create
    STATUS      current
    DESCRIPTION
        "The value of tmnxMobPdnApnUmtsQosPolName specifies the name of 
         Universal Mobile Telecommunications System (UMTS) Quality of Service
         (QoS) Policy on this Access Point Name (APN).

         If a corresponding UMTS QoS policy profile does not exist in
         TIMETRA-MOBILE-PROFILE-MIB::tmnxMobUmtsQosPolTable,
         an 'inconsistentValue' error will be returned.

         If the mapping between pre-Rel-8 QoS parameter value pairs and QoS 
         Class Identifier (QCI) values is not 1-to-1 for this UMTS Qos Policy,
         an 'inconsistentValue' error will be returned."
    DEFVAL { ''H }
    ::= { tmnxMobPdnApnEntry 38 }

tmnxMobPdnApnPcrfDynPccFHSession  OBJECT-TYPE
    SYNTAX      TmnxEnabledDisabled
    MAX-ACCESS  read-create
    STATUS      current
    DESCRIPTION
        "The value of tmnxMobPdnApnPcrfDynPccFHSession specifies whether to 
         enable Failure-Handling Session when Policy and Charging Rules 
         Function (PCRF) is enabled. 

         When tmnxMobPdnApnPcrfDynPccFHSession is enabled, new sessions will be 
         allowed to set up even when both primary and secondary PCRF are down 
         or there is no secondary configuration and the primary PCRF goes down. 
         Such sessions will continue without any further PCRF control even when 
         PCRF recovers."
    DEFVAL { disabled }
    ::= { tmnxMobPdnApnEntry 39 }


--
--  APN Extension table
--

tmnxMobPdnApnExtTableLastChanged  OBJECT-TYPE
    SYNTAX      TimeStamp
    MAX-ACCESS  read-only
    STATUS      current
    DESCRIPTION
        "The value of tmnxMobPdnApnExtTableLastChanged indicates the sysUpTime 
         at the time of the last modification to tmnxMobPdnApnExtTable by
         adding, deleting an entry or change to a writable object in the table.

         If no changes were made to the table since the last re-initialization
         of the local network management subsystem, then this object contains
         a zero value."
    ::= { tmnxMobPdnGlobalObjs 10 }

tmnxMobPdnApnExtTable  OBJECT-TYPE
    SYNTAX      SEQUENCE OF TmnxMobPdnApnExtEntry
    MAX-ACCESS  not-accessible
    STATUS      current
    DESCRIPTION
        "The tmnxMobPdnApnExtTable has an entry for each Access Point Name 
         (APN). An APN identifies an external network that is accessible from a
         terminal.

         The tmnxMobPdnApnExtTable provides an extension of the 
         tmnxMobPdnApnTable."
    ::= { tmnxMobPdnConfObjs 10 }

tmnxMobPdnApnExtEntry  OBJECT-TYPE
    SYNTAX      TmnxMobPdnApnExtEntry
    MAX-ACCESS  not-accessible
    STATUS      current
    DESCRIPTION
        "Each row entry represents additional columns for attributes specific 
         to Access Point Name (APN) configuration."
    AUGMENTS { tmnxMobPdnApnEntry }
    ::= { tmnxMobPdnApnExtTable 1 }

TmnxMobPdnApnExtEntry ::= SEQUENCE {
        tmnxMobPdnApnExtLastChanged         TimeStamp,
        tmnxMobPdnApnDnsServerV4AddrType    InetAddressType,
        tmnxMobPdnApnDnsServerV4Addr        InetAddress,
        tmnxMobPdnApnDnsServerV6AddrType    InetAddressType,
        tmnxMobPdnApnDnsServerV6Addr        InetAddress,
        tmnxMobPdnApnDhcpRelayV4RouterId    TmnxVRtrID,
        tmnxMobPdnApnDhcpRlyV4GiAddrType    InetAddressType,
        tmnxMobPdnApnDhcpRelayV4GiAddr      InetAddress,
        tmnxMobPdnApnDhcpRelayV6RouterId    TmnxVRtrID,
        tmnxMobPdnApnDhcpRlyV6GiAddrType    InetAddressType,
        tmnxMobPdnApnDhcpRelayV6GiAddr      InetAddress,
        tmnxMobPdnApnDhcpProxyV4RouterId    TmnxVRtrID,
        tmnxMobPdnApnDhcpPxyV4GiAddrType    InetAddressType,
        tmnxMobPdnApnDhcpProxyV4GiAddr      InetAddress,
        tmnxMobPdnApnDhcpProxyV6RouterId    TmnxVRtrID,
        tmnxMobPdnApnDhcpPxyV6GiAddrType    InetAddressType,
        tmnxMobPdnApnDhcpProxyV6GiAddr      InetAddress,
        tmnxMobPdnApnPcoDnsV4PriAddrType    InetAddressType,
        tmnxMobPdnApnPcoDnsV4PriAddr        InetAddress,
        tmnxMobPdnApnPcoDnsV4SecAddrType    InetAddressType,
        tmnxMobPdnApnPcoDnsV4SecAddr        InetAddress,
        tmnxMobPdnApnPcoDnsV6PriAddrType    InetAddressType,
        tmnxMobPdnApnPcoDnsV6PriAddr        InetAddress,
        tmnxMobPdnApnPcoDnsV6SecAddrType    InetAddressType,
        tmnxMobPdnApnPcoDnsV6SecAddr        InetAddress,
        tmnxMobPdnApnPcoPcscfV4PriAdrTyp    InetAddressType,
        tmnxMobPdnApnPcoPcscfV4PriAddr      InetAddress,
        tmnxMobPdnApnPcoPcscfV6PriAdrTyp    InetAddressType,
        tmnxMobPdnApnPcoPcscfV6PriAddr      InetAddress,
        tmnxMobPdnApnPcoNbnsV4PriAdrType    InetAddressType,
        tmnxMobPdnApnPcoNbnsV4PriAddr       InetAddress,
        tmnxMobPdnApnPcoNbnsV4SecAdrType    InetAddressType,
        tmnxMobPdnApnPcoNbnsV4SecAddr       InetAddress,
        tmnxMobPdnApnPcoNbnsV6PriAdrType    InetAddressType,
        tmnxMobPdnApnPcoNbnsV6PriAddr       InetAddress,
        tmnxMobPdnApnPcoNbnsV6SecAdrType    InetAddressType,
        tmnxMobPdnApnPcoNbnsV6SecAddr       InetAddress
    }

tmnxMobPdnApnExtLastChanged  OBJECT-TYPE
    SYNTAX      TimeStamp
    MAX-ACCESS  read-only
    STATUS      current
    DESCRIPTION
        "The value of tmnxMobPdnApnExtLastChanged indicates the timestamp of
         the last change to this row in tmnxMobPdnApnExtTable."
    ::= { tmnxMobPdnApnExtEntry 1 }

tmnxMobPdnApnDnsServerV4AddrType  OBJECT-TYPE
    SYNTAX      InetAddressType
    MAX-ACCESS  read-create
    STATUS      current
    DESCRIPTION
        "The value of tmnxMobPdnApnDnsServerV4AddrType specifies the type of
         address represented by tmnxMobPdnApnDnsServerV4Addr."
    DEFVAL { unknown }
    ::= { tmnxMobPdnApnExtEntry 2 }

tmnxMobPdnApnDnsServerV4Addr  OBJECT-TYPE
    SYNTAX      InetAddress (SIZE (0|4))
    MAX-ACCESS  read-create
    STATUS      current
    DESCRIPTION
        "The value of tmnxMobPdnApnDnsServerV4Addr specifies the IPv4 address of
         the DNS server used for resolving the FQDN names of charging, Proxy 
         Call Session Control Function (P-CSCF )and Policy and Charging Rules 
         Function (PCRF) servers."
    DEFVAL { ''H }
    ::= { tmnxMobPdnApnExtEntry 3 }

tmnxMobPdnApnDnsServerV6AddrType  OBJECT-TYPE
    SYNTAX      InetAddressType
    MAX-ACCESS  read-create
    STATUS      current
    DESCRIPTION
        "The value of tmnxMobPdnApnDnsServerV6AddrType specifies the type of
         address represented by tmnxMobPdnApnDnsServerV6Addr."
    DEFVAL { unknown }
    ::= { tmnxMobPdnApnExtEntry 4 }

tmnxMobPdnApnDnsServerV6Addr  OBJECT-TYPE
    SYNTAX      InetAddress (SIZE (0|16))
    MAX-ACCESS  read-create
    STATUS      current
    DESCRIPTION
        "The value of tmnxMobPdnApnDnsServerV6Addr specifies the IPv6 address of
         the DNS server used for resolving the FQDN names of charging, Proxy 
         Call Session Control Function (P-CSCF )and Policy and Charging Rules 
         Function (PCRF) servers."
    DEFVAL { ''H }
    ::= { tmnxMobPdnApnExtEntry 5 }

tmnxMobPdnApnDhcpRelayV4RouterId  OBJECT-TYPE
    SYNTAX      TmnxVRtrID
    MAX-ACCESS  read-create
    STATUS      current
    DESCRIPTION
        "The value of tmnxMobPdnApnDhcpRelayV4RouterId specifies the virtual 
         router in which the DHCP requests or responses are sent or received to
         an external DHCP server."
    DEFVAL { 1 }
    ::= { tmnxMobPdnApnExtEntry 6 }

tmnxMobPdnApnDhcpRlyV4GiAddrType  OBJECT-TYPE
    SYNTAX      InetAddressType
    MAX-ACCESS  read-create
    STATUS      current
    DESCRIPTION
        "The value of tmnxMobPdnApnDhcpRlyV4GiAddrType specifies the type of
         address represented by tmnxMobPdnApnDhcpRelayV4GiAddr."
    DEFVAL { unknown }
    ::= { tmnxMobPdnApnExtEntry 7 }

tmnxMobPdnApnDhcpRelayV4GiAddr  OBJECT-TYPE
    SYNTAX      InetAddress (SIZE (0|4))
    MAX-ACCESS  read-create
    STATUS      current
    DESCRIPTION
        "The value of tmnxMobPdnApnDhcpRelayV4GiAddr specifies the subnet in
         which the DHCP server should return addresses for DHCP requests for 
         the User Equipments (UEs) entering a particular Packet Data Network 
         (PDN) access point. A corresponding IP loopback interface must be 
         configured in the Packet Data Network Gateway (PGW), in the same sub 
         network as the DHCP gateway address."
    DEFVAL { ''H }
    ::= { tmnxMobPdnApnExtEntry 8 }

tmnxMobPdnApnDhcpRelayV6RouterId  OBJECT-TYPE
    SYNTAX      TmnxVRtrID
    MAX-ACCESS  read-create
    STATUS      current
    DESCRIPTION
        "The value of tmnxMobPdnApnDhcpRelayV6RouterId specifies the virtual 
         router in which the DHCP requests or responses are sent or received to
         an external DHCP server."
    DEFVAL { 1 }
    ::= { tmnxMobPdnApnExtEntry 9 }

tmnxMobPdnApnDhcpRlyV6GiAddrType  OBJECT-TYPE
    SYNTAX      InetAddressType
    MAX-ACCESS  read-create
    STATUS      current
    DESCRIPTION
        "The value of tmnxMobPdnApnDhcpRlyV6GiAddrType specifies the type of
         address represented by tmnxMobPdnApnDhcpRelayV6GiAddr."
    DEFVAL { unknown }
    ::= { tmnxMobPdnApnExtEntry 10 }

tmnxMobPdnApnDhcpRelayV6GiAddr  OBJECT-TYPE
    SYNTAX      InetAddress (SIZE (0|16))
    MAX-ACCESS  read-create
    STATUS      current
    DESCRIPTION
        "The value of tmnxMobPdnApnDhcpRelayV6GiAddr specifies the subnet in
         which the DHCP server should return addresses for DHCP requests for 
         the User Equipments (UEs) entering a particular Packet Data Network 
         (PDN) access point. A corresponding IP loopback interface must be 
         configured in the Packet Data Network Gateway (PGW), in the same sub 
         network as the DHCP gateway address."
    DEFVAL { ''H }
    ::= { tmnxMobPdnApnExtEntry 11 }
    
tmnxMobPdnApnDhcpProxyV4RouterId  OBJECT-TYPE
    SYNTAX      TmnxVRtrID
    MAX-ACCESS  read-create
    STATUS      current
    DESCRIPTION
        "The value of tmnxMobPdnApnDhcpProxyV4RouterId specifies the virtual 
         router "
    DEFVAL { 1 }
    ::= { tmnxMobPdnApnExtEntry 12 }

tmnxMobPdnApnDhcpPxyV4GiAddrType  OBJECT-TYPE
    SYNTAX      InetAddressType
    MAX-ACCESS  read-create
    STATUS      current
    DESCRIPTION
        "The value of tmnxMobPdnApnDhcpPxyV4GiAddrType specifies the type of
         address represented by tmnxMobPdnApnDhcpProxyV4GiAddr."
    DEFVAL { unknown }
    ::= { tmnxMobPdnApnExtEntry 13 }

tmnxMobPdnApnDhcpProxyV4GiAddr  OBJECT-TYPE
    SYNTAX      InetAddress (SIZE (0|4))
    MAX-ACCESS  read-create
    STATUS      current
    DESCRIPTION
        "The value of tmnxMobPdnApnDhcpProxyV4GiAddr specifies the IPv4 address"
    DEFVAL { ''H }
    ::= { tmnxMobPdnApnExtEntry 14 }
    
tmnxMobPdnApnDhcpProxyV6RouterId  OBJECT-TYPE
    SYNTAX      TmnxVRtrID
    MAX-ACCESS  read-create
    STATUS      current
    DESCRIPTION
        "The value of tmnxMobPdnApnDhcpProxyV6RouterId specifies the virtual 
         router "
    DEFVAL { 1 }
    ::= { tmnxMobPdnApnExtEntry 15 }

tmnxMobPdnApnDhcpPxyV6GiAddrType  OBJECT-TYPE
    SYNTAX      InetAddressType
    MAX-ACCESS  read-create
    STATUS      current
    DESCRIPTION
        "The value of tmnxMobPdnApnDhcpPxyV6GiAddrType specifies the type of
         address represented by tmnxMobPdnApnDhcpProxyV6GiAddr."
    DEFVAL { unknown }
    ::= { tmnxMobPdnApnExtEntry 16 }

tmnxMobPdnApnDhcpProxyV6GiAddr  OBJECT-TYPE
    SYNTAX      InetAddress (SIZE (0|16))
    MAX-ACCESS  read-create
    STATUS      current
    DESCRIPTION
        "The value of tmnxMobPdnApnDhcpProxyV6GiAddr specifies the IPv6 address"
    DEFVAL { ''H }
    ::= { tmnxMobPdnApnExtEntry 17 }

tmnxMobPdnApnPcoDnsV4PriAddrType  OBJECT-TYPE
    SYNTAX      InetAddressType
    MAX-ACCESS  read-create
    STATUS      current
    DESCRIPTION
        "The value of tmnxMobPdnApnPcoDnsV4PriAddrType specifies the type of
         address represented by tmnxMobPdnApnPcoDnsV4PriAddr."
    DEFVAL { unknown }
    ::= { tmnxMobPdnApnExtEntry 18 }

tmnxMobPdnApnPcoDnsV4PriAddr  OBJECT-TYPE
    SYNTAX      InetAddress (SIZE (0|4))
    MAX-ACCESS  read-create
    STATUS      current
    DESCRIPTION
        "The value of tmnxMobPdnApnPcoDnsV4PriAddr specifies the IPv4 address
         of the primary DNS server used by a User Equipment (UE) to resolve 
         domain names to IP addresses."
    DEFVAL { ''H }
    ::= { tmnxMobPdnApnExtEntry 19 }
    
tmnxMobPdnApnPcoDnsV4SecAddrType  OBJECT-TYPE
    SYNTAX      InetAddressType
    MAX-ACCESS  read-create
    STATUS      current
    DESCRIPTION
        "The value of tmnxMobPdnApnPcoDnsV4SecAddrType specifies the type of
         address represented by tmnxMobPdnApnPcoDnsV4SecAddr."
    DEFVAL { unknown }
    ::= { tmnxMobPdnApnExtEntry 20 }

tmnxMobPdnApnPcoDnsV4SecAddr  OBJECT-TYPE
    SYNTAX      InetAddress (SIZE (0|4))
    MAX-ACCESS  read-create
    STATUS      current
    DESCRIPTION
        "The value of tmnxMobPdnApnPcoDnsV4SecAddr specifies the IPv4 address
         of the secondary DNS server used by a User Equipment (UE) to resolve 
         domain names to IP addresses."
    DEFVAL { ''H }
    ::= { tmnxMobPdnApnExtEntry 21 }

tmnxMobPdnApnPcoDnsV6PriAddrType  OBJECT-TYPE
    SYNTAX      InetAddressType
    MAX-ACCESS  read-create
    STATUS      current
    DESCRIPTION
        "The value of tmnxMobPdnApnPcoDnsV6PriAddrType specifies the type of
         address represented by tmnxMobPdnApnPcoDnsV6PriAddr."
    DEFVAL { unknown }
    ::= { tmnxMobPdnApnExtEntry 22 }

tmnxMobPdnApnPcoDnsV6PriAddr  OBJECT-TYPE
    SYNTAX      InetAddress (SIZE (0|16))
    MAX-ACCESS  read-create
    STATUS      current
    DESCRIPTION
        "The value of tmnxMobPdnApnPcoDnsV6PriAddr specifies the IPv6 address
         of the primary DNS server used by a User Equipment (UE) to resolve 
         domain names to IP addresses."
    DEFVAL { ''H }
    ::= { tmnxMobPdnApnExtEntry 23 }
    
tmnxMobPdnApnPcoDnsV6SecAddrType  OBJECT-TYPE
    SYNTAX      InetAddressType
    MAX-ACCESS  read-create
    STATUS      current
    DESCRIPTION
        "The value of tmnxMobPdnApnPcoDnsV6SecAddrType specifies the type of
         address represented by tmnxMobPdnApnPcoDnsV6SecAddr."
    DEFVAL { unknown }
    ::= { tmnxMobPdnApnExtEntry 24 }

tmnxMobPdnApnPcoDnsV6SecAddr  OBJECT-TYPE
    SYNTAX      InetAddress (SIZE (0|16))
    MAX-ACCESS  read-create
    STATUS      current
    DESCRIPTION
        "The value of tmnxMobPdnApnPcoDnsV6SecAddr specifies the IPv6 address
         of the secondary DNS server used by a User Equipment (UE) to resolve 
         domain names to IP addresses."
    DEFVAL { ''H }
    ::= { tmnxMobPdnApnExtEntry 25 }

tmnxMobPdnApnPcoPcscfV4PriAdrTyp  OBJECT-TYPE
    SYNTAX      InetAddressType
    MAX-ACCESS  read-create
    STATUS      current
    DESCRIPTION
        "The value of tmnxMobPdnApnPcoPcscfV4PriAdrTyp specifies the type of
         address represented by tmnxMobPdnApnPcoPcscfV4PriAddr."
    DEFVAL { unknown }
    ::= { tmnxMobPdnApnExtEntry 26 }

tmnxMobPdnApnPcoPcscfV4PriAddr  OBJECT-TYPE
    SYNTAX      InetAddress
    MAX-ACCESS  read-create
    STATUS      current
    DESCRIPTION
        "The value of tmnxMobPdnApnPcoPcscfV4PriAddr specifies the IPv4 address
         or FQDN of the primary Proxy Call Session Control Function (PCSCF) 
         server used by a User Equipment (UE) to reach a IMS server for Session 
         Initiation Protocol (SIP) applications."
    DEFVAL { ''H }
    ::= { tmnxMobPdnApnExtEntry 27 }

tmnxMobPdnApnPcoPcscfV6PriAdrTyp  OBJECT-TYPE
    SYNTAX      InetAddressType
    MAX-ACCESS  read-create
    STATUS      current
    DESCRIPTION
        "The value of tmnxMobPdnApnPcoPcscfV6PriAdrTyp specifies the type of
         address represented by tmnxMobPdnApnPcoDnsV6PriAddr."
    DEFVAL { unknown }
    ::= { tmnxMobPdnApnExtEntry 28 }

tmnxMobPdnApnPcoPcscfV6PriAddr  OBJECT-TYPE
    SYNTAX      InetAddress
    MAX-ACCESS  read-create
    STATUS      current
    DESCRIPTION
        "The value of tmnxMobPdnApnPcoPcscfV6PriAddr specifies the IPv6 address
         or FQDN of the primary Proxy Call Session Control Function (PCSCF) 
         server used by a User Equipment (UE) to reach a IMS server for Session 
         Initiation Protocol (SIP) applications."
    DEFVAL { ''H }
    ::= { tmnxMobPdnApnExtEntry 29 }

tmnxMobPdnApnPcoNbnsV4PriAdrType  OBJECT-TYPE
    SYNTAX      InetAddressType
    MAX-ACCESS  read-create
    STATUS      current
    DESCRIPTION
        "The value of tmnxMobPdnApnPcoNbnsV4PriAdrType specifies the type of
         address represented by tmnxMobPdnApnPcoNbnsV4PriAddr."
    DEFVAL { unknown }
    ::= { tmnxMobPdnApnExtEntry 30 }

tmnxMobPdnApnPcoNbnsV4PriAddr  OBJECT-TYPE
    SYNTAX      InetAddress (SIZE (0|4))
    MAX-ACCESS  read-create
    STATUS      current
    DESCRIPTION
        "The value of tmnxMobPdnApnPcoNbnsV4PriAddr specifies the IPv4 address
         of the primary netbios Name Service (NBNS) server used by Microsoft 
         Netbios clients to reach netbios servers."
    DEFVAL { ''H }
    ::= { tmnxMobPdnApnExtEntry 31 }
    
tmnxMobPdnApnPcoNbnsV4SecAdrType  OBJECT-TYPE
    SYNTAX      InetAddressType
    MAX-ACCESS  read-create
    STATUS      current
    DESCRIPTION
        "The value of tmnxMobPdnApnPcoNbnsV4SecAdrType specifies the type of
         address represented by tmnxMobPdnApnPcoNbnsV4SecAddr."
    DEFVAL { unknown }
    ::= { tmnxMobPdnApnExtEntry 32 }

tmnxMobPdnApnPcoNbnsV4SecAddr  OBJECT-TYPE
    SYNTAX      InetAddress (SIZE (0|4))
    MAX-ACCESS  read-create
    STATUS      current
    DESCRIPTION
        "The value of tmnxMobPdnApnPcoNbnsV4SecAddr specifies the IPv4 address
         of the secondary netbios Name Service (NBNS) server used by Microsoft 
         Netbios clients to reach netbios servers."
    DEFVAL { ''H }
    ::= { tmnxMobPdnApnExtEntry 33 }

tmnxMobPdnApnPcoNbnsV6PriAdrType  OBJECT-TYPE
    SYNTAX      InetAddressType
    MAX-ACCESS  read-create
    STATUS      current
    DESCRIPTION
        "The value of tmnxMobPdnApnPcoNbnsV6PriAdrType specifies the type of
         address represented by tmnxMobPdnApnPcoNbnsV6PriAddr."
    DEFVAL { unknown }
    ::= { tmnxMobPdnApnExtEntry 34 }

tmnxMobPdnApnPcoNbnsV6PriAddr  OBJECT-TYPE
    SYNTAX      InetAddress (SIZE (0|16))
    MAX-ACCESS  read-create
    STATUS      current
    DESCRIPTION
        "The value of tmnxMobPdnApnPcoNbnsV6PriAddr specifies the IPv6 address
         of the primary netbios Name Service (NBNS) server used by Microsoft 
         Netbios clients to reach netbios servers."
    DEFVAL { ''H }
    ::= { tmnxMobPdnApnExtEntry 35 }
    
tmnxMobPdnApnPcoNbnsV6SecAdrType  OBJECT-TYPE
    SYNTAX      InetAddressType
    MAX-ACCESS  read-create
    STATUS      current
    DESCRIPTION
        "The value of tmnxMobPdnApnPcoNbnsV6SecAdrType specifies the type of
         address represented by tmnxMobPdnApnPcoNbnsV6SecAddr."
    DEFVAL { unknown }
    ::= { tmnxMobPdnApnExtEntry 36 }

tmnxMobPdnApnPcoNbnsV6SecAddr  OBJECT-TYPE
    SYNTAX      InetAddress (SIZE (0|16))
    MAX-ACCESS  read-create
    STATUS      current
    DESCRIPTION
        "The value of tmnxMobPdnApnPcoNbnsV6SecAddr specifies the IPv6 address
         of the secondary netbios Name Service (NBNS) server used by Microsoft 
         Netbios clients to reach netbios servers."
    DEFVAL { ''H }
    ::= { tmnxMobPdnApnExtEntry 37 }
    
--
--  APN Extension-2 table
--

tmnxMobPdnApnExt2TableLastChangd  OBJECT-TYPE
    SYNTAX      TimeStamp
    MAX-ACCESS  read-only
    STATUS      current
    DESCRIPTION
        "The value of tmnxMobPdnApnExt2TableLastChangd indicates the sysUpTime 
         at the time of the last modification to tmnxMobPdnApnExt2Table by
         adding, deleting an entry or change to a writable object in the table.

         If no changes were made to the table since the last re-initialization
         of the local network management subsystem, then this object contains
         a zero value."
    ::= { tmnxMobPdnGlobalObjs 11 }

tmnxMobPdnApnExt2Table  OBJECT-TYPE
    SYNTAX      SEQUENCE OF TmnxMobPdnApnExt2Entry
    MAX-ACCESS  not-accessible
    STATUS      current
    DESCRIPTION
        "The tmnxMobPdnApnExt2Table has an entry for each Access Point Name 
         (APN). An APN identifies an external network that is accessible from a
         terminal.

         The tmnxMobPdnApnExt2Table provides an extension of the 
         tmnxMobPdnApnTable."
    ::= { tmnxMobPdnConfObjs 11 }

tmnxMobPdnApnExt2Entry  OBJECT-TYPE
    SYNTAX      TmnxMobPdnApnExt2Entry
    MAX-ACCESS  not-accessible
    STATUS      current
    DESCRIPTION
        "Each row entry represents additional columns for attributes specific 
         to Access Point Name (APN) configuration."
    AUGMENTS { tmnxMobPdnApnEntry }
    ::= { tmnxMobPdnApnExt2Table 1 }

TmnxMobPdnApnExt2Entry ::= SEQUENCE {
        tmnxMobPdnApnExt2LastChanged        TimeStamp,
        tmnxMobPdnApnChrgProfileHome        TmnxMobChargingProfileOrInherit,
        tmnxMobPdnApnChrgProfileVisiting    TmnxMobChargingProfileOrInherit,
        tmnxMobPdnApnChrgProfileRoaming     TmnxMobChargingProfileOrInherit,
        tmnxMobPdnApnChrgCcIgnoreAny        TmnxEnabledDisabledOrInherit,
        tmnxMobPdnApnChrgCcIgnoreHome       TmnxEnabledDisabledOrInherit,
        tmnxMobPdnApnChrgCcIgnoreVisit      TmnxEnabledDisabledOrInherit,
        tmnxMobPdnApnChrgCcIgnoreRoaming    TmnxEnabledDisabledOrInherit,
        tmnxMobPdnApnCdfPriDiaPeer          TmnxMobProfNameOrEmpty,
        tmnxMobPdnApnCdfSecDiaPeer          TmnxMobProfNameOrEmpty,
        tmnxMobPdnApnPreAuthType            TmnxMobAuthType,
        tmnxMobPdnApnPreAuthUserName        TmnxMobAuthUserName,
        tmnxMobPdnApnAuthType               TmnxMobAuthType,
        tmnxMobPdnApnAuthUserName           INTEGER,
        tmnxMobPdnApnAcctType               TmnxMobAuthType,
        tmnxMobPdnApnAcctUserName           TmnxMobAuthUserName,
        tmnxMobPdnApnAcctInterimReport      TmnxEnabledDisabledOrInherit,
        tmnxMobPdnApnChrgCcReject           TmnxEnabledDisabledOrInherit,
        tmnxMobPdnApnAuthServerGroup        TmnxMobProfNameOrEmpty,
        tmnxMobPdnApnAuthAcctSupImsi        TmnxEnabledDisabled,
        tmnxMobPdnApnAcctServerGroup        TmnxMobProfNameOrEmpty,
        tmnxMobPdnApnWaitAccounting         TmnxEnabledDisabled,
        tmnxMobPdnApnOcsPriDiaPeer          TmnxMobProfNameOrEmpty,
        tmnxMobPdnApnOcsSecDiaPeer          TmnxMobProfNameOrEmpty,
        tmnxMobPdnApnGyDccaProfile          TmnxMobProfNameOrEmpty,
        tmnxMobPdnApnPreAuthServerGroup     TmnxMobProfNameOrEmpty,
        tmnxMobPdnApnChangeRepAction        INTEGER,
        tmnxMobPdnApnSuppFramedRoute        TruthValue,
        tmnxMobPdnApnPccQciValue            TmnxMobQciValueOrZero,
        tmnxMobPdnApnPccArpValue            TmnxMobArpValueOrZero,
        tmnxMobPdnApnAuthFixUserName        TNamedItemOrEmpty,
        tmnxMobPdnApnAuthFixPassword        TNamedItemOrEmpty
    }

tmnxMobPdnApnExt2LastChanged  OBJECT-TYPE
    SYNTAX      TimeStamp
    MAX-ACCESS  read-only
    STATUS      current
    DESCRIPTION
        "The value of tmnxMobPdnApnExt2LastChanged indicates the timestamp of
         the last change to this row in tmnxMobPdnApnExt2Table."
    ::= { tmnxMobPdnApnExt2Entry 1 }

tmnxMobPdnApnChrgProfileHome  OBJECT-TYPE
    SYNTAX      TmnxMobChargingProfileOrInherit
    MAX-ACCESS  read-create
    STATUS      current
    DESCRIPTION
        "The value of tmnxMobPdnApnChrgProfileHome specifies the charging 
         trigger rules applied for generating Charging Data Records (CDR) for 
         home subscribers.

         If a corresponding charging profile does not exist in
         TIMETRA-MOBILE-PROFILE-MIB::tmnxMobProfPgwChargingTable, 
         an 'inconsistentValue' error will be returned.

         A value of '-1' specifies that charging profile information is
         inherited from the value of tmnxMobPdnChargingProfHome which specifies
         the charging trigger rules applied for home subscribers at the gateway
         level."
    DEFVAL { -1 }
    ::= { tmnxMobPdnApnExt2Entry 2 }

tmnxMobPdnApnChrgProfileVisiting  OBJECT-TYPE
    SYNTAX      TmnxMobChargingProfileOrInherit
    MAX-ACCESS  read-create
    STATUS      current
    DESCRIPTION
        "The value of tmnxMobPdnApnChrgProfileVisiting specifies the visiting 
         charging trigger rules applied for generating Charging Data Records 
         (CDR) for visiting subscribers.

         If a corresponding charging profile does not exist in
         TIMETRA-MOBILE-PROFILE-MIB::tmnxMobProfPgwChargingTable,
         an 'inconsistentValue' error will be returned.

         A value of '-1' specifies that charging profile information is
         inherited from the value of tmnxMobPdnChargingProfVisiting which 
         specifies the charging trigger rules applied for visiting subscribers
         at the gateway level."
    DEFVAL { -1 }
    ::= { tmnxMobPdnApnExt2Entry 3 }

tmnxMobPdnApnChrgProfileRoaming  OBJECT-TYPE
    SYNTAX      TmnxMobChargingProfileOrInherit
    MAX-ACCESS  read-create
    STATUS      current
    DESCRIPTION
        "The value of tmnxMobPdnApnChrgProfileRoaming specifies the charging 
         trigger rules applied for generating Charging Data Records (CDR) for 
         roaming subscribers.

         If a corresponding charging profile does not exist in
         TIMETRA-MOBILE-PROFILE-MIB::tmnxMobProfPgwChargingTable,
         an 'inconsistentValue' error will be returned.

         A value of '-1' specifies that charging profile information is
         inherited from the value of tmnxMobPdnChargingProfRoaming which 
         specifies the charging trigger rules applied for roaming subscribers
         at the gateway level."
    DEFVAL { -1 }
    ::= { tmnxMobPdnApnExt2Entry 4 }

tmnxMobPdnApnChrgCcIgnoreAny  OBJECT-TYPE
    SYNTAX      TmnxEnabledDisabledOrInherit
    MAX-ACCESS  read-create
    STATUS      current
    DESCRIPTION
        "The value of tmnxMobPdnApnChrgCcIgnoreAny specifies to ignore 
         HSS or MME supplied charging characteristics for any subscriber. 
         Corresponding default profile is selected when the received charging 
         characteristics is ignored.

         When the value of tmnxMobPdnApnChrgCcIgnoreAny is 'inherit', the value 
         is inherited from the value of tmnxMobPdnChrgCcIgnoreAny which 
         specifies to ignore HSS or MME supplied charging characteristics for 
         any subscriber at the gateway level."
    DEFVAL { inherit }
    ::= { tmnxMobPdnApnExt2Entry 5 }

tmnxMobPdnApnChrgCcIgnoreHome  OBJECT-TYPE
    SYNTAX      TmnxEnabledDisabledOrInherit
    MAX-ACCESS  read-create
    STATUS      current
    DESCRIPTION
        "The value of tmnxMobPdnApnChrgCcIgnoreHome specifies to ignore 
         HSS or MME supplied charging characteristics for home scenarios. 
         Corresponding default profile is selected when the received charging 
         characteristics is ignored.

         When the value of tmnxMobPdnApnChrgCcIgnoreHome is 'inherit', the value 
         is inherited from the value of tmnxMobPdnChrgCcIgnoreHome which 
         specifies to ignore HSS or MME supplied charging characteristics for 
         home scenarios at the gateway level."
    DEFVAL { inherit }
    ::= { tmnxMobPdnApnExt2Entry 6 }

tmnxMobPdnApnChrgCcIgnoreVisit  OBJECT-TYPE
    SYNTAX      TmnxEnabledDisabledOrInherit
    MAX-ACCESS  read-create
    STATUS      current
    DESCRIPTION
        "The value of tmnxMobPdnApnChrgCcIgnoreVisit specifies to ignore 
         HSS or MME supplied charging characteristics for visiting scenarios. 
         Corresponding default profile is selected when the received charging 
         characteristics is ignored.

         When the value of tmnxMobPdnApnChrgCcIgnoreVisit is 'inherit', the
         value is inherited from the value of tmnxMobPdnChrgCcIgnoreVisiting
         which specifies to ignore HSS or MME supplied charging characteristics
         for visiting scenarios at the gateway level."
    DEFVAL { inherit }
    ::= { tmnxMobPdnApnExt2Entry 7 }

tmnxMobPdnApnChrgCcIgnoreRoaming  OBJECT-TYPE
    SYNTAX      TmnxEnabledDisabledOrInherit
    MAX-ACCESS  read-create
    STATUS      current
    DESCRIPTION
        "The value of tmnxMobPdnApnChrgCcIgnoreRoaming specifies to ignore 
         HSS or MME supplied charging characteristics for roaming scenarios. 
         Corresponding default profile is selected when the received charging 
         characteristics is ignored.

         When the value of tmnxMobPdnApnChrgCcIgnoreRoaming is 'inherit', the
         value is inherited from the value of tmnxMobPdnChrgCcIgnoreRoaming
         which specifies to ignore HSS or MME supplied charging characteristics
         for roaming scenarios at the gateway level."
    DEFVAL { inherit }
    ::= { tmnxMobPdnApnExt2Entry 8 }
    
tmnxMobPdnApnCdfPriDiaPeer  OBJECT-TYPE
    SYNTAX      TmnxMobProfNameOrEmpty
    MAX-ACCESS  read-create
    STATUS      current
    DESCRIPTION
        "The value of tmnxMobPdnApnCdfPriDiaPeer specifies the diameter peer 
         profile to be used for the primary Charging Data Function (CDF).

         If a corresponding diameter peer profile does not exist in
         TIMETRA-MOBILE-PROFILE-MIB::tmnxMobProfDiaPeerTable,
         an 'inconsistentValue' error will be returned."
    DEFVAL { ''H }
    ::= { tmnxMobPdnApnExt2Entry 9 }

tmnxMobPdnApnCdfSecDiaPeer  OBJECT-TYPE
    SYNTAX      TmnxMobProfNameOrEmpty
    MAX-ACCESS  read-create
    STATUS      current
    DESCRIPTION
        "The value of tmnxMobPdnApnCdfSecDiaPeer specifies the diameter peer 
         profile to be used for the secondary Charging Data Function (CDF).

         If a corresponding diameter peer profile does not exist in
         TIMETRA-MOBILE-PROFILE-MIB::tmnxMobProfDiaPeerTable,
         an 'inconsistentValue' error will be returned."
    DEFVAL { ''H }
    ::= { tmnxMobPdnApnExt2Entry 10 }

tmnxMobPdnApnPreAuthType  OBJECT-TYPE
    SYNTAX      TmnxMobAuthType
    MAX-ACCESS  read-create
    STATUS      current
    DESCRIPTION
        "The value of tmnxMobPdnApnPreAuthType specifies the authentication 
         type used for pre-authentication from a AAA server."
    DEFVAL { radius }
    ::= { tmnxMobPdnApnExt2Entry 11 }

tmnxMobPdnApnPreAuthUserName  OBJECT-TYPE
    SYNTAX      TmnxMobAuthUserName
    MAX-ACCESS  read-create
    STATUS      current
    DESCRIPTION
        "The value of tmnxMobPdnApnPreAuthUserName specifies the user name 
         used in access requests sent to a AAA server."
    DEFVAL { imsi }
    ::= { tmnxMobPdnApnExt2Entry 12 }

tmnxMobPdnApnAuthType  OBJECT-TYPE
    SYNTAX      TmnxMobAuthType
    MAX-ACCESS  read-create
    STATUS      current
    DESCRIPTION
        "The value of tmnxMobPdnApnAuthType specifies the authentication 
         type used for authentication from a AAA server."
    DEFVAL { radius }
    ::= { tmnxMobPdnApnExt2Entry 13}

tmnxMobPdnApnAuthUserName  OBJECT-TYPE
    SYNTAX      INTEGER {
                          imsi    (1),
                          msisdn  (2),
                          pco     (3),
                          fixed   (4)
                         }
    MAX-ACCESS  read-create
    STATUS      current
    DESCRIPTION
        "The value of tmnxMobPdnApnAuthUserName specifies the user name 
         used in access requests sent to a AAA server."
    DEFVAL { imsi }
    ::= { tmnxMobPdnApnExt2Entry 14 }
    
tmnxMobPdnApnAcctType  OBJECT-TYPE
    SYNTAX      TmnxMobAuthType
    MAX-ACCESS  read-create
    STATUS      current
    DESCRIPTION
        "The value of tmnxMobPdnApnAcctType specifies the accounting 
         type used for accounting purposes."
    DEFVAL { radius }
    ::= { tmnxMobPdnApnExt2Entry 15 }

tmnxMobPdnApnAcctUserName  OBJECT-TYPE
    SYNTAX      TmnxMobAuthUserName
    MAX-ACCESS  read-create
    STATUS      current
    DESCRIPTION
        "The value of tmnxMobPdnApnAcctUserName specifies the user name 
         used in requests sent to a AAA server for accounting purposes."
    DEFVAL { imsi }
    ::= { tmnxMobPdnApnExt2Entry 16}

tmnxMobPdnApnAcctInterimReport  OBJECT-TYPE
    SYNTAX      TmnxEnabledDisabledOrInherit
    MAX-ACCESS  read-create
    STATUS      current
    DESCRIPTION
        "The value of tmnxMobPdnApnAcctInterimReport specifies whether to enable
         the periodic reporting of accounting usage stats per bearer."
    DEFVAL { enabled }
    ::= { tmnxMobPdnApnExt2Entry 17 }

tmnxMobPdnApnChrgCcReject  OBJECT-TYPE
    SYNTAX      TmnxEnabledDisabledOrInherit
    MAX-ACCESS  read-create
    STATUS      current
    DESCRIPTION
        "The value of tmnxMobPdnApnChrgCcReject specifies to reject HSS or MME
         supplied charging characteristics for a subscriber. 
         Corresponding default chargin profile is selected when the value of 
         this object is set to 'disable'.

         The value of tmnxMobPdnApnChrgCcReject is applicable only when the HSS
         or MME supplied charging characteristics are not ignored.

         When the value of tmnxMobPdnApnChrgCcReject is 'inherit', the
         value is inherited from the value of tmnxMobPdnChrgCcReject which 
         specifies to reject HSS or MME supplied charging characteristics for
         a subscriber at the gateway level."        
    DEFVAL { inherit }
    ::= { tmnxMobPdnApnExt2Entry 18 }   

tmnxMobPdnApnAuthServerGroup  OBJECT-TYPE
    SYNTAX      TmnxMobProfNameOrEmpty
    MAX-ACCESS  read-create
    STATUS      current
    DESCRIPTION
        "The value of tmnxMobPdnApnAuthServerGroup specifies the radius group 
         profile to be used for the authentication.

         If a corresponding radius group profile does not exist in
         TIMETRA-MOBILE-PROFILE-MIB::tmnxMobProfRadGrpTable,
         an 'inconsistentValue' error will be returned."
    DEFVAL { ''H }
    ::= { tmnxMobPdnApnExt2Entry 19 }

tmnxMobPdnApnAuthAcctSupImsi  OBJECT-TYPE
    SYNTAX      TmnxEnabledDisabled
    MAX-ACCESS  read-create
    STATUS      obsolete
    DESCRIPTION
        "The value of tmnxMobPdnApnAuthAcctSupImsi specifies to remove the 
         3GPP-IMSI attribute when sending an authentication or accounting 
         message.

         When the value of tmnxMobPdnApnAuthAcctSupImsi is not specifed, 
         the 3GPP-IMSI attribute shall be sent.

         This object was made obsolete in the 3.0R5 release.
         "
    DEFVAL { disabled }
    ::= { tmnxMobPdnApnExt2Entry 20 }

tmnxMobPdnApnAcctServerGroup  OBJECT-TYPE
    SYNTAX      TmnxMobProfNameOrEmpty
    MAX-ACCESS  read-create
    STATUS      current
    DESCRIPTION
        "The value of tmnxMobPdnApnAcctServerGroup specifies the radius group 
         profile to be used for the accouting message.

         If a corresponding radius group profile does not exist in
         TIMETRA-MOBILE-PROFILE-MIB::tmnxMobProfRadGrpTable,
         an 'inconsistentValue' error will be returned."
    DEFVAL { ''H }
    ::= { tmnxMobPdnApnExt2Entry 21 }

tmnxMobPdnApnWaitAccounting  OBJECT-TYPE
    SYNTAX      TmnxEnabledDisabled
    MAX-ACCESS  read-create
    STATUS      current
    DESCRIPTION
        "The value of tmnxMobPdnApnWaitAccounting specifies to configure the 
         PGW/GGSN to wait for an accounting response before sending a GPRS 
         Tunneling Protocol (GTP) response.
                 
         When the value of tmnxMobPdnApnWaitAccounting is not specifed, 
         the PGW/GGSN shall not wait for a response."
    DEFVAL { disabled }
    ::= { tmnxMobPdnApnExt2Entry 22 }

tmnxMobPdnApnOcsPriDiaPeer  OBJECT-TYPE
    SYNTAX      TmnxMobProfNameOrEmpty
    MAX-ACCESS  read-create
    STATUS      current
    DESCRIPTION
        "The value of tmnxMobPdnApnOcsPriDiaPeer specifies the diameter peer 
         profile to be used for the primary Online Charging System (OCS).

         The value of tmnxMobPdnApnOcsPriDiaPeer at the APN level overrides the
         value of tmnxMobPdnGyPriDiaPeer at the gateway level."
    DEFVAL { ''H }
    ::= { tmnxMobPdnApnExt2Entry 23 }

tmnxMobPdnApnOcsSecDiaPeer  OBJECT-TYPE
    SYNTAX      TmnxMobProfNameOrEmpty
    MAX-ACCESS  read-create
    STATUS      current
    DESCRIPTION
        "The value of tmnxMobPdnApnOcsSecDiaPeer specifies the diameter peer 
         profile to be used for the secondary Online Charging System (OCS).

         The value of tmnxMobPdnApnOcsSecDiaPeer at the APN level overrides the
         value of tmnxMobPdnGySecDiaPeer at the gateway level."
    DEFVAL { ''H }
    ::= { tmnxMobPdnApnExt2Entry 24 }

tmnxMobPdnApnGyDccaProfile  OBJECT-TYPE
    SYNTAX      TmnxMobProfNameOrEmpty
    MAX-ACCESS  read-create
    STATUS      current
    DESCRIPTION
        "The value of tmnxMobPdnApnGyDccaProfile specifies Diameter Credit
         Control Application (DCCA) profile used for the primary and secondary 
         Online Charging System (OCS) for this APN."
    DEFVAL { ''H }
    ::= { tmnxMobPdnApnExt2Entry 25 }

tmnxMobPdnApnPreAuthServerGroup  OBJECT-TYPE
    SYNTAX      TmnxMobProfNameOrEmpty
    MAX-ACCESS  read-create
    STATUS      current
    DESCRIPTION
        "The value of tmnxMobPdnApnPreAuthServerGroup specifies the radius
        group profile to be used for the pre-authentication.

         If a corresponding radius group profile does not exist in
         TIMETRA-MOBILE-PROFILE-MIB::tmnxMobProfRadGrpTable,
         an 'inconsistentValue' error will be returned."
    DEFVAL { ''H }
    ::= { tmnxMobPdnApnExt2Entry 26 }

tmnxMobPdnApnChangeRepAction  OBJECT-TYPE
    SYNTAX      INTEGER {
                         none       (0),   
                         cgiSai     (1),
                         rai        (2),
                         cgiSaiRai  (3),
                         tai        (4),
                         egci       (5),
                         taiEgci    (6)
                        }
    MAX-ACCESS  read-create
    STATUS      current
    DESCRIPTION
        "The value of tmnxMobPdnApnChangeRepAction specifies which kind of 
         location based reporting is enabled."
    DEFVAL { none }
    ::= { tmnxMobPdnApnExt2Entry 27 }

tmnxMobPdnApnSuppFramedRoute  OBJECT-TYPE
    SYNTAX      TruthValue
    MAX-ACCESS  read-create
    STATUS      current
    DESCRIPTION
        "The value of tmnxMobPdnApnSuppFramedRoute specifies whether the 
         Framed-Route attribute is enabled. This enables the GGSN to support
         set of subnets behind the User Equipment (UE)."
    DEFVAL { false }
    ::= { tmnxMobPdnApnExt2Entry 28 }

tmnxMobPdnApnPccQciValue  OBJECT-TYPE
    SYNTAX      TmnxMobQciValueOrZero
    MAX-ACCESS  read-create
    STATUS      current
    DESCRIPTION
        "The value of tmnxMobPdnApnPccQciValue specifies a reference to access
         a set of node-specific parameters that control bearer level QoS packet
         forwarding treatment. Internally, this value is mapped to Forwarding
         Class (FC) within the mobile gateway system."
    DEFVAL { 0 }
    ::= { tmnxMobPdnApnExt2Entry 29 }

tmnxMobPdnApnPccArpValue  OBJECT-TYPE
    SYNTAX      TmnxMobArpValueOrZero
    MAX-ACCESS  read-create
    STATUS      current
    DESCRIPTION
        "The value of tmnxMobPdnApnPccArpValue specifies the admission control
         to prioritize allocation and retention for bearer establishment and
         modification."
    DEFVAL { 0 }
    ::= { tmnxMobPdnApnExt2Entry 30 }

tmnxMobPdnApnAuthFixUserName  OBJECT-TYPE
    SYNTAX        TNamedItemOrEmpty
    MAX-ACCESS    read-create
    STATUS        current
    DESCRIPTION  
         "The value of tmnxMobPdnApnAuthFixUserName specifies the user name 
          used in access requests sent to a AAA server when tmnxMobPdnApnAuthUserName
          is set to 'fixed'."
    DEFVAL { "default" } 
    ::= { tmnxMobPdnApnExt2Entry 31 }        
         
tmnxMobPdnApnAuthFixPassword  OBJECT-TYPE
    SYNTAX        TNamedItemOrEmpty
    MAX-ACCESS    read-create
    STATUS        current
    DESCRIPTION  
         "The value of tmnxMobPdnApnAuthFixPassword specifies the password used to
          authenticate requests sent to a AAA server when the user name is sent by 
          setting tmnxMobPdnApnAuthFixUserName and tmnxMobPdnApnAuthUserName is
          set to 'fixed'.

          This object will always return an empty string on a read." 
    DEFVAL { ''H } 
    ::= { tmnxMobPdnApnExt2Entry 32 }        

--
--  APN IP pool table
--

tmnxMobPdnApnIpPoolTableLastChgd  OBJECT-TYPE
    SYNTAX      TimeStamp
    MAX-ACCESS  read-only
    STATUS      current
    DESCRIPTION
        "The value of tmnxMobPdnApnIpPoolTableLastChgd indicates the sysUpTime 
         at the time of the last modification to tmnxMobPdnApnIpPoolTable by
         adding, deleting an entry or change to a writable object in the table.

         If no changes were made to the table since the last re-initialization
         of the local network management subsystem, then this object contains
         a zero value."
    ::= { tmnxMobPdnGlobalObjs 12 }

tmnxMobPdnApnIpPoolTable  OBJECT-TYPE
    SYNTAX      SEQUENCE OF TmnxMobPdnApnIpPoolEntry
    MAX-ACCESS  not-accessible
    STATUS      current
    DESCRIPTION
        "The tmnxMobPdnApnIpPoolTable has an entry for each IP pool configured 
         for an Access Point Name (APN).

         A maximum of 8 IP pools can be configured for each APN."
    ::= { tmnxMobPdnConfObjs 12 }

tmnxMobPdnApnIpPoolEntry  OBJECT-TYPE
    SYNTAX      TmnxMobPdnApnIpPoolEntry
    MAX-ACCESS  not-accessible
    STATUS      current
    DESCRIPTION
        "Each row entry represents an IP pool in an Access Point Name (APN). 
         Entries can be created and deleted by the user."
    INDEX { tmnxMobGwId,
            tmnxMobPdnApnName,
            vRtrID,
            vRtrIpPoolName
          }
    ::= { tmnxMobPdnApnIpPoolTable 1 }

TmnxMobPdnApnIpPoolEntry ::= SEQUENCE {
        tmnxMobPdnApnIpPoolRowStatus  RowStatus
    }

tmnxMobPdnApnIpPoolRowStatus  OBJECT-TYPE
    SYNTAX      RowStatus
    MAX-ACCESS  read-create
    STATUS      current
    DESCRIPTION
        "The value of tmnxMobPdnApnIpPoolRowStatus specifies the row status of
         this entry. It is used for creation and deletion of this IP pool for 
         an Access Point Name (APN).

         If a corresponding IP pool does not exist in
         TIMETRA-VRTR-MIB::vRtrIpPoolTable, an 'inconsistentName' error will 
         be returned."
    ::= { tmnxMobPdnApnIpPoolEntry 1 }

--
--  APN base policy table
--

tmnxMobPdnApnBasePolTableLstChgd  OBJECT-TYPE
    SYNTAX      TimeStamp
    MAX-ACCESS  read-only
    STATUS      current
    DESCRIPTION
        "The value of tmnxMobPdnApnBasePolTableLstChgd indicates the sysUpTime 
         at the time of the last modification to tmnxMobPdnApnBasePolTable by
         adding, deleting an entry or change to a writable object in the table.

         If no changes were made to the table since the last re-initialization
         of the local network management subsystem, then this object contains
         a zero value."
    ::= { tmnxMobPdnGlobalObjs 13 }

tmnxMobPdnApnBasePolTable  OBJECT-TYPE
    SYNTAX      SEQUENCE OF TmnxMobPdnApnBasePolEntry
    MAX-ACCESS  not-accessible
    STATUS      current
    DESCRIPTION
        "The tmnxMobPdnApnBasePolTable has an entry for each static policy base 
         profile configured for an Access Point Name (APN).

         A maximum of 8 static policy base profiles can be configured for 
         each Internet Protocol Connectivity Access Network (IP-CAN) session 
         in an APN."
    ::= { tmnxMobPdnConfObjs 13 }

tmnxMobPdnApnBasePolEntry  OBJECT-TYPE
    SYNTAX      TmnxMobPdnApnBasePolEntry
    MAX-ACCESS  not-accessible
    STATUS      current
    DESCRIPTION
        "Each row entry represents a static policy base profile in an Access 
         Point Name (APN). Entries can be created and deleted by the user."
    INDEX { tmnxMobGwId,
            tmnxMobPdnApnName,
            tmnxMobProfPolBaseName
          }
    ::= { tmnxMobPdnApnBasePolTable 1 }

TmnxMobPdnApnBasePolEntry ::= SEQUENCE {
        tmnxMobPdnApnBasePolRowStatus  RowStatus
    }

tmnxMobPdnApnBasePolRowStatus  OBJECT-TYPE
    SYNTAX      RowStatus
    MAX-ACCESS  read-create
    STATUS      current
    DESCRIPTION
        "The value of tmnxMobPdnApnBasePolRowStatus specifies the row status of
         this entry. It is used for creation and deletion of this static policy 
         base profile for an Access Point Name (APN).

         If no row exists in the 
         TIMETRA-MOBILE-PROFILE-MIB::tmnxMobProfPolBaseTable with the 
         corresponding base policy, an 'inconsistentName' error will be 
         returned.

         If the precedence value, specified by 
         TIMETRA-MOBILE-PROFILE-MIB::tmnxMobProfPolBasePrecedence, is equal to
         the precedence value of a base profile associated in this APN, then
         an 'inconsistentValue' error will be returned."
    ::= { tmnxMobPdnApnBasePolEntry 1 }

--
--  Ga table
--

tmnxMobPdnGaTableLastChanged  OBJECT-TYPE
    SYNTAX      TimeStamp
    MAX-ACCESS  read-only
    STATUS      current
    DESCRIPTION
        "The value of tmnxMobPdnGaTableLastChanged indicates the sysUpTime at
         the time of the last modification to tmnxMobPdnGaTable by adding,
         deleting an entry or change to a writable object in the table.

         If no changes were made to the table since the last re-initialization
         of the local network management subsystem, then this object contains
         a zero value."
    ::= { tmnxMobPdnGlobalObjs 15 }

tmnxMobPdnGaTable  OBJECT-TYPE
    SYNTAX      SEQUENCE OF TmnxMobPdnGaEntry
    MAX-ACCESS  not-accessible
    STATUS      current
    DESCRIPTION
        "The tmnxMobPdnGaTable provides an extension of the tmnxMobPdnTable
         for Ga reference point configuration."
    ::= { tmnxMobPdnConfObjs 14 }

tmnxMobPdnGaEntry  OBJECT-TYPE
    SYNTAX      TmnxMobPdnGaEntry
    MAX-ACCESS  not-accessible
    STATUS      current
    DESCRIPTION
        "Each row entry represents additional columns for Ga reference point
         configuration for a Packet Data Network Gateway (PGW)."
    AUGMENTS { tmnxMobPdnEntry }
    ::= { tmnxMobPdnGaTable 1 }

TmnxMobPdnGaEntry ::= SEQUENCE {
        tmnxMobPdnGaLastChanged             TimeStamp,
        tmnxMobPdnGaIfVRtrId                TmnxVRtrID,
        tmnxMobPdnGaIfIndex                 InterfaceIndexOrZero,
        tmnxMobPdnGaGtpcProfile             TmnxMobProfNameOrEmpty,
        tmnxMobPdnGaGtpPrimeGrpName         TmnxMobProfNameOrEmpty
    }

tmnxMobPdnGaLastChanged  OBJECT-TYPE
    SYNTAX      TimeStamp
    MAX-ACCESS  read-only
    STATUS      current
    DESCRIPTION
        "The value of tmnxMobPdnGaLastChanged indicates the timestamp of
         the last change to this row in tmnxMobPdnGaTable."
    ::= { tmnxMobPdnGaEntry 1 }

tmnxMobPdnGaIfVRtrId  OBJECT-TYPE
    SYNTAX      TmnxVRtrID
    MAX-ACCESS  read-write
    STATUS      current
    DESCRIPTION
        "The value of tmnxMobPdnGaIfVRtrId specifies the virtual
         router to which the interface specified by tmnxMobPdnGaIfIndex
         belongs."
    DEFVAL { 1 }
    ::= { tmnxMobPdnGaEntry 2 }

tmnxMobPdnGaIfIndex  OBJECT-TYPE
    SYNTAX      InterfaceIndexOrZero
    MAX-ACCESS  read-write
    STATUS      current
    DESCRIPTION
        "The value of tmnxMobPdnGaIfIndex specifies the interface
         index of the local interface used for the Ga reference point.
         When the value of this object is set to 0, no interface has
         been assigned.
         
         If tmnxMobPdnGaGtpPrimeGrpName is specified, then the value of 
         TIMETRA-MOBILE-PROFILE-MIB::tmnxMobGtpPriGrpIfIndex is used as the
         interface index of the local interface used for the Ga reference
         point."
    DEFVAL { 0 }
    ::= { tmnxMobPdnGaEntry 3 }

tmnxMobPdnGaGtpcProfile  OBJECT-TYPE
    SYNTAX      TmnxMobProfNameOrEmpty
    MAX-ACCESS  read-write
    STATUS      current
    DESCRIPTION
        "The value of tmnxMobPdnGaGtpcProfile specifies the GPRS Tunneling
         Protocol-Control plane (GTP-C) profile name. The GTP-C profile provides
         GTP-C signaling related configuration.

         If a corresponding GTP profile does not exist in
         TIMETRA-MOBILE-PROFILE-MIB::tmnxMobProfGtpTable,
         an 'inconsistentValue' error will be returned."
    DEFVAL { ''H }
    ::= { tmnxMobPdnGaEntry 4 }

tmnxMobPdnGaGtpPrimeGrpName  OBJECT-TYPE
    SYNTAX      TmnxMobProfNameOrEmpty
    MAX-ACCESS  read-write
    STATUS      current
    DESCRIPTION
        "The value of tmnxMobPdnGaGtpPrimeGrpName specifies GPRS Tunneling
         Protocol (GTP) prime group name. 

         If a corresponding GPRS Tunneling Protocol (GTP) prime group does not
         exist in TIMETRA-MOBILE-PROFILE-MIB::tmnxMobGtpPriGrpTable,
         an 'inconsistentValue' error will be returned."
    DEFVAL { ''H }
    ::= { tmnxMobPdnGaEntry 5 }

--
--  Gn table
--

tmnxMobPdnGnTableLastChanged  OBJECT-TYPE
    SYNTAX      TimeStamp
    MAX-ACCESS  read-only
    STATUS      current
    DESCRIPTION
        "The value of tmnxMobPdnGnTableLastChanged indicates the sysUpTime at
         the time of the last modification to tmnxMobPdnGnTable by adding,
         deleting an entry or change to a writable object in the table.

         If no changes were made to the table since the last re-initialization
         of the local network management subsystem, then this object contains
         a zero value."
    ::= { tmnxMobPdnGlobalObjs 16 }

tmnxMobPdnGnTable  OBJECT-TYPE
    SYNTAX      SEQUENCE OF TmnxMobPdnGnEntry
    MAX-ACCESS  not-accessible
    STATUS      current
    DESCRIPTION
        "The tmnxMobPdnGnTable provides an extension of the tmnxMobPdnTable
         for Gn reference point configuration."
    ::= { tmnxMobPdnConfObjs 15 }

tmnxMobPdnGnEntry  OBJECT-TYPE
    SYNTAX      TmnxMobPdnGnEntry
    MAX-ACCESS  not-accessible
    STATUS      current
    DESCRIPTION
        "Each row entry represents additional columns for Gn reference point
         configuration for a Packet Data Network Gateway (PGW)."
    AUGMENTS { tmnxMobPdnEntry }
    ::= { tmnxMobPdnGnTable 1 }

TmnxMobPdnGnEntry ::= SEQUENCE {
        tmnxMobPdnGnLastChanged        TimeStamp,
        tmnxMobPdnGnGtpcIfVRtrId       TmnxVRtrID,
        tmnxMobPdnGnGtpcIfIndex        InterfaceIndexOrZero,
        tmnxMobPdnGnGtpuIfVRtrId       TmnxVRtrID,
        tmnxMobPdnGnGtpuIfIndex        InterfaceIndexOrZero,
        tmnxMobPdnGnGtpcProfile        TmnxMobProfNameOrEmpty,
        tmnxMobPdnGnGtpuProfile        TmnxMobProfNameOrEmpty,
        tmnxMobPdnGnPeerList           TmnxMobProfNameOrEmpty
    }

tmnxMobPdnGnLastChanged  OBJECT-TYPE
    SYNTAX      TimeStamp
    MAX-ACCESS  read-only
    STATUS      current
    DESCRIPTION
        "The value of tmnxMobPdnGnLastChanged indicates the timestamp of
         the last change to this row in tmnxMobPdnGnTable."
    ::= { tmnxMobPdnGnEntry 1 }

tmnxMobPdnGnGtpcIfVRtrId  OBJECT-TYPE
    SYNTAX      TmnxVRtrID
    MAX-ACCESS  read-write
    STATUS      current
    DESCRIPTION
        "The value of tmnxMobPdnGnGtpcIfVRtrId specifies the virtual
         router to which the interface specified by tmnxMobPdnGnGtpcIfIndex
         belongs."
    DEFVAL { 1 }
    ::= { tmnxMobPdnGnEntry 2 }

tmnxMobPdnGnGtpcIfIndex  OBJECT-TYPE
    SYNTAX      InterfaceIndexOrZero
    MAX-ACCESS  read-write
    STATUS      current
    DESCRIPTION
        "The value of tmnxMobPdnGnGtpcIfIndex specifies the interface
         index of the local interface used for the General Packet Radio
         Services Tunneling Protocol for Control Plane (GTP-C) signaling.
         When the value of this object is set to 0, no interface has
         been assigned."
    DEFVAL { 0 }
    ::= { tmnxMobPdnGnEntry 3 }

tmnxMobPdnGnGtpuIfVRtrId  OBJECT-TYPE
    SYNTAX      TmnxVRtrID
    MAX-ACCESS  read-write
    STATUS      current
    DESCRIPTION
        "The value of tmnxMobPdnGnGtpuIfVRtrId specifies the virtual
         router to which the interface specified by tmnxMobPdnGnGtpuIfIndex
         belongs."
    DEFVAL { 1 }
    ::= { tmnxMobPdnGnEntry 4 }

tmnxMobPdnGnGtpuIfIndex  OBJECT-TYPE
    SYNTAX      InterfaceIndexOrZero
    MAX-ACCESS  read-write
    STATUS      current
    DESCRIPTION
        "The value of tmnxMobPdnGnGtpuIfIndex specifies the interface
         index of the local interface used for the General Packet Radio
         Services Tunneling Protocol for User Plane (GTP-U) signaling.
         When the value of this object is set to 0, no interface has
         been assigned."
    DEFVAL { 0 }
    ::= { tmnxMobPdnGnEntry 5 }

tmnxMobPdnGnGtpcProfile  OBJECT-TYPE
    SYNTAX      TmnxMobProfNameOrEmpty
    MAX-ACCESS  read-write
    STATUS      current
    DESCRIPTION
        "The value of tmnxMobPdnGnGtpcProfile specifies the GPRS Tunneling
         Protocol-Control plane (GTP-C) profile name. The GTP-C profile provides
         GTP-C signaling related configuration.

         If a corresponding GTP profile does not exist in
         TIMETRA-MOBILE-PROFILE-MIB::tmnxMobProfGtpTable,
         an 'inconsistentValue' error will be returned."
    DEFVAL { ''H }
    ::= { tmnxMobPdnGnEntry 6 }

tmnxMobPdnGnGtpuProfile  OBJECT-TYPE
    SYNTAX      TmnxMobProfNameOrEmpty
    MAX-ACCESS  read-write
    STATUS      current
    DESCRIPTION
        "The value of tmnxMobPdnGnGtpuProfile specifies the GPRS Tunneling
         Protocol-User plane (GTP-U) profile name. The GTP-U profile provides
         GTP-U signaling related configuration.

         If a corresponding GTP profile does not exist in
         TIMETRA-MOBILE-PROFILE-MIB::tmnxMobProfGtpTable,
         an 'inconsistentValue' error will be returned."
    DEFVAL { ''H }
    ::= { tmnxMobPdnGnEntry 7 }

tmnxMobPdnGnPeerList  OBJECT-TYPE
    SYNTAX      TmnxMobProfNameOrEmpty
    MAX-ACCESS  read-write
    STATUS      current
    DESCRIPTION
        "The value of tmnxMobPdnGnPeerList specifies the GPRS Tunneling
         Protocol (GTP) peer list. 

         If a corresponding GTP peer list does not exist in
         TIMETRA-MOBILE-PROFILE-MIB::tmnxMobProfPeerListTable,
         an 'inconsistentValue' error will be returned."
    DEFVAL { ''H }
    ::= { tmnxMobPdnGnEntry 8 }

--
--  PDN KCI/KPI Accounting Policy Table
--

tmnxMobPdnApTableLastChanged     OBJECT-TYPE
    SYNTAX      TimeStamp
    MAX-ACCESS  read-only
    STATUS      current
    DESCRIPTION
        "The value of tmnxMobPdnApTableLastChanged indicates the sysUpTime at
         the time of the last modification to tmnxMobPdnApTable by adding,
         deleting an entry or change to a writable object in the table.

         If no changes were made to the table since the last re-initialization
         of the local network management subsystem, then this object contains
         a zero value."
    ::= { tmnxMobPdnGlobalObjs 17 }

tmnxMobPdnApTable  OBJECT-TYPE
    SYNTAX      SEQUENCE OF TmnxMobPdnApEntry
    MAX-ACCESS  not-accessible
    STATUS      current
    DESCRIPTION
        "The tmnxMobPdnApTable has an entry for each Accounting Policy 
         associated with the Packet Data Network Gateway (PGW). The policy 
         can be either Key Capacity Indicator (KCI) or Key Performance 
         Indicator (KPI)."
    ::= { tmnxMobPdnConfObjs 16 }

tmnxMobPdnApEntry  OBJECT-TYPE
    SYNTAX      TmnxMobPdnApEntry
    MAX-ACCESS  not-accessible
    STATUS      current
    DESCRIPTION
        "Each row entry represents a Accounting Policy associated with the
         Packet Data Network Gateway (PGW). Entries can be created and deleted
         by the user."
    INDEX { tmnxMobGwId, tmnxMobPdnApPolicyId }
    ::= { tmnxMobPdnApTable 1 }

TmnxMobPdnApEntry ::= SEQUENCE {
        tmnxMobPdnApPolicyId           Unsigned32,
        tmnxMobPdnApRowStatus          RowStatus,
        tmnxMobPdnApLastChanged        TimeStamp,
        tmnxMobPdnApCollectAcctStats   TruthValue
    }

tmnxMobPdnApPolicyId  OBJECT-TYPE
   SYNTAX      Unsigned32 (1..99)
   MAX-ACCESS  not-accessible
   STATUS      current
   DESCRIPTION
       "The value of tmnxMobPdnApPolicyId uniquely identifies an Accounting
        Policy to be used for creating accounting records on this Packet Data
        Network Gateway (PGW).

        If a corresponding Accounting Policy does not exist in
        TIMETRA-LOG-MIB::tmnxLogApTable,
        an 'inconsistentValue' error will be returned."
   ::= { tmnxMobPdnApEntry 1 }

tmnxMobPdnApRowStatus  OBJECT-TYPE
    SYNTAX      RowStatus
    MAX-ACCESS  read-create
    STATUS      current
    DESCRIPTION
        "The value of tmnxMobPdnApRowStatus specifies the row status of
         this entry. It is used for creation and deletion of this Accounting
         Policy for the Packet Data Network Gateway (PGW)."
    ::= { tmnxMobPdnApEntry 2 }

tmnxMobPdnApLastChanged  OBJECT-TYPE
    SYNTAX      TimeStamp
    MAX-ACCESS  read-only
    STATUS      current
    DESCRIPTION
        "The value of tmnxMobPdnLastChanged indicates the timestamp of the last
         change to this row in tmnxMobPdnApTable."
    ::= { tmnxMobPdnApEntry 3 }

tmnxMobPdnApCollectAcctStats OBJECT-TYPE
    SYNTAX          TruthValue
    MAX-ACCESS      read-create
    STATUS          current
    DESCRIPTION     
        "The value of tmnxMobPdnApCollectAcctStats specifies whether the agent
         collects accounting statistics for this Accouning Policy."
    DEFVAL { false }
    ::= { tmnxMobPdnApEntry 4 }

--
--  UE Table
--

tmnxMobPdnUeTable  OBJECT-TYPE
    SYNTAX      SEQUENCE OF TmnxMobPdnUeEntry
    MAX-ACCESS  not-accessible
    STATUS      current
    DESCRIPTION
        "The tmnxMobPdnUeTable has an entry for an User Equipment (UE)
         being served by this gateway.

         There will not be more than one row in this table. Whenever a new row
         is created, existing row will be deleted and then new row will be
         created.

         This table will only have an entry for a UE served by the gateways, 
         identified by TIMETRA-MOBILE-GATEWAY-MIB::tmnxMobGwId, where the value 
         of TIMETRA-MOBILE-GATEWAY-MIB::tmnxMobGwType is equal to 'pgw'."
    ::= { tmnxMobPdnStatObjs 1 }

tmnxMobPdnUeEntry  OBJECT-TYPE
    SYNTAX      TmnxMobPdnUeEntry
    MAX-ACCESS  not-accessible
    STATUS      current
    DESCRIPTION
        "Each row entry represents an User Equipment (UE) and contains
         identification, connection information."
    INDEX { tmnxMobGwId,
            tmnxMobPdnUeImsi
          }
    ::= { tmnxMobPdnUeTable 1 }

TmnxMobPdnUeEntry ::= SEQUENCE {
        tmnxMobPdnUeImsi                   TmnxMobUeId,
        tmnxMobPdnUeRowStatus              RowStatus,
        tmnxMobPdnUeMsIsdn                 TmnxMobMsisdn,
        tmnxMobPdnUeImei                   TmnxMobImei,
        tmnxMobPdnUeNai                    TmnxMobNai,
        tmnxMobPdnUeNwkMcc                 TmnxMobMcc,
        tmnxMobPdnUeNwkMnc                 TmnxMobMnc,
        tmnxMobPdnUeTrackingAreaId         Unsigned32,
        tmnxMobPdnUeCellId                 Unsigned32,
        tmnxMobPdnUeState                  TmnxMobUeState,
        tmnxMobPdnUeRat                    TmnxMobUeRat,
        tmnxMobPdnUePdnContexts            Unsigned32,
        tmnxMobPdnUeBearerContexts         Unsigned32,
        tmnxMobPdnUeRfPgwAddrType          InetAddressType,
        tmnxMobPdnUeRfPgwAddr              InetAddress,
        tmnxMobPdnUeCtxAccessType          TmnxMobAccessType,
        tmnxMobPdnUeSubType                TmnxMobUeSubType,
        tmnxMobPdnKeyType                  TmnxMobUeIdType,
        tmnxMobPdnUeImsiStr                TmnxMobImsiStr 
    }

tmnxMobPdnUeImsi  OBJECT-TYPE
    SYNTAX      TmnxMobUeId
    MAX-ACCESS  not-accessible
    STATUS      current
    DESCRIPTION
        "The value of tmnxMobPdnUeImsi indicates the International Mobile
         Subscriber Identity (IMSI) of this User Equipment (UE). IMSI is used
         to uniquely identify an UE."
    ::= { tmnxMobPdnUeEntry 1 }

tmnxMobPdnUeRowStatus  OBJECT-TYPE
    SYNTAX      RowStatus
    MAX-ACCESS  read-create
    STATUS      current
    DESCRIPTION
        "The value of tmnxMobPdnUeRowStatus specifies the row status of this
         entry. It is used for the creation and deletion of this User 
         Equipment (UE) entry. Creation of a new row will result in the 
         existing row, if any, to be deleted.

         If a UE is not served by the gateway identified by tmnxMobGwId, then 
         the row creation will fail with an 'inconsistentName' error.

         The creation or deletion of an entry in this table causes creation or
         deletion of corresponding entries in tmnxMobPdnPdnContextTable, 
         tmnxMobPdnBearerContextTable, tmnxMobPdnBcSdfTable and
         tmnxMobPdnBcSdfFilterTable."
    ::= { tmnxMobPdnUeEntry 2 }

tmnxMobPdnUeMsIsdn  OBJECT-TYPE
    SYNTAX      TmnxMobMsisdn
    MAX-ACCESS  read-only
    STATUS      current
    DESCRIPTION
        "The value of tmnxMobPdnUeMsIsdn indicates the Mobile Subscriber
         Integrated Services Digital Network (MSISDN) number of this User
         Equipment (UE)."
    ::= { tmnxMobPdnUeEntry 3 }

tmnxMobPdnUeImei  OBJECT-TYPE
    SYNTAX      TmnxMobImei
    MAX-ACCESS  read-only
    STATUS      current
    DESCRIPTION
        "The value of tmnxMobPdnUeImei indicates the International Mobile
         Equipment Identity (IMEI) of this User Equipment (UE)."
    ::= { tmnxMobPdnUeEntry 4 }

tmnxMobPdnUeNai  OBJECT-TYPE
    SYNTAX      TmnxMobNai
    MAX-ACCESS  read-only
    STATUS      current
    DESCRIPTION
        "The value of tmnxMobPdnUeNai indicates the Network Address
         Identifier (NAI) of this User Equipment (UE)."
    ::= { tmnxMobPdnUeEntry 5 }

tmnxMobPdnUeNwkMcc  OBJECT-TYPE
    SYNTAX      TmnxMobMcc
    MAX-ACCESS  read-only
    STATUS      current
    DESCRIPTION
        "The value of tmnxMobPdnUeNwkMcc indicates the Mobile Country Code
         (MCC) of this User Equipment (UE)."
    ::= { tmnxMobPdnUeEntry 6 }

tmnxMobPdnUeNwkMnc  OBJECT-TYPE
    SYNTAX      TmnxMobMnc
    MAX-ACCESS  read-only
    STATUS      current
    DESCRIPTION
        "The value of tmnxMobPdnUeNwkMnc indicates the Mobile Network Code
         (MNC) of this User Equipment (UE)."
    ::= { tmnxMobPdnUeEntry 7 }

tmnxMobPdnUeTrackingAreaId  OBJECT-TYPE
    SYNTAX      Unsigned32
    MAX-ACCESS  read-only
    STATUS      current
    DESCRIPTION
        "The value of tmnxMobPdnUeTrackingAreaId indicates the tracking area
         identifier of this User Equipment (UE)."
    ::= { tmnxMobPdnUeEntry 8 }

tmnxMobPdnUeCellId  OBJECT-TYPE
    SYNTAX      Unsigned32
    MAX-ACCESS  read-only
    STATUS      current
    DESCRIPTION
        "The value of tmnxMobPdnUeCellId indicates the cell identification of
         this User Equipment (UE)."
    ::= { tmnxMobPdnUeEntry 9 }

tmnxMobPdnUeState  OBJECT-TYPE
    SYNTAX      TmnxMobUeState
    MAX-ACCESS  read-only
    STATUS      current
    DESCRIPTION
        "The value of tmnxMobPdnUeState indicates the current state of this
         User Equipment (UE)."
    ::= { tmnxMobPdnUeEntry 10 }

tmnxMobPdnUeRat  OBJECT-TYPE
    SYNTAX      TmnxMobUeRat
    MAX-ACCESS  read-only
    STATUS      current
    DESCRIPTION
        "The value of tmnxMobPdnUeRat indicates the Radio Access Type (RAT)
         of this User Equipment (UE)."
    ::= { tmnxMobPdnUeEntry 11 }

tmnxMobPdnUePdnContexts  OBJECT-TYPE
    SYNTAX      Unsigned32
    MAX-ACCESS  read-only
    STATUS      current
    DESCRIPTION
        "The value of tmnxMobPdnUePdnContexts indicates the number of Packet
         Data Network (PDN) contexts on this User Equipment (UE)."
    ::= { tmnxMobPdnUeEntry 12 }

tmnxMobPdnUeBearerContexts  OBJECT-TYPE
    SYNTAX      Unsigned32
    MAX-ACCESS  read-only
    STATUS      current
    DESCRIPTION
        "The value of tmnxMobPdnUeBearerContexts indicates the number of 
         bearer contexts on this User Equipment (UE)."
    ::= { tmnxMobPdnUeEntry 13 }

tmnxMobPdnUeRfPgwAddrType  OBJECT-TYPE
    SYNTAX      InetAddressType
    MAX-ACCESS  read-only
    STATUS      current
    DESCRIPTION
        "The value of tmnxMobPdnUeRfPgwAddrType indicates the type of
         address represented by tmnxMobPdnUeRfPgwAddr."
    ::= { tmnxMobPdnUeEntry 14 }

tmnxMobPdnUeRfPgwAddr  OBJECT-TYPE
    SYNTAX      InetAddress (SIZE (0|4|16))
    MAX-ACCESS  read-only
    STATUS      current
    DESCRIPTION
        "The value of tmnxMobPdnUeRfPgwAddr indicates the IP address of
         the Packet Data Network Gateway (PGW) in Rf reference point."
    ::= { tmnxMobPdnUeEntry 15 }

tmnxMobPdnUeCtxAccessType  OBJECT-TYPE
    SYNTAX      TmnxMobAccessType
    MAX-ACCESS  read-only
    STATUS      current
    DESCRIPTION
        "The value of tmnxMobPdnUeCtxAccessType specifies the access type for
         the User Equipment (UE)."
    ::= { tmnxMobPdnUeEntry 16 }
    
tmnxMobPdnUeSubType  OBJECT-TYPE
    SYNTAX      TmnxMobUeSubType
    MAX-ACCESS  read-only
    STATUS      current
    DESCRIPTION
        "The value of tmnxMobPdnUeSubType indicates the subscription type of 
         this User Equipment (UE)."
    ::= { tmnxMobPdnUeEntry 17 }

tmnxMobPdnKeyType  OBJECT-TYPE
    SYNTAX      TmnxMobUeIdType
    MAX-ACCESS  read-create
    STATUS      current
    DESCRIPTION
        "The value of tmnxMobPdnKeyType indicates the subscriber
         identification type of this User Equipment (UE)."
    ::= { tmnxMobPdnUeEntry 18 }

tmnxMobPdnUeImsiStr  OBJECT-TYPE
    SYNTAX      TmnxMobImsiStr
    MAX-ACCESS  read-only
    STATUS      current
    DESCRIPTION
        "The value of tmnxMobPdnUeImsiStr indicates the International Mobile
         Subscriber Identity (IMSI) of this User Equipment (UE)."
    ::= { tmnxMobPdnUeEntry 19 }

--
--  PDN Context Table
--

tmnxMobPdnPdnContextTable  OBJECT-TYPE
    SYNTAX      SEQUENCE OF TmnxMobPdnPdnContextEntry
    MAX-ACCESS  not-accessible
    STATUS      current
    DESCRIPTION
        "The tmnxMobPdnPdnContextTable has an entry for each Pakcet Data
         Network (PDN) context of an User Equipment (UE)."
    ::= { tmnxMobPdnStatObjs 2 }

tmnxMobPdnPdnContextEntry  OBJECT-TYPE
    SYNTAX      TmnxMobPdnPdnContextEntry
    MAX-ACCESS  not-accessible
    STATUS      current
    DESCRIPTION
        "Each row entry represents a Pakcet Data Network (PDN) context of an
         User Equipment (UE) and contains identification, connection
         information."
    INDEX { tmnxMobGwId,
            tmnxMobPdnUeImsi,
            tmnxMobPdnPcApn,
            tmnxMobPdnPcPdnType
          }
    ::= { tmnxMobPdnPdnContextTable 1 }

TmnxMobPdnPdnContextEntry ::= SEQUENCE {
        tmnxMobPdnPcApn                    TmnxMobApn,
        tmnxMobPdnPcPdnType                TmnxMobPdnType,
        tmnxMobPdnPcLinkedBearerId         TmnxMobBearerId,
        tmnxMobPdnPcApnRestriction         Unsigned32,
        tmnxMobPdnPcUlApnAmbr              Unsigned32,
        tmnxMobPdnPcDlApnAmbr              Unsigned32,
        tmnxMobPdnPcIpv4AddressType        InetAddressType,
        tmnxMobPdnPcIpv4Address            InetAddress,
        tmnxMobPdnPcIpv6AddressType        InetAddressType,
        tmnxMobPdnPcIpv6Address            InetAddress,
        tmnxMobPdnPcBearerContexts         Unsigned32,
        tmnxMobPdnPcSessionState           TmnxMobPdnSessionState,
        tmnxMobPdnPcLastEvent              TmnxMobPdnSessionEvent,
        tmnxMobPdnPcSigProtocol            TmnxMobPgwSigProtocol,
        tmnxMobPdnPcTnlRemoteCtrlTeid      Unsigned32,
        tmnxMobPdnPcTnlRemoteCtrlAddrTyp   InetAddressType,
        tmnxMobPdnPcTnlRemoteCtrlAddr      InetAddress,
        tmnxMobPdnPcTnlRemV6CtrlAddrTyp    InetAddressType,
        tmnxMobPdnPcTnlRemV6CtrlAddr       InetAddress,
        tmnxMobPdnPcTnlLocalCtrlTeid       Unsigned32,
        tmnxMobPdnPcTnlLocalCtrlAddrType   InetAddressType,
        tmnxMobPdnPcTnlLocalCtrlAddr       InetAddress,
        tmnxMobPdnPcTnlLocalV6CtrlAdrTyp   InetAddressType,
        tmnxMobPdnPcTnlLocalV6CtrlAddr     InetAddress,
        tmnxMobPdnPcOfcBearerType          TmnxMobChargingBearerType,
        tmnxMobPdnPcPcrfEventTriggers      Unsigned32,
        tmnxMobPdnPcGxPcrfAddressType      InetAddressType,
        tmnxMobPdnPcGxPcrfAddress          InetAddress,
        tmnxMobPdnPcGxPgwAddressType       InetAddressType,
        tmnxMobPdnPcGxPgwAddress           InetAddress,
        tmnxMobPdnPcAccessType             TmnxMobAccessType,
        tmnxMobPdnPcSelectionMode          INTEGER,
        tmnxMobPdnPcTnlLocalDataAddrType   InetAddressType,
        tmnxMobPdnPcTnlLocalDataAddr       InetAddress,
        tmnxMobPdnPcPGWGREkey              Unsigned32, 
        tmnxMobPdnPcMAGGREkey              Unsigned32,
        tmnxMobPdnPcTnlRemoteDataAddrTyp   InetAddressType,
        tmnxMobPdnPcTnlRemoteDataAddr      InetAddress,
        tmnxMobPdnPcRfSrvAddrType          InetAddressType,
        tmnxMobPdnPcRfSrvAddr              InetAddress,
        tmnxMobPdnPcRfServerState          TmnxMobServerState,
        tmnxMobPdnPcRfChargingLevel        TmnxMobChargingLevel,
        tmnxMobPdnPcRfChargingProfile      TmnxMobChargingProfile,
        tmnxMobPdnPcRfInterimRecords       Unsigned32,
        tmnxMobPdnPcRfTriggeredRecords     Unsigned32,
        tmnxMobPdnPcTnlDLPackets           Counter64,
        tmnxMobPdnPcTnlDLBytes             Counter64,
        tmnxMobPdnPcSgiULPackets           Counter64,
        tmnxMobPdnPcSgiULBytes             Counter64,
        tmnxMobPdnPcTnlDLPacketsLow        Counter32,
        tmnxMobPdnPcTnlDLPacketsHigh       Counter32,
        tmnxMobPdnPcTnlDLBytesLow          Counter32,
        tmnxMobPdnPcTnlDLBytesHigh         Counter32,
        tmnxMobPdnPcSgiULPacketsLow        Counter32,
        tmnxMobPdnPcSgiULPacketsHigh       Counter32,
        tmnxMobPdnPcSgiULBytesLow          Counter32,
        tmnxMobPdnPcSgiULBytesHigh         Counter32,
        tmnxMobPdnPcImsiAuthStatus         INTEGER,
        tmnxMobPdnPcImeiStr                TmnxMobImei,
        tmnxMobPdnPcImsiStr                TmnxMobImsiStr,        
        tmnxMobPdnPcSessConfigTime         Counter32,
        tmnxMobPdnPcSessRemExpTime         Counter32,
        tmnxMobPdnPcSessTimeDerivedFrom    INTEGER,
        tmnxMobPdnPcIdleConfigTime         Counter32,
        tmnxMobPdnPcIdleRemExpTime         Counter32,
        tmnxMobPdnPcIdleTimeDerivedFrom    INTEGER,
        tmnxMobPdnPcRefPointType           TmnxMobPdnRefPointType
    }

tmnxMobPdnPcApn  OBJECT-TYPE
    SYNTAX      TmnxMobApn
    MAX-ACCESS  not-accessible
    STATUS      current
    DESCRIPTION
        "The value of tmnxMobPdnPcApn indicates the Access Point Name (APN)
         which uniquely identifies a Pakcet Data Network (PDN) context of
         an User Equipment (UE)."
    ::= { tmnxMobPdnPdnContextEntry 1 }

tmnxMobPdnPcPdnType  OBJECT-TYPE
    SYNTAX      TmnxMobPdnType
    MAX-ACCESS  not-accessible
    STATUS      current
    DESCRIPTION
        "The value of tmnxMobPdnPcPdnType indicates the Pakcet Data Network
         (PDN) type of this context."
    ::= { tmnxMobPdnPdnContextEntry 2 }

tmnxMobPdnPcLinkedBearerId  OBJECT-TYPE
    SYNTAX      TmnxMobBearerId
    MAX-ACCESS  read-only
    STATUS      current
    DESCRIPTION
        "The value of tmnxMobPdnPcLinkedBearerId indicates the Linked Evolved 
         Packet System (EPS) Bearer Identity (LBI) which is the EPS Bearer 
         Identity of the default bearer in this Pakcet Data Network (PDN) 
         context."
    ::= { tmnxMobPdnPdnContextEntry 3 }

tmnxMobPdnPcApnRestriction  OBJECT-TYPE
    SYNTAX      Unsigned32
    MAX-ACCESS  read-only
    STATUS      current
    DESCRIPTION
        "The value of tmnxMobPdnPcApnRestriction indicates the restriction
         required by any active bearer context in this Pakcet Data Network
         (PDN) context."
    ::= { tmnxMobPdnPdnContextEntry 4 }

tmnxMobPdnPcUlApnAmbr  OBJECT-TYPE
    SYNTAX      Unsigned32
    UNITS       "kbps"
    MAX-ACCESS  read-only
    STATUS      current
    DESCRIPTION
        "The value of tmnxMobPdnPcUlApnAmbr indicates the uplink Aggregate 
         Maximum Bit Rate (AMBR) of this Pakcet Data Network (PDN) context."
    ::= { tmnxMobPdnPdnContextEntry 5 }

tmnxMobPdnPcDlApnAmbr  OBJECT-TYPE
    SYNTAX      Unsigned32
    UNITS       "kbps"
    MAX-ACCESS  read-only
    STATUS      current
    DESCRIPTION
        "The value of tmnxMobPdnPcDlApnAmbr indicates the downlink Aggregate 
         Maximum Bit Rate (AMBR) of this Pakcet Data Network (PDN) context."
    ::= { tmnxMobPdnPdnContextEntry 6 }

tmnxMobPdnPcIpv4AddressType  OBJECT-TYPE
    SYNTAX      InetAddressType
    MAX-ACCESS  read-only
    STATUS      current
    DESCRIPTION
        "The value of tmnxMobPdnPcIpv4AddressType indicates the type of
         address represented by tmnxMobPdnPcIpv4Address."
    ::= { tmnxMobPdnPdnContextEntry 7 }

tmnxMobPdnPcIpv4Address  OBJECT-TYPE
    SYNTAX      InetAddress (SIZE (0|4))
    MAX-ACCESS  read-only
    STATUS      current
    DESCRIPTION
        "The value of tmnxMobPdnPcIpv4Address indicates the IPv4 address of
         the User Equipment (UE) in this Pakcet Data Network (PDN) context."
    ::= { tmnxMobPdnPdnContextEntry 8 }

tmnxMobPdnPcIpv6AddressType  OBJECT-TYPE
    SYNTAX      InetAddressType
    MAX-ACCESS  read-only
    STATUS      current
    DESCRIPTION
        "The value of tmnxMobPdnPcIpv6AddressType indicates the type of
         address represented by tmnxMobPdnPcIpv6Address."
    ::= { tmnxMobPdnPdnContextEntry 9 }

tmnxMobPdnPcIpv6Address  OBJECT-TYPE
    SYNTAX      InetAddress (SIZE (0|16))
    MAX-ACCESS  read-only
    STATUS      current
    DESCRIPTION
        "The value of tmnxMobPdnPcIpv6Address indicates the IPv6 address of
         the User Equipment (UE) in this Pakcet Data Network (PDN) context."
    ::= { tmnxMobPdnPdnContextEntry 10 }

tmnxMobPdnPcBearerContexts  OBJECT-TYPE
    SYNTAX      Unsigned32
    MAX-ACCESS  read-only
    STATUS      current
    DESCRIPTION
        "The value of tmnxMobPdnPcBearerContexts indicates the number of
         bearer contexts in this Packet Data Network (PDN) context."
    ::= { tmnxMobPdnPdnContextEntry 11 }

tmnxMobPdnPcSessionState  OBJECT-TYPE
    SYNTAX      TmnxMobPdnSessionState
    MAX-ACCESS  read-only
    STATUS      current
    DESCRIPTION
        "The value of tmnxMobPdnPcSessionState indicates the current
         feedback signaling message (FSM) state of this context."
    ::= { tmnxMobPdnPdnContextEntry 12 }

tmnxMobPdnPcLastEvent  OBJECT-TYPE
    SYNTAX      TmnxMobPdnSessionEvent
    MAX-ACCESS  read-only
    STATUS      current
    DESCRIPTION
        "The value of tmnxMobPdnPcLastEvent indicates the last
         feedback signaling message (FSM) event of this context."
    ::= { tmnxMobPdnPdnContextEntry 13 }

tmnxMobPdnPcSigProtocol  OBJECT-TYPE
    SYNTAX      TmnxMobPgwSigProtocol
    MAX-ACCESS  read-only
    STATUS      current
    DESCRIPTION
        "The value of tmnxMobPdnPcSigProtocol indicates the signaling
         protocol used on S5, S8 or S2a reference point."
    ::= { tmnxMobPdnPdnContextEntry 14 }

tmnxMobPdnPcTnlRemoteCtrlTeid  OBJECT-TYPE
    SYNTAX      Unsigned32
    MAX-ACCESS  read-only
    STATUS      current
    DESCRIPTION
        "The value of tmnxMobPdnPcTnlRemoteCtrlTeid indicates the Serving 
         Gateway (SGW) control plane Tunnel Endpoint Identifier (TEID) on S5 or 
         S8 reference point."
    ::= { tmnxMobPdnPdnContextEntry 15 }

tmnxMobPdnPcTnlRemoteCtrlAddrTyp  OBJECT-TYPE
    SYNTAX      InetAddressType
    MAX-ACCESS  read-only
    STATUS      current
    DESCRIPTION
        "The value of tmnxMobPdnPcTnlRemoteCtrlAddrTyp indicates the type of
         address represented by tmnxMobPdnPcTnlRemoteCtrlAddr."
    ::= { tmnxMobPdnPdnContextEntry 16 }

tmnxMobPdnPcTnlRemoteCtrlAddr  OBJECT-TYPE
    SYNTAX      InetAddress (SIZE (0|4))
    MAX-ACCESS  read-only
    STATUS      current
    DESCRIPTION
        "The value of tmnxMobPdnPcTnlRemoteCtrlAddr indicates the IP address of 
         the Serving Gateway (SGW) currently used  for sending the control 
         plane signaling on S5 or S8 reference point when the value of 
         tmnxMobPdnPcSigProtocol is 'gtp'.

         The value of tmnxMobPdnPcTnlRemoteCtrlAddr indicates the IP address 
         of the Mobile Access Gateway (MAG) currently used for sending the control 
         plane signal on S2a reference point when the value of tmnxMobPdnPcSigProtocol
         is 'pmip'."
    ::= { tmnxMobPdnPdnContextEntry 17 }

tmnxMobPdnPcTnlRemV6CtrlAddrTyp  OBJECT-TYPE
    SYNTAX      InetAddressType
    MAX-ACCESS  read-only
    STATUS      current
    DESCRIPTION
        "The value of tmnxMobPdnPcTnlRemV6CtrlAddrTyp indicates the type of
         address represented by tmnxMobPdnPcTnlRemV6CtrlAddr."
    ::= { tmnxMobPdnPdnContextEntry 18 }

tmnxMobPdnPcTnlRemV6CtrlAddr  OBJECT-TYPE
    SYNTAX      InetAddress (SIZE (0|16))
    MAX-ACCESS  read-only
    STATUS      current
    DESCRIPTION
        "The value of tmnxMobPdnPcTnlRemV6CtrlAddr indicates the IPv6 address 
         of the Serving Gateway (SGW) currently used for sending the control 
         plane signaling on S5 or S8 reference point when the value of 
         tmnxMobPdnPcSigProtocol is 'gtp'.

         The value of tmnxMobPdnPcTnlRemoteCtrlAddr indicates the IPv6 address 
         of the Mobile Access Gateway (MAG) currently used for sending the 
         control plane signal on S2a reference point when the value of
         tmnxMobPdnPcSigProtocol is 'pmip'."
    ::= { tmnxMobPdnPdnContextEntry 19 }

tmnxMobPdnPcTnlLocalCtrlTeid  OBJECT-TYPE
    SYNTAX      Unsigned32
    MAX-ACCESS  read-only
    STATUS      current
    DESCRIPTION
        "The value of tmnxMobPdnPcTnlLocalCtrlTeid indicates the Pakcet Data 
         Network Gateway (PGW) control plane Tunnel Endpoint Identifier (TEID) 
         on S5 or S8 reference point."
    ::= { tmnxMobPdnPdnContextEntry 20 }

tmnxMobPdnPcTnlLocalCtrlAddrType  OBJECT-TYPE
    SYNTAX      InetAddressType
    MAX-ACCESS  read-only
    STATUS      current
    DESCRIPTION
        "The value of tmnxMobPdnPcTnlLocalCtrlAddrType indicates the type of
         address represented by tmnxMobPdnPcTnlLocalCtrlAddr."
    ::= { tmnxMobPdnPdnContextEntry 21 }

tmnxMobPdnPcTnlLocalCtrlAddr  OBJECT-TYPE
    SYNTAX      InetAddress (SIZE (0|4))
    MAX-ACCESS  read-only
    STATUS      current
    DESCRIPTION
        "The value of tmnxMobPdnPcTnlLocalCtrlAddr indicates the IPv4 address of 
         the Pakcet Data Network Gateway (PGW) currently used for sending the 
         control plane signaling on S5, S8 or S2a reference point."
    ::= { tmnxMobPdnPdnContextEntry 22 }

tmnxMobPdnPcTnlLocalV6CtrlAdrTyp  OBJECT-TYPE
    SYNTAX      InetAddressType
    MAX-ACCESS  read-only
    STATUS      current
    DESCRIPTION
        "The value of tmnxMobPdnPcTnlLocalV6CtrlAdrTyp indicates the type of
         address represented by tmnxMobPdnPcTnlLocalV6CtrlAddr."
    ::= { tmnxMobPdnPdnContextEntry 23 }

tmnxMobPdnPcTnlLocalV6CtrlAddr  OBJECT-TYPE
    SYNTAX      InetAddress (SIZE (0|16))
    MAX-ACCESS  read-only
    STATUS      current
    DESCRIPTION
        "The value of tmnxMobPdnPcTnlLocalV6CtrlAddr indicates the IPv6 address 
         of the Pakcet Data Network Gateway (PGW) currently used for sending the 
         control plane signaling on S5, S8 or S2a reference point."
    ::= { tmnxMobPdnPdnContextEntry 24 }

tmnxMobPdnPcOfcBearerType  OBJECT-TYPE
    SYNTAX      TmnxMobChargingBearerType
    MAX-ACCESS  read-only
    STATUS      current
    DESCRIPTION
        "The value of tmnxMobPdnPcOfcBearerType indicates the bearer type used 
         in charging on the Rf reference point."
    ::= { tmnxMobPdnPdnContextEntry 25 }

tmnxMobPdnPcPcrfEventTriggers  OBJECT-TYPE
    SYNTAX      Unsigned32
    MAX-ACCESS  read-only
    STATUS      current
    DESCRIPTION
        "The value of tmnxMobPdnPcPcrfEventTriggers indicates the diameter 
         policy control triggers."
    ::= { tmnxMobPdnPdnContextEntry 26 }

tmnxMobPdnPcGxPcrfAddressType  OBJECT-TYPE
    SYNTAX      InetAddressType
    MAX-ACCESS  read-only
    STATUS      current
    DESCRIPTION
        "The value of tmnxMobPdnPcGxPcrfAddressType indicates the type of
         address represented by tmnxMobPdnPcGxPcrfAddress."
    ::= { tmnxMobPdnPdnContextEntry 27 }

tmnxMobPdnPcGxPcrfAddress  OBJECT-TYPE
    SYNTAX      InetAddress (SIZE (0|4|16))
    MAX-ACCESS  read-only
    STATUS      current
    DESCRIPTION
        "The value of tmnxMobPdnPcGxPcrfAddress indicates the Policy and
         Charging Rules Function (PCRF) IP address of the Gx control plane."
    ::= { tmnxMobPdnPdnContextEntry 28 }

tmnxMobPdnPcGxPgwAddressType  OBJECT-TYPE
    SYNTAX      InetAddressType
    MAX-ACCESS  read-only
    STATUS      current
    DESCRIPTION
        "The value of tmnxMobPdnPcGxPgwAddressType indicates the type of
         address represented by tmnxMobPdnPcGxPgwAddress."
    ::= { tmnxMobPdnPdnContextEntry 29 }

tmnxMobPdnPcGxPgwAddress  OBJECT-TYPE
    SYNTAX      InetAddress (SIZE (0|4|16))
    MAX-ACCESS  read-only
    STATUS      current
    DESCRIPTION
        "The value of tmnxMobPdnPcGxPgwAddress indicates the Packet Data 
         Network Gateway (PGW) IP address of the Gx control plane."
    ::= { tmnxMobPdnPdnContextEntry 30 }

tmnxMobPdnPcAccessType  OBJECT-TYPE
    SYNTAX      TmnxMobAccessType
    MAX-ACCESS  read-only
    STATUS      current
    DESCRIPTION
        "The value of tmnxMobPdnPcAccessType specifies the access type for the 
         Pakcet Data Network (PDN) context of an User Equipment (UE)."
    ::= { tmnxMobPdnPdnContextEntry 31 }

tmnxMobPdnPcSelectionMode  OBJECT-TYPE
    SYNTAX      INTEGER {
                         subscribed         (0),
                         sentByMs           (1),
                         chosenByServNode   (2)
                         }
    MAX-ACCESS  read-only
    STATUS      current
    DESCRIPTION
        "The value of tmnxMobPdnPcSelectionMode indicates the way the 
         Mobile Management Entity (MME) or Serving GPRS Support Node (SGSN) 
         selected the Access Point Name (APN)."
    ::= { tmnxMobPdnPdnContextEntry 32 }

tmnxMobPdnPcTnlLocalDataAddrType  OBJECT-TYPE
    SYNTAX      InetAddressType
    MAX-ACCESS  read-only
    STATUS      current
    DESCRIPTION
        "The value of tmnxMobPdnPcTnlLocalDataAddrType indicates the type of
         address represented by tmnxMobPdnPcTnlLocalDataAddr."
    ::= { tmnxMobPdnPdnContextEntry 33 }

tmnxMobPdnPcTnlLocalDataAddr  OBJECT-TYPE
    SYNTAX      InetAddress (SIZE (0|4|16))
    MAX-ACCESS  read-only
    STATUS      current
    DESCRIPTION
        "The value of tmnxMobPdnPcTnlLocalDataAddr indicates the Packet Data 
         Network Gateway (PGW) IP address of the Proxy Mobile Internet Protocol
         (PMIP) data plane."
    ::= { tmnxMobPdnPdnContextEntry 34 }

tmnxMobPdnPcPGWGREkey  OBJECT-TYPE
    SYNTAX      Unsigned32
    MAX-ACCESS  read-only
    STATUS      current
    DESCRIPTION
        "The value of tmnxMobPdnPcPGWGREkey indicates the Pakcet Data 
         Network Gateway (PGW) data plane Generic Routing Encapsulation
         (GRE) key on S2a reference point in uplink direction."
    ::= { tmnxMobPdnPdnContextEntry 35 }

tmnxMobPdnPcMAGGREkey  OBJECT-TYPE
    SYNTAX      Unsigned32
    MAX-ACCESS  read-only
    STATUS      current
    DESCRIPTION
        "The value of tmnxMobPdnPcMAGGREkey indicates the Mobile Access Gateway 
         (MAG) data plane Generic Routing Encapsulation (GRE) key on S2a reference
         point in downlink direction."
    ::= { tmnxMobPdnPdnContextEntry 36 }

tmnxMobPdnPcTnlRemoteDataAddrTyp  OBJECT-TYPE
    SYNTAX      InetAddressType
    MAX-ACCESS  read-only
    STATUS      current
    DESCRIPTION
        "The value of tmnxMobPdnPcTnlRemoteDataAddrTyp indicates the type of
         address represented by tmnxMobPdnPcTnlRemoteDataAddr."
    ::= { tmnxMobPdnPdnContextEntry 37 }

tmnxMobPdnPcTnlRemoteDataAddr  OBJECT-TYPE
    SYNTAX      InetAddress (SIZE (0|4|16))
    MAX-ACCESS  read-only
    STATUS      current
    DESCRIPTION
        "The value of tmnxMobPdnPcTnlRemoteDataAddr indicates the Mobile Access Gateway 
        (MAG) IP address of the Proxy Mobile Internet Protocol (PMIP) data plane." 
    ::= { tmnxMobPdnPdnContextEntry 38 }

tmnxMobPdnPcRfSrvAddrType  OBJECT-TYPE
    SYNTAX      InetAddressType
    MAX-ACCESS  read-only
    STATUS      current
    DESCRIPTION
        "The value of tmnxMobPdnPcRfSrvAddrType indicates the type of
         address represented by tmnxMobPdnPcRfSrvAddr."
    ::= { tmnxMobPdnPdnContextEntry 39 }

tmnxMobPdnPcRfSrvAddr  OBJECT-TYPE
    SYNTAX      InetAddress (SIZE (0|4|16))
    MAX-ACCESS  read-only
    STATUS      current
    DESCRIPTION
        "The value of tmnxMobPdnPcRfSrvAddr indicates the IP address of
        Rf Offline Charging Server." 
    ::= { tmnxMobPdnPdnContextEntry 40 }

tmnxMobPdnPcRfServerState  OBJECT-TYPE
    SYNTAX      TmnxMobServerState
    MAX-ACCESS  read-only
    STATUS      current
    DESCRIPTION
        "The value of tmnxMobPdnPcRfServerState indicates the  charging server
         state on the Rf reference point.

         The value of this object is valid only if the value of 
         tmnxMobPdnPcRfChargingLevel is equal to 'pdn'." 
    ::= { tmnxMobPdnPdnContextEntry 41 }

tmnxMobPdnPcRfChargingLevel  OBJECT-TYPE
    SYNTAX      TmnxMobChargingLevel
    MAX-ACCESS  read-only
    STATUS      current
    DESCRIPTION
        "The value of tmnxMobPdnPcRfChargingLevel indicates the  charging level
         on the Rf reference point." 
    ::= { tmnxMobPdnPdnContextEntry 42 }

tmnxMobPdnPcRfChargingProfile  OBJECT-TYPE
    SYNTAX      TmnxMobChargingProfile
    MAX-ACCESS  read-only
    STATUS      current
    DESCRIPTION
        "The value of tmnxMobPdnPcRfChargingProfile indicates the  charging 
         profile used on the Rf reference point.

         The value of this object is valid only if the value of 
         tmnxMobPdnPcRfChargingLevel is equal to 'pdn'." 
    ::= { tmnxMobPdnPdnContextEntry 43 }

tmnxMobPdnPcRfInterimRecords  OBJECT-TYPE
    SYNTAX      Unsigned32
    MAX-ACCESS  read-only
    STATUS      current
    DESCRIPTION
        "The value of tmnxMobPdnPcRfInterimRecords indicates the total number
         of interim records sent on the Rf reference point.

         The value of this object is valid only if the value of 
         tmnxMobPdnPcRfChargingLevel is equal to 'pdn'." 
    ::= { tmnxMobPdnPdnContextEntry 44 }

tmnxMobPdnPcRfTriggeredRecords  OBJECT-TYPE
    SYNTAX      Unsigned32
    MAX-ACCESS  read-only
    STATUS      current
    DESCRIPTION
        "The value of tmnxMobPdnPcRfTriggeredRecords indicates the number of 
         records generated by triggers on the Rf reference point.

         The value of this object is valid only if the value of 
         tmnxMobPdnPcRfChargingLevel is equal to 'pdn'."
    ::= { tmnxMobPdnPdnContextEntry 45 }

tmnxMobPdnPcTnlDLPackets  OBJECT-TYPE
    SYNTAX      Counter64
    MAX-ACCESS  read-only
    STATUS      current
    DESCRIPTION
        "The value of tmnxMobPdnPcTnlDLPackets indicates the aggregate number
         of S2a downlink packets."
    ::= { tmnxMobPdnPdnContextEntry 46 }

tmnxMobPdnPcTnlDLBytes  OBJECT-TYPE
    SYNTAX      Counter64
    MAX-ACCESS  read-only
    STATUS      current
    DESCRIPTION
        "The value of tmnxMobPdnPcTnlDLBytes indicates the aggregate number 
         of S2a downlink bytes."
    ::= { tmnxMobPdnPdnContextEntry 47 }

tmnxMobPdnPcSgiULPackets  OBJECT-TYPE
    SYNTAX      Counter64
    MAX-ACCESS  read-only
    STATUS      current
    DESCRIPTION
        "The value of tmnxMobPdnPcSgiULPackets indicates the aggregate number
         of S1-U uplink packets."
    ::= { tmnxMobPdnPdnContextEntry 48 }

tmnxMobPdnPcSgiULBytes  OBJECT-TYPE
    SYNTAX      Counter64
    MAX-ACCESS  read-only
    STATUS      current
    DESCRIPTION
        "The value of tmnxMobPdnPcSgiULBytes indicates the aggregate number
         of S1-U uplink bytes."
    ::= { tmnxMobPdnPdnContextEntry 49 }

tmnxMobPdnPcTnlDLPacketsLow  OBJECT-TYPE
    SYNTAX      Counter32
    MAX-ACCESS  read-only
    STATUS      current
    DESCRIPTION
        "The value of tmnxMobPdnPcTnlDLPacketsLow indicates the lower 32 bits
         of the value of tmnxMobPdnPcTnlDLPackets."
    ::= { tmnxMobPdnPdnContextEntry 50 }

tmnxMobPdnPcTnlDLPacketsHigh  OBJECT-TYPE
    SYNTAX      Counter32
    MAX-ACCESS  read-only
    STATUS      current
    DESCRIPTION
        "The value of tmnxMobPdnPcTnlDLPacketsHigh indicates the higher 32
         bits of the value of tmnxMobPdnPcTnlDLPackets."
    ::= { tmnxMobPdnPdnContextEntry 51 }

tmnxMobPdnPcTnlDLBytesLow  OBJECT-TYPE
    SYNTAX      Counter32
    MAX-ACCESS  read-only
    STATUS      current
    DESCRIPTION
        "The value of tmnxMobPdnPcTnlDLBytesLow indicates the lower 32 bits
         of the value of tmnxMobPdnPcTnlDLBytes."
    ::= { tmnxMobPdnPdnContextEntry 52 }

tmnxMobPdnPcTnlDLBytesHigh  OBJECT-TYPE
    SYNTAX      Counter32
    MAX-ACCESS  read-only
    STATUS      current
    DESCRIPTION
        "The value of tmnxMobPdnPcTnlDLBytesHigh indicates the higher 32
         bits of the value of tmnxMobPdnPcTnlDLBytes."
    ::= { tmnxMobPdnPdnContextEntry 53 }

tmnxMobPdnPcSgiULPacketsLow  OBJECT-TYPE
    SYNTAX      Counter32
    MAX-ACCESS  read-only
    STATUS      current
    DESCRIPTION
        "The value of tmnxMobPdnPcSgiULPacketsLow indicates the lower 32 bits
         of the value of tmnxMobPdnPcSgiULPackets."
    ::= { tmnxMobPdnPdnContextEntry 54 }

tmnxMobPdnPcSgiULPacketsHigh  OBJECT-TYPE
    SYNTAX      Counter32
    MAX-ACCESS  read-only
    STATUS      current
    DESCRIPTION
        "The value of tmnxMobPdnPcSgiULPacketsHigh indicates the higher 32
         bits of the value of tmnxMobPdnPcSgiULPackets."
    ::= { tmnxMobPdnPdnContextEntry 55 }

tmnxMobPdnPcSgiULBytesLow  OBJECT-TYPE
    SYNTAX      Counter32
    MAX-ACCESS  read-only
    STATUS      current
    DESCRIPTION
        "The value of tmnxMobPdnPcSgiULBytesLow indicates the lower 32 bits
         of the value of tmnxMobPdnPcSgiULBytes."
    ::= { tmnxMobPdnPdnContextEntry 56 }

tmnxMobPdnPcSgiULBytesHigh  OBJECT-TYPE
    SYNTAX      Counter32
    MAX-ACCESS  read-only
    STATUS      current
    DESCRIPTION
        "The value of tmnxMobPdnPcSgiULBytesHigh indicates the higher 32
         bits of the value of tmnxMobPdnPcSgiULBytes."
    ::= { tmnxMobPdnPdnContextEntry 57 }

tmnxMobPdnPcImsiAuthStatus  OBJECT-TYPE
    SYNTAX      INTEGER {
                         notApplicable    (0),  
                         authenticated    (1),
                         unauthenticated  (2)
                        }
    MAX-ACCESS  read-only
    STATUS      current
    DESCRIPTION
        "The value of tmnxMobPdnPcImsiAuthStatus indicates the
         authentication status for the International Mobile Subscriber
         Identity (IMSI) of this User Equipment (UE)."
    ::= { tmnxMobPdnPdnContextEntry 58 }

tmnxMobPdnPcImeiStr  OBJECT-TYPE
    SYNTAX      TmnxMobImei
    MAX-ACCESS  read-only
    STATUS      current
    DESCRIPTION
        "The value of tmnxMobPdnPcImeiStr indicates the International Mobile
         Equipment Identity (IMEI) of this User Equipment (UE)."
    ::= { tmnxMobPdnPdnContextEntry 59 }

tmnxMobPdnPcImsiStr  OBJECT-TYPE
    SYNTAX      TmnxMobImsiStr
    MAX-ACCESS  read-only
    STATUS      current
    DESCRIPTION
        "The value of tmnxMobPdnPcImsiStr indicates the International Mobile
         Subscriber Identity (IMSI) of this User Equipment (UE)."
    ::= { tmnxMobPdnPdnContextEntry 60 }

tmnxMobPdnPcSessConfigTime  OBJECT-TYPE
    SYNTAX      Counter32
    UNITS       "seconds"
    MAX-ACCESS  read-only
    STATUS      current
    DESCRIPTION
        "The value of tmnxMobPdnPcSessConfigTime indicates the
         configured session timeout value for the session."
    ::= { tmnxMobPdnPdnContextEntry 61 }

tmnxMobPdnPcSessRemExpTime  OBJECT-TYPE
    SYNTAX      Counter32
    UNITS       "seconds"
    MAX-ACCESS  read-only
    STATUS      current
    DESCRIPTION
        "The value of tmnxMobPdnPcSessRemExpTime indicates the
         time remaining for the expiry of the session timeout value for the
         session."
    ::= { tmnxMobPdnPdnContextEntry 62 }

tmnxMobPdnPcSessTimeDerivedFrom  OBJECT-TYPE
    SYNTAX      INTEGER {
                         static  (0),
                         radius  (1)
                        }
    MAX-ACCESS  read-only
    STATUS      current
    DESCRIPTION
        "The value of tmnxMobPdnPcSessTimeDerivedFrom indicates whether the
         session timeout value is derived from radius or from static
         configuration."
    ::= { tmnxMobPdnPdnContextEntry 63 }

tmnxMobPdnPcIdleConfigTime  OBJECT-TYPE
    SYNTAX      Counter32
    UNITS       "seconds"
    MAX-ACCESS  read-only
    STATUS      current
    DESCRIPTION
        "The value of tmnxMobPdnPcIdleConfigTime indicates the
         configured idle timeout value for the session."
    ::= { tmnxMobPdnPdnContextEntry 64 }

tmnxMobPdnPcIdleRemExpTime  OBJECT-TYPE
    SYNTAX      Counter32
    UNITS       "seconds"
    MAX-ACCESS  read-only
    STATUS      current
    DESCRIPTION
        "The value of tmnxMobPdnPcIdleRemExpTime indicates the
         time remaining for the expiry of the idle timeout value for the
         session."
    ::= { tmnxMobPdnPdnContextEntry 65 }

tmnxMobPdnPcIdleTimeDerivedFrom  OBJECT-TYPE
    SYNTAX      INTEGER {
                         static  (0),
                         radius  (1)
                        }
    MAX-ACCESS  read-only
    STATUS      current
    DESCRIPTION
        "The value of tmnxMobPdnPcIdleTimeDerivedFrom indicates whether the
         idle timeout value is derived from radius or from static
         configuration."
    ::= { tmnxMobPdnPdnContextEntry 66 }

tmnxMobPdnPcRefPointType  OBJECT-TYPE
    SYNTAX      TmnxMobPdnRefPointType
    MAX-ACCESS  read-only
    STATUS      current
    DESCRIPTION
        "The value of tmnxMobPdnPcRefPointType indicates the reference point
         type for the session."
    ::= { tmnxMobPdnPdnContextEntry 67 }

--
--  Bearer Context Table
--

tmnxMobPdnBearerContextTable  OBJECT-TYPE
    SYNTAX      SEQUENCE OF TmnxMobPdnBearerContextEntry
    MAX-ACCESS  not-accessible
    STATUS      current
    DESCRIPTION
        "The tmnxMobPdnBearerContextTable has an entry for each bearer context
         of an User Equipment (UE)."
    ::= { tmnxMobPdnStatObjs 3 }

tmnxMobPdnBearerContextEntry  OBJECT-TYPE
    SYNTAX      TmnxMobPdnBearerContextEntry
    MAX-ACCESS  not-accessible
    STATUS      current
    DESCRIPTION
        "Each row entry represents a bearer context of an User Equipment (UE)
         and contains identification, connection, statistics information."
    INDEX { tmnxMobGwId,
            tmnxMobPdnUeImsi,
            tmnxMobPdnPcApn,
            tmnxMobPdnPcPdnType,
            tmnxMobPdnBcBearerId
          }
    ::= { tmnxMobPdnBearerContextTable 1 }

TmnxMobPdnBearerContextEntry ::= SEQUENCE {
        tmnxMobPdnBcBearerId               TmnxMobBearerId,
        tmnxMobPdnBcBearerType             TmnxMobBearerType,
        tmnxMobPdnBcUpTime                 Unsigned32,
        tmnxMobPdnBcQci                    TmnxMobQci,
        tmnxMobPdnBcArp                    TmnxMobArp,
        tmnxMobPdnBcSdfs                   TmnxMobSdf,
        tmnxMobPdnBcFilters                TmnxMobSdfFilterNum,
        tmnxMobPdnBcTnlRemoteTeid          Unsigned32,
        tmnxMobPdnBcTnlRemoteDataAddrTyp   InetAddressType,
        tmnxMobPdnBcTnlRemoteDataAddr      InetAddress,
        tmnxMobPdnBcTnlLocalTeid           Unsigned32,
        tmnxMobPdnBcTnlLocalDataAddrType   InetAddressType,
        tmnxMobPdnBcTnlLocalDataAddr       InetAddress,
        tmnxMobPdnBcTnlDLPackets           Counter64,
        tmnxMobPdnBcTnlDLBytes             Counter64,
        tmnxMobPdnBcSgiULPackets           Counter64,
        tmnxMobPdnBcSgiULBytes             Counter64,
        tmnxMobPdnBcTnlDLPacketsLow        Counter32,
        tmnxMobPdnBcTnlDLPacketsHigh       Counter32,
        tmnxMobPdnBcTnlDLBytesLow          Counter32,
        tmnxMobPdnBcTnlDLBytesHigh         Counter32,
        tmnxMobPdnBcSgiULPacketsLow        Counter32,
        tmnxMobPdnBcSgiULPacketsHigh       Counter32,
        tmnxMobPdnBcSgiULBytesLow          Counter32,
        tmnxMobPdnBcSgiULBytesHigh         Counter32,
        tmnxMobPdnBcOfcServerAddrType      InetAddressType,
        tmnxMobPdnBcOfcServerAddr          InetAddress,
        tmnxMobPdnBcOfcServerState         TmnxMobServerState,
        tmnxMobPdnBcOfcChargingProfile     TmnxMobChargingProfile,
        tmnxMobPdnBcOfcTriggeredRecords    Counter32,
        tmnxMobPdnBcOfcInterimRecords      Counter32,
        tmnxMobPdnBcAccessType             TmnxMobAccessType,
        tmnxMobPdnBcPGWGreKey              Unsigned32,
        tmnxMobPdnBcMAGGreKey              Unsigned32,
        tmnxMobPdnBcRefPointType           TmnxMobPdnRefPointType,
        tmnxMobPdnBcChargingChar           Unsigned32,
        tmnxMobPdnBcQosBytes               TmnxQosBytesHex
    }

tmnxMobPdnBcBearerId  OBJECT-TYPE
    SYNTAX      TmnxMobBearerId
    MAX-ACCESS  not-accessible
    STATUS      current
    DESCRIPTION
        "The value of tmnxMobPdnBcBearerId indicates the bearer id which
         uniquely identifies a bearer context in a Packet Data Network (PDN)
         context."
    ::= { tmnxMobPdnBearerContextEntry 1 }

tmnxMobPdnBcBearerType  OBJECT-TYPE
    SYNTAX      TmnxMobBearerType
    MAX-ACCESS  read-only
    STATUS      current
    DESCRIPTION
        "The value of tmnxMobPdnBcBearerType indicates the type of this
         bearer."
    ::= { tmnxMobPdnBearerContextEntry 2 }

tmnxMobPdnBcUpTime  OBJECT-TYPE
    SYNTAX      Unsigned32
    UNITS       "seconds"
    MAX-ACCESS  read-only
    STATUS      current
    DESCRIPTION
        "The value of tmnxMobPdnBcUpTime indicates the time, in seconds,
         since this bearer context was created."
    ::= { tmnxMobPdnBearerContextEntry 3 }
    
tmnxMobPdnBcQci  OBJECT-TYPE
    SYNTAX      TmnxMobQci
    MAX-ACCESS  read-only
    STATUS      current
    DESCRIPTION
        "The value of tmnxMobPdnBcQci indicates the Qos Class Identifier of
         this bearer context. The value of this object is used as a reference
         to access node-specific parameters that control bearer level packet
         forwarding treatment."
    ::= { tmnxMobPdnBearerContextEntry 4 }

tmnxMobPdnBcArp  OBJECT-TYPE
    SYNTAX      TmnxMobArp
    MAX-ACCESS  read-only
    STATUS      current
    DESCRIPTION
        "The value of tmnxMobPdnBcArp indicates the Allocation and Retention
         Priority (ARP) of this bearer context. The value of this object gives
         information about the priority level, the pre-emption capability and
         the pre-emption vulnerability."
    ::= { tmnxMobPdnBearerContextEntry 5 }

tmnxMobPdnBcSdfs  OBJECT-TYPE
    SYNTAX      TmnxMobSdf
    MAX-ACCESS  read-only
    STATUS      current
    DESCRIPTION
        "The value of tmnxMobPdnBcSdfs indicates the number of Service Data
         Flows (SDFs) in this bearer context."
    ::= { tmnxMobPdnBearerContextEntry 6 }

tmnxMobPdnBcFilters  OBJECT-TYPE
    SYNTAX      TmnxMobSdfFilterNum
    MAX-ACCESS  read-only
    STATUS      current
    DESCRIPTION
        "The value of tmnxMobPdnBcFilters indicates the number of IP filters 
         in this bearer context."
    ::= { tmnxMobPdnBearerContextEntry 7 }

tmnxMobPdnBcTnlRemoteTeid  OBJECT-TYPE
    SYNTAX      Unsigned32
    MAX-ACCESS  read-only
    STATUS      current
    DESCRIPTION
        "The value of tmnxMobPdnBcTnlRemoteTeid indicates the Tunnel Endpoint
         Identifier (TEID) of the Serving Gateway (SGW) on the S5 or S8
         reference point."
    ::= { tmnxMobPdnBearerContextEntry 8 }

tmnxMobPdnBcTnlRemoteDataAddrTyp  OBJECT-TYPE
    SYNTAX      InetAddressType
    MAX-ACCESS  read-only
    STATUS      current
    DESCRIPTION
        "The value of tmnxMobPdnBcTnlRemoteDataAddrTyp indicates the type of
         address represented by tmnxMobPdnBcTnlRemoteDataAddr."
    ::= { tmnxMobPdnBearerContextEntry 9 }

tmnxMobPdnBcTnlRemoteDataAddr  OBJECT-TYPE
    SYNTAX      InetAddress (SIZE (0|4|16))
    MAX-ACCESS  read-only
    STATUS      current
    DESCRIPTION
        "The value of tmnxMobPdnBcTnlRemoteDataAddr indicates the IP address of
         the Serving Gateway (SGW) on the S5 or S8 reference point.

         The value of tmnxMobPdnBcTnlRemoteDataAddr indicates the IP address of 
         the Mobile Access Gateway (MAG) on the S2a reference point."
    ::= { tmnxMobPdnBearerContextEntry 10 }

tmnxMobPdnBcTnlLocalTeid  OBJECT-TYPE
    SYNTAX      Unsigned32
    MAX-ACCESS  read-only
    STATUS      current
    DESCRIPTION
        "The value of tmnxMobPdnBcTnlLocalTeid indicates the Tunnel Endpoint
         Identifier (TEID) of the Packet Data Network Gateway (PGW) on the S5 
         or S8 reference point."
    ::= { tmnxMobPdnBearerContextEntry 11 }

tmnxMobPdnBcTnlLocalDataAddrType  OBJECT-TYPE
    SYNTAX      InetAddressType
    MAX-ACCESS  read-only
    STATUS      current
    DESCRIPTION
        "The value of tmnxMobPdnBcTnlLocalDataAddrType indicates the type of
         address represented by tmnxMobPdnBcTnlLocalDataAddr."
    ::= { tmnxMobPdnBearerContextEntry 12 }

tmnxMobPdnBcTnlLocalDataAddr  OBJECT-TYPE
    SYNTAX      InetAddress (SIZE (0|4|16))
    MAX-ACCESS  read-only
    STATUS      current
    DESCRIPTION
        "The value of tmnxMobPdnBcTnlLocalDataAddr indicates the IP address of
         the Packet Data Network Gateway (PGW) on the S5, S8 or S2a reference point."
    ::= { tmnxMobPdnBearerContextEntry 13 }

tmnxMobPdnBcTnlDLPackets  OBJECT-TYPE
    SYNTAX      Counter64
    MAX-ACCESS  read-only
    STATUS      current
    DESCRIPTION
        "The value of tmnxMobPdnBcTnlDLPackets indicates the number of
         S5 or S2a downlink packets."
    ::= { tmnxMobPdnBearerContextEntry 14 }

tmnxMobPdnBcTnlDLBytes  OBJECT-TYPE
    SYNTAX      Counter64
    MAX-ACCESS  read-only
    STATUS      current
    DESCRIPTION
        "The value of tmnxMobPdnBcTnlDLBytes indicates the number of
         S5 or S2a downlink bytes."
    ::= { tmnxMobPdnBearerContextEntry 15 }

tmnxMobPdnBcSgiULPackets  OBJECT-TYPE
    SYNTAX      Counter64
    MAX-ACCESS  read-only
    STATUS      current
    DESCRIPTION
        "The value of tmnxMobPdnBcSgiULPackets indicates the number of
         S1-U uplink packets."
    ::= { tmnxMobPdnBearerContextEntry 16 }

tmnxMobPdnBcSgiULBytes  OBJECT-TYPE
    SYNTAX      Counter64
    MAX-ACCESS  read-only
    STATUS      current
    DESCRIPTION
        "The value of tmnxMobPdnBcSgiULBytes indicates the number of
         S1-U uplink bytes."
    ::= { tmnxMobPdnBearerContextEntry 17 }
    
tmnxMobPdnBcTnlDLPacketsLow  OBJECT-TYPE
    SYNTAX      Counter32
    MAX-ACCESS  read-only
    STATUS      current
    DESCRIPTION
        "The value of tmnxMobPdnBcTnlDLPacketsLow indicates the lower 32 bits
         of the value of tmnxMobPdnBcTnlDLPackets."
    ::= { tmnxMobPdnBearerContextEntry 18 }

tmnxMobPdnBcTnlDLPacketsHigh  OBJECT-TYPE
    SYNTAX      Counter32
    MAX-ACCESS  read-only
    STATUS      current
    DESCRIPTION
        "The value of tmnxMobPdnBcTnlDLPacketsHigh indicates the higher 32
         bits of the value of tmnxMobPdnBcTnlDLPackets."
    ::= { tmnxMobPdnBearerContextEntry 19 }

tmnxMobPdnBcTnlDLBytesLow  OBJECT-TYPE
    SYNTAX      Counter32
    MAX-ACCESS  read-only
    STATUS      current
    DESCRIPTION
        "The value of tmnxMobPdnBcTnlDLBytesLow indicates the lower 32 bits
         of the value of tmnxMobPdnBcTnlDLBytes."
    ::= { tmnxMobPdnBearerContextEntry 20 }

tmnxMobPdnBcTnlDLBytesHigh  OBJECT-TYPE
    SYNTAX      Counter32
    MAX-ACCESS  read-only
    STATUS      current
    DESCRIPTION
        "The value of tmnxMobPdnBcTnlDLBytesHigh indicates the higher 32
         bits of the value of tmnxMobPdnBcTnlDLBytes."
    ::= { tmnxMobPdnBearerContextEntry 21 }

tmnxMobPdnBcSgiULPacketsLow  OBJECT-TYPE
    SYNTAX      Counter32
    MAX-ACCESS  read-only
    STATUS      current
    DESCRIPTION
        "The value of tmnxMobPdnBcSgiULPacketsLow indicates the lower 32 bits
         of the value of tmnxMobPdnBcSgiULPackets."
    ::= { tmnxMobPdnBearerContextEntry 22 }

tmnxMobPdnBcSgiULPacketsHigh  OBJECT-TYPE
    SYNTAX      Counter32
    MAX-ACCESS  read-only
    STATUS      current
    DESCRIPTION
        "The value of tmnxMobPdnBcSgiULPacketsHigh indicates the higher 32
         bits of the value of tmnxMobPdnBcSgiULPackets."
    ::= { tmnxMobPdnBearerContextEntry 23 }

tmnxMobPdnBcSgiULBytesLow  OBJECT-TYPE
    SYNTAX      Counter32
    MAX-ACCESS  read-only
    STATUS      current
    DESCRIPTION
        "The value of tmnxMobPdnBcSgiULBytesLow indicates the lower 32 bits
         of the value of tmnxMobPdnBcSgiULBytes."
    ::= { tmnxMobPdnBearerContextEntry 24 }

tmnxMobPdnBcSgiULBytesHigh  OBJECT-TYPE
    SYNTAX      Counter32
    MAX-ACCESS  read-only
    STATUS      current
    DESCRIPTION
        "The value of tmnxMobPdnBcSgiULBytesHigh indicates the higher 32
         bits of the value of tmnxMobPdnBcSgiULBytes."
    ::= { tmnxMobPdnBearerContextEntry 25 }

tmnxMobPdnBcOfcServerAddrType  OBJECT-TYPE
    SYNTAX      InetAddressType
    MAX-ACCESS  read-only
    STATUS      current
    DESCRIPTION
        "The value of tmnxMobPdnBcOfcServerAddrType indicates the type of
         address represented by tmnxMobPdnBcOfcServerAddr."
    ::= { tmnxMobPdnBearerContextEntry 26 }

tmnxMobPdnBcOfcServerAddr  OBJECT-TYPE
    SYNTAX      InetAddress (SIZE (0|4|16))
    MAX-ACCESS  read-only
    STATUS      current
    DESCRIPTION
        "The value of tmnxMobPdnBcOfcServerAddr indicates the charging server
         address on the Rf reference point."
    ::= { tmnxMobPdnBearerContextEntry 27 }

tmnxMobPdnBcOfcServerState  OBJECT-TYPE
    SYNTAX      TmnxMobServerState
    MAX-ACCESS  read-only
    STATUS      current
    DESCRIPTION
        "The value of tmnxMobPdnBcOfcServerState indicates the charging server
         state on the Rf reference point."
    ::= { tmnxMobPdnBearerContextEntry 28 }

tmnxMobPdnBcOfcChargingProfile  OBJECT-TYPE
    SYNTAX      TmnxMobChargingProfile
    MAX-ACCESS  read-only
    STATUS      current
    DESCRIPTION
        "The value of tmnxMobPdnBcOfcChargingProfile indicates the charging 
         profile used on the Rf reference point."
    ::= { tmnxMobPdnBearerContextEntry 29 }

tmnxMobPdnBcOfcTriggeredRecords  OBJECT-TYPE
    SYNTAX      Counter32
    MAX-ACCESS  read-only
    STATUS      current
    DESCRIPTION
        "The value of tmnxMobPdnBcOfcTriggeredRecords indicates the number of 
         records generated by triggers on the Rf reference point."
    ::= { tmnxMobPdnBearerContextEntry 30 }

tmnxMobPdnBcOfcInterimRecords  OBJECT-TYPE
    SYNTAX      Counter32
    MAX-ACCESS  read-only
    STATUS      current
    DESCRIPTION
        "The value of tmnxMobPdnBcOfcInterimRecords indicates the number of
         interim records sent on the Rf reference point."
    ::= { tmnxMobPdnBearerContextEntry 31 }

tmnxMobPdnBcAccessType  OBJECT-TYPE
    SYNTAX      TmnxMobAccessType
    MAX-ACCESS  read-only
    STATUS      current
    DESCRIPTION
        "The value of tmnxMobPdnBcAccessType specifies the access type for the 
         bearer context of an User Equipment (UE)."
    ::= { tmnxMobPdnBearerContextEntry 32 }

tmnxMobPdnBcPGWGreKey  OBJECT-TYPE
    SYNTAX      Unsigned32
    MAX-ACCESS  read-only
    STATUS      current
    DESCRIPTION
        "The value of tmnxMobPdnBcPGWGreKey indicates the Pakcet Data 
         Network Gateway (PGW) data plane Generic Routing Encapsulation
         (GRE) key on S2a reference point in the uplink direction."
    ::= { tmnxMobPdnBearerContextEntry 33 }

tmnxMobPdnBcMAGGreKey  OBJECT-TYPE
    SYNTAX      Unsigned32
    MAX-ACCESS  read-only
    STATUS      current
    DESCRIPTION
        "The value of tmnxMobPdnBcMAGGreKey indicates the Mobile Access Gateway 
         (MAG) data plane Generic Routing Encapsulation (GRE) key on S2a
         reference point in the downlink direction."
    ::= { tmnxMobPdnBearerContextEntry 34 }

tmnxMobPdnBcRefPointType  OBJECT-TYPE
    SYNTAX      TmnxMobPdnRefPointType
    MAX-ACCESS  read-only
    STATUS      current
    DESCRIPTION
        "The value of tmnxMobPdnBcRefPointType indicates the reference point
         type for the bearer context of an User Equipment (UE)."
    ::= { tmnxMobPdnBearerContextEntry 35 }

tmnxMobPdnBcChargingChar  OBJECT-TYPE
    SYNTAX      Unsigned32
    MAX-ACCESS  read-only
    STATUS      current
    DESCRIPTION
        "The value of tmnxMobPdnBcChargingChar indicates the charging
         characteristics received for the bearer context of an User
         Equipment (UE)."
    ::= { tmnxMobPdnBearerContextEntry 36 }

tmnxMobPdnBcQosBytes  OBJECT-TYPE
    SYNTAX      TmnxQosBytesHex
    MAX-ACCESS  read-only
    STATUS      current
    DESCRIPTION
        "The value of tmnxMobPdnBcQosBytes indicates the QoS bytes that has been
         requested for the bearer context of an User Equipment (UE)."
    ::= { tmnxMobPdnBearerContextEntry 37 }

--
--  Bearer Context SDF Table
--

tmnxMobPdnBcSdfTable  OBJECT-TYPE
    SYNTAX      SEQUENCE OF TmnxMobPdnBcSdfEntry
    MAX-ACCESS  not-accessible
    STATUS      current
    DESCRIPTION
        "The tmnxMobPdnBcSdfTable has an entry for each Service Data
         Flow mapped to a bearer of a User Equipment (UE)."
    ::= { tmnxMobPdnStatObjs 4 }

tmnxMobPdnBcSdfEntry  OBJECT-TYPE
    SYNTAX      TmnxMobPdnBcSdfEntry
    MAX-ACCESS  not-accessible
    STATUS      current
    DESCRIPTION
        "Each row entry represents an Service Data Flow (SDF). Service Data
         Flows are defined by the Policy and Charging Rules Function (PCRF)."
    INDEX { tmnxMobGwId,
            tmnxMobPdnUeImsi,
            tmnxMobPdnPcApn,
            tmnxMobPdnPcPdnType,
            tmnxMobPdnBcBearerId,
            tmnxMobPdnBcSdfPrecedence
          }
    ::= { tmnxMobPdnBcSdfTable 1 }

TmnxMobPdnBcSdfEntry ::= SEQUENCE {
        tmnxMobPdnBcSdfPrecedence          Unsigned32,
        tmnxMobPdnBcSdfPcrfPrecedence      Unsigned32,
        tmnxMobPdnBcSdfRuleName            TmnxMobSdfRuleName,
        tmnxMobPdnBcSdfPacketFilters       Unsigned32,
        tmnxMobPdnBcSdfQosUlMbr            Unsigned32,
        tmnxMobPdnBcSdfQosDlMbr            Unsigned32,
        tmnxMobPdnBcSdfQosUlGbr            Unsigned32,
        tmnxMobPdnBcSdfQosDlGbr            Unsigned32
    }

tmnxMobPdnBcSdfPrecedence  OBJECT-TYPE
    SYNTAX      Unsigned32 (0..4294967295)
    MAX-ACCESS  not-accessible
    STATUS      current
    DESCRIPTION
        "The value of tmnxMobPdnBcSdfPrecedence indicates the internally 
         mapped value of rule precedence of this Service Data Flow (SDF)."
    ::= { tmnxMobPdnBcSdfEntry 1 }

tmnxMobPdnBcSdfPcrfPrecedence  OBJECT-TYPE
    SYNTAX      Unsigned32
    MAX-ACCESS  read-only
    STATUS      current
    DESCRIPTION
        "The value of tmnxMobPdnBcSdfPcrfPrecedence indicates the rule
         precedence of this Service Data Flow (SDF) received from the Policy
         and Charging Rules Function (PCRF)."
    ::= { tmnxMobPdnBcSdfEntry 2 }

tmnxMobPdnBcSdfRuleName  OBJECT-TYPE
    SYNTAX      TmnxMobSdfRuleName
    MAX-ACCESS  read-only
    STATUS      current
    DESCRIPTION
        "The value of tmnxMobPdnBcSdfRuleName indicates the policy rule name
         of this Service Data Flow (SDF). Rule name is unique within an IP-CAN
         session."
    ::= { tmnxMobPdnBcSdfEntry 3 }

tmnxMobPdnBcSdfPacketFilters  OBJECT-TYPE
    SYNTAX      Unsigned32
    MAX-ACCESS  read-only
    STATUS      current
    DESCRIPTION
        "The value of tmnxMobPdnBcSdfPacketFilters indicates the number of
         packet filters in this Service Data Flow (SDF)."
    ::= { tmnxMobPdnBcSdfEntry 4 }

tmnxMobPdnBcSdfQosUlMbr  OBJECT-TYPE
    SYNTAX      Unsigned32
    UNITS       "Kbps"
    MAX-ACCESS  read-only
    STATUS      current
    DESCRIPTION
        "The value of tmnxMobPdnBcSdfQosUlMbr indicates the uplink Maximum
         Bit Rate (MBR) included within the rule."
    ::= { tmnxMobPdnBcSdfEntry 5 }

tmnxMobPdnBcSdfQosDlMbr  OBJECT-TYPE
    SYNTAX      Unsigned32
    UNITS       "Kbps"
    MAX-ACCESS  read-only
    STATUS      current
    DESCRIPTION
        "The value of tmnxMobPdnBcSdfQosDlMbr indicates the downlink Maximum
         Bit Rate (MBR) included within the rule."
    ::= { tmnxMobPdnBcSdfEntry 6 }

tmnxMobPdnBcSdfQosUlGbr  OBJECT-TYPE
    SYNTAX      Unsigned32
    UNITS       "Kbps"
    MAX-ACCESS  read-only
    STATUS      current
    DESCRIPTION
        "The value of tmnxMobPdnBcSdfQosUlGbr indicates the uplink Guaranteed
         Bit Rate (MBR) included within the rule."
    ::= { tmnxMobPdnBcSdfEntry 7 }

tmnxMobPdnBcSdfQosDlGbr  OBJECT-TYPE
    SYNTAX      Unsigned32
    UNITS       "Kbps"
    MAX-ACCESS  read-only
    STATUS      current
    DESCRIPTION
        "The value of tmnxMobPdnBcSdfQosDlGbr indicates the downlink
         Guaranteed Bit Rate (MBR) included within the rule."
    ::= { tmnxMobPdnBcSdfEntry 8 }

--
--  Bearer Context SDF IP Packet Filter Table
--

tmnxMobPdnBcSdfFilterTable  OBJECT-TYPE
    SYNTAX      SEQUENCE OF TmnxMobPdnBcSdfFilterEntry
    MAX-ACCESS  not-accessible
    STATUS      current
    DESCRIPTION
        "The tmnxMobPdnBcSdfFilterTable has an entry for each IP filter rule
         defined in a Service Data Flow (SDF)."
    ::= { tmnxMobPdnStatObjs 5 }

tmnxMobPdnBcSdfFilterEntry  OBJECT-TYPE
    SYNTAX      TmnxMobPdnBcSdfFilterEntry
    MAX-ACCESS  not-accessible
    STATUS      current
    DESCRIPTION
        "Each row entry represents an IP filter rule defined in a Service Data
         Flow (SDF)."
    INDEX { tmnxMobGwId,
            tmnxMobPdnUeImsi,
            tmnxMobPdnPcApn,
            tmnxMobPdnPcPdnType,
            tmnxMobPdnBcBearerId,
            tmnxMobPdnBcSdfPrecedence,
            tmnxMobPdnBcSdfFilterDirection,
            tmnxMobPdnBcSdfFilterId
          }
    ::= { tmnxMobPdnBcSdfFilterTable 1 }

TmnxMobPdnBcSdfFilterEntry ::= SEQUENCE {
        tmnxMobPdnBcSdfFilterDirection     TmnxMobSdfFilterDirection,
        tmnxMobPdnBcSdfFilterId            TmnxMobSdfFilter,
        tmnxMobPdnBcSdfFilterProtocol      TmnxMobSdfFilterProtocol,
        tmnxMobPdnBcSdfFilterSrcAdrType    InetAddressType,
        tmnxMobPdnBcSdfFilterSrcAddr       InetAddress,
        tmnxMobPdnBcSdfFilterSrcPfxLen     InetAddressPrefixLength,
        tmnxMobPdnBcSdfFilterDstAdrType    InetAddressType,
        tmnxMobPdnBcSdfFilterDestAddr      InetAddress,
        tmnxMobPdnBcSdfFilterDestPfxLen    InetAddressPrefixLength,
        tmnxMobPdnBcSdfFilterSrcPorts      Unsigned32,
        tmnxMobPdnBcSdfFilterDestPorts     Unsigned32,
        tmnxMobPdnBcSdfFirstSrcPortOper    TTcpUdpPortOperator,
        tmnxMobPdnBcSdfFirstSrcPortVal1    TTcpUdpPort,
        tmnxMobPdnBcSdfFirstSrcPortVal2    TTcpUdpPort,
        tmnxMobPdnBcSdfSecndSrcPortOper    TTcpUdpPortOperator,
        tmnxMobPdnBcSdfSecndSrcPortVal1    TTcpUdpPort,
        tmnxMobPdnBcSdfSecndSrcPortVal2    TTcpUdpPort,
        tmnxMobPdnBcSdfFirstDstPortOper    TTcpUdpPortOperator,
        tmnxMobPdnBcSdfFirstDstPortVal1    TTcpUdpPort,
        tmnxMobPdnBcSdfFirstDstPortVal2    TTcpUdpPort,
        tmnxMobPdnBcSdfSecndDstPortOper    TTcpUdpPortOperator,
        tmnxMobPdnBcSdfSecndDstPortVal1    TTcpUdpPort,
        tmnxMobPdnBcSdfSecndDstPortVal2    TTcpUdpPort
    }

tmnxMobPdnBcSdfFilterDirection  OBJECT-TYPE
    SYNTAX      TmnxMobSdfFilterDirection
    MAX-ACCESS  not-accessible
    STATUS      current
    DESCRIPTION
        "The value of tmnxMobPdnBcSdfFilterDirection indicates the direction
         on which this filter rule is valid."
    ::= { tmnxMobPdnBcSdfFilterEntry 1 }

tmnxMobPdnBcSdfFilterId  OBJECT-TYPE
    SYNTAX      TmnxMobSdfFilter
    MAX-ACCESS  not-accessible
    STATUS      current
    DESCRIPTION
        "The value of tmnxMobPdnBcSdfFilterId indicates the unique value which
         identifies a filter rule in the Service Data Flow (SDF)."
    ::= { tmnxMobPdnBcSdfFilterEntry 2 }

tmnxMobPdnBcSdfFilterProtocol  OBJECT-TYPE
    SYNTAX      TmnxMobSdfFilterProtocol
    MAX-ACCESS  read-only
    STATUS      current
    DESCRIPTION
        "The value of tmnxMobPdnBcSdfFilterProtocol indicates the IPv4 protocol 
         or IPv6 next header on which this filter matches.

         If the value of this object is set to 'any', then this filter matches
         any protocol field."
    ::= { tmnxMobPdnBcSdfFilterEntry 3 }

tmnxMobPdnBcSdfFilterSrcAdrType  OBJECT-TYPE
    SYNTAX      InetAddressType
    MAX-ACCESS  read-only
    STATUS      current
    DESCRIPTION
        "The value of tmnxMobPdnBcSdfFilterSrcAdrType indicates the type of
         address represented by tmnxMobPdnBcSdfFilterSrcAddr."
    ::= { tmnxMobPdnBcSdfFilterEntry 4 }

tmnxMobPdnBcSdfFilterSrcAddr  OBJECT-TYPE
    SYNTAX      InetAddress (SIZE (0|4|16))
    MAX-ACCESS  read-only
    STATUS      current
    DESCRIPTION
        "The value of tmnxMobPdnBcSdfFilterSrcAddr indicates the local IP 
         adddress of the Mobile Subscriber (MS) on which this filter rule 
         is applied."
    ::= { tmnxMobPdnBcSdfFilterEntry 5 }

tmnxMobPdnBcSdfFilterSrcPfxLen  OBJECT-TYPE
    SYNTAX      InetAddressPrefixLength
    MAX-ACCESS  read-only
    STATUS      current
    DESCRIPTION
        "The value of tmnxMobPdnBcSdfFilterSrcPfxLen indicates the prefix
         mask length of tmnxMobPdnBcSdfFilterSrcAddr."
    ::= { tmnxMobPdnBcSdfFilterEntry 6 }

tmnxMobPdnBcSdfFilterDstAdrType  OBJECT-TYPE
    SYNTAX      InetAddressType
    MAX-ACCESS  read-only
    STATUS      current
    DESCRIPTION
        "The value of tmnxMobPdnBcSdfFilterDstAdrType indicates the type of
         address represented by tmnxMobPdnBcSdfFilterDestAddr."
    ::= { tmnxMobPdnBcSdfFilterEntry 7 }

tmnxMobPdnBcSdfFilterDestAddr  OBJECT-TYPE
    SYNTAX      InetAddress (SIZE (0|4|16))
    MAX-ACCESS  read-only
    STATUS      current
    DESCRIPTION
        "The value of tmnxMobPdnBcSdfFilterDestAddr indicates the remote IP
         adddress of the external network entity on which this filter rule 
         is applied."
    ::= { tmnxMobPdnBcSdfFilterEntry 8 }

tmnxMobPdnBcSdfFilterDestPfxLen  OBJECT-TYPE
    SYNTAX      InetAddressPrefixLength
    MAX-ACCESS  read-only
    STATUS      current
    DESCRIPTION
        "The value of tmnxMobPdnBcSdfFilterDestPfxLen indicates the prefix
         mask length of tmnxMobPdnBcSdfFilterDestPfxLen."
    ::= { tmnxMobPdnBcSdfFilterEntry 9 }

tmnxMobPdnBcSdfFilterSrcPorts  OBJECT-TYPE
    SYNTAX      Unsigned32
    MAX-ACCESS  read-only
    STATUS      current
    DESCRIPTION
        "The value of tmnxMobPdnBcSdfFilterSrcPorts indicates the number of
         local ports."
    ::= { tmnxMobPdnBcSdfFilterEntry 10 }

tmnxMobPdnBcSdfFilterDestPorts  OBJECT-TYPE
    SYNTAX      Unsigned32
    MAX-ACCESS  read-only
    STATUS      current
    DESCRIPTION
        "The value of tmnxMobPdnBcSdfFilterDestPorts indicates the number of
         remote ports."
    ::= { tmnxMobPdnBcSdfFilterEntry 11 }

tmnxMobPdnBcSdfFirstSrcPortOper  OBJECT-TYPE
    SYNTAX      TTcpUdpPortOperator
    MAX-ACCESS  read-only
    STATUS      current
    DESCRIPTION
        "The value of tmnxMobPdnBcSdfFirstSrcPortOper indicates the manner in
         which tmnxMobPdnBcSdfFirstSrcPortVal1 and
         tmnxMobPdnBcSdfFirstSrcPortVal2 are to be used. The values of these
         three objects are used as described in TTcpUdpPortOperator."
    ::= { tmnxMobPdnBcSdfFilterEntry 12 }

tmnxMobPdnBcSdfFirstSrcPortVal1  OBJECT-TYPE
    SYNTAX      TTcpUdpPort
    MAX-ACCESS  read-only
    STATUS      current
    DESCRIPTION
        "The value of tmnxMobPdnBcSdfFirstSrcPortVal1 indicates the TCP or UDP
         starting local port. The value of this object is used as per the
         description for tmnxMobPdnBcSdfFirstSrcPortOper."
    ::= { tmnxMobPdnBcSdfFilterEntry 13 }

tmnxMobPdnBcSdfFirstSrcPortVal2  OBJECT-TYPE
    SYNTAX      TTcpUdpPort
    MAX-ACCESS  read-only
    STATUS      current
    DESCRIPTION
        "The value of tmnxMobPdnBcSdfFirstSrcPortVal2 indicates the TCP or UDP
         starting local port. The value of this object is used as per the
         description for tmnxMobPdnBcSdfFirstSrcPortOper."
    ::= { tmnxMobPdnBcSdfFilterEntry 14 }

tmnxMobPdnBcSdfSecndSrcPortOper  OBJECT-TYPE
    SYNTAX      TTcpUdpPortOperator
    MAX-ACCESS  read-only
    STATUS      current
    DESCRIPTION
        "The value of tmnxMobPdnBcSdfSecndSrcPortOper indicates the manner in
         which tmnxMobPdnBcSdfSecndSrcPortVal2 and
         tmnxMobPdnBcSdfFirstSrcPortVal2 are to be used. The values of these
         three objects are used as described in TTcpUdpPortOperator."
    ::= { tmnxMobPdnBcSdfFilterEntry 15 }

tmnxMobPdnBcSdfSecndSrcPortVal1  OBJECT-TYPE
    SYNTAX      TTcpUdpPort
    MAX-ACCESS  read-only
    STATUS      current
    DESCRIPTION
        "The value of tmnxMobPdnBcSdfSecndSrcPortVal1 indicates the TCP or UDP
         starting local port. The value of this object is used as per the
         description for tmnxMobPdnBcSdfSecndSrcPortOper."
    ::= { tmnxMobPdnBcSdfFilterEntry 16 }

tmnxMobPdnBcSdfSecndSrcPortVal2  OBJECT-TYPE
    SYNTAX      TTcpUdpPort
    MAX-ACCESS  read-only
    STATUS      current
    DESCRIPTION
        "The value of tmnxMobPdnBcSdfSecndSrcPortVal2 indicates the TCP or UDP
         starting local port. The value of this object is used as per the
         description for tmnxMobPdnBcSdfSecndSrcPortOper."
    ::= { tmnxMobPdnBcSdfFilterEntry 17 }

tmnxMobPdnBcSdfFirstDstPortOper  OBJECT-TYPE
    SYNTAX      TTcpUdpPortOperator
    MAX-ACCESS  read-only
    STATUS      current
    DESCRIPTION
        "The value of tmnxMobPdnBcSdfFirstDstPortOper indicates the manner in
         which tmnxMobPdnBcSdfFirstDstPortVal1 and
         tmnxMobPdnBcSdfFirstDstPortVal2 are to be used. The values of these
         three objects are used as described in TTcpUdpPortOperator."
    ::= { tmnxMobPdnBcSdfFilterEntry 18 }

tmnxMobPdnBcSdfFirstDstPortVal1  OBJECT-TYPE
    SYNTAX      TTcpUdpPort
    MAX-ACCESS  read-only
    STATUS      current
    DESCRIPTION
        "The value of tmnxMobPdnBcSdfFirstDstPortVal1 indicates the TCP or UDP
         starting remote port. The value of this object is used as per the
         description for tmnxMobPdnBcSdfFirstDstPortOper."
    ::= { tmnxMobPdnBcSdfFilterEntry 19 }

tmnxMobPdnBcSdfFirstDstPortVal2  OBJECT-TYPE
    SYNTAX      TTcpUdpPort
    MAX-ACCESS  read-only
    STATUS      current
    DESCRIPTION
        "The value of tmnxMobPdnBcSdfFirstDstPortVal2 indicates the TCP or UDP
         starting remote port. The value of this object is used as per the
         description for tmnxMobPdnBcSdfFirstDstPortOper."
    ::= { tmnxMobPdnBcSdfFilterEntry 20 }

tmnxMobPdnBcSdfSecndDstPortOper  OBJECT-TYPE
    SYNTAX      TTcpUdpPortOperator
    MAX-ACCESS  read-only
    STATUS      current
    DESCRIPTION
        "The value of tmnxMobPdnBcSdfSecndDstPortOper indicates the manner in
         which tmnxMobPdnBcSdfSecndDstPortVal1 and
         tmnxMobPdnBcSdfSecndDstPortVal2 are to be used. The values of these
         three objects are used as described in TTcpUdpPortOperator."
    ::= { tmnxMobPdnBcSdfFilterEntry 21 }

tmnxMobPdnBcSdfSecndDstPortVal1  OBJECT-TYPE
    SYNTAX      TTcpUdpPort
    MAX-ACCESS  read-only
    STATUS      current
    DESCRIPTION
        "The value of tmnxMobPdnBcSdfSecndDstPortVal1 indicates the TCP or UDP
         starting remote port. The value of this object is used as per the
         description for tmnxMobPdnBcSdfSecndDstPortOper."
    ::= { tmnxMobPdnBcSdfFilterEntry 22 }

tmnxMobPdnBcSdfSecndDstPortVal2  OBJECT-TYPE
    SYNTAX      TTcpUdpPort
    MAX-ACCESS  read-only
    STATUS      current
    DESCRIPTION
        "The value of tmnxMobPdnBcSdfSecndDstPortVal2 indicates the TCP or UDP
         starting remote port. The value of this object is used as per the
         description for tmnxMobPdnBcSdfSecndDstPortOper."
    ::= { tmnxMobPdnBcSdfFilterEntry 23 }

--
--  Statistics Table
--

tmnxMobPdnStatTable  OBJECT-TYPE
    SYNTAX      SEQUENCE OF TmnxMobPdnStatEntry
    MAX-ACCESS  not-accessible
    STATUS      current
    DESCRIPTION
        "The tmnxMobPdnStatTable has an entry for each each Mobility Service
         Module (MSM) configured in the mobility system group defined
         for a Packet Data Network Gateway (PGW)."
    ::= { tmnxMobPdnStatObjs 6 }

tmnxMobPdnStatEntry  OBJECT-TYPE
    SYNTAX      TmnxMobPdnStatEntry
    MAX-ACCESS  not-accessible
    STATUS      current
    DESCRIPTION
        "Each row entry represents a Mobility Service Module (MSM) and contains
         statictics for this card.

         When the value of tmnxCardSlotNum is equal to '0', then each row entry
         contains aggregated statistics for a given gateway."
    INDEX { tmnxMobGwId,
            tmnxChassisIndex,
            tmnxMobPdnCardSlotNum
          }
    ::= { tmnxMobPdnStatTable 1 }

TmnxMobPdnStatEntry ::= SEQUENCE {
        tmnxMobPdnCardSlotNum              TmnxSlotNumOrZero,
        tmnxMobPdnStatRealApn              Gauge32,
        tmnxMobPdnStatVirtualApn           Gauge32,
        tmnxMobPdnStatBearers              Gauge32,
        tmnxMobPdnStatDefaultBearers       Gauge32,
        tmnxMobPdnStatDedicatedBearers     Gauge32,
        tmnxMobPdnStatIpv4Bearers          Gauge32,
        tmnxMobPdnStatIpv6Bearers          Gauge32,
        tmnxMobPdnStatIpv4v6Bearers        Gauge32,
        tmnxMobPdnStatRoamers              Gauge32,
        tmnxMobPdnStatIpv4Sdf              Gauge32,
        tmnxMobPdnStatIpv6Sdf              Gauge32,
        tmnxMobPdnStatVPRNs                Gauge32,
        tmnxMobPdnStatPdnSessions          Gauge32,
        tmnxMobPdnStatIpv4PdnSessions      Gauge32,
        tmnxMobPdnStatIpv6PdnSessions      Gauge32,
        tmnxMobPdnStatIpv4v6PdnSessions    Gauge32,
        tmnxMobPdnStatIpLocalPools         Gauge32,
        tmnxMobPdnStatGnSgsns              Gauge32,
        tmnxMobPdnStatHomers               Gauge32,
        tmnxMobPdnStatVisitors             Gauge32,
        tmnxMobPdnStatHSSStaticIpv4Sess    Gauge32,
        tmnxMobPdnStatHSSStaticIpv6Sess    Gauge32,
        tmnxMobPdnStatHSSSttIpv4v6Sess     Gauge32,
        tmnxMobPdnStateHRPDPDNSess         Gauge32,
        tmnxMobPdnStatLTEPDNSess           Gauge32,
        tmnxMobPdnStat2G3GPDNSess          Gauge32,
        tmnxMobPdnStatNumSuspendedPDN      Gauge32,
        tmnxMobPdnStatEmergencyPdnSess     Gauge32,
        tmnxMobPdnStatRfPeer               Gauge32,
        tmnxMobPdnStatRfAcctStartBuf       Gauge32,
        tmnxMobPdnStatRfAcctIntBuf         Gauge32,
        tmnxMobPdnStatRfAcctStopBuf        Gauge32
    }

tmnxMobPdnCardSlotNum    OBJECT-TYPE
    SYNTAX      TmnxSlotNumOrZero
    MAX-ACCESS  not-accessible
    STATUS      current
    DESCRIPTION
        "The value of tmnxMobPdnCardSlotNum indicates the slot number of this 
         card."
    ::= { tmnxMobPdnStatEntry 1 }

tmnxMobPdnStatRealApn  OBJECT-TYPE
    SYNTAX      Gauge32
    MAX-ACCESS  read-only
    STATUS      current
    DESCRIPTION
        "The value of tmnxMobPdnStatRealApn indicates the number of real
         Access Point Names (APNs) being served by this card."
    ::= { tmnxMobPdnStatEntry 2 }

tmnxMobPdnStatVirtualApn  OBJECT-TYPE
    SYNTAX      Gauge32
    MAX-ACCESS  read-only
    STATUS      current
    DESCRIPTION
        "The value of tmnxMobPdnStatVirtualApn indicates the number of virtual
         Access Point Names (APNs) being served by this card."
    ::= { tmnxMobPdnStatEntry 3 }

tmnxMobPdnStatBearers  OBJECT-TYPE
    SYNTAX      Gauge32
    MAX-ACCESS  read-only
    STATUS      current
    DESCRIPTION
        "The value of tmnxMobPdnStatBearers indicates the number of bearers
         being served by this card."
    ::= { tmnxMobPdnStatEntry 4 }

tmnxMobPdnStatDefaultBearers  OBJECT-TYPE
    SYNTAX      Gauge32
    MAX-ACCESS  read-only
    STATUS      current
    DESCRIPTION
        "The value of tmnxMobPdnStatDefaultBearers indicates the number of
         default bearers being served by this card."
    ::= { tmnxMobPdnStatEntry 5 }

tmnxMobPdnStatDedicatedBearers  OBJECT-TYPE
    SYNTAX      Gauge32
    MAX-ACCESS  read-only
    STATUS      current
    DESCRIPTION
        "The value of tmnxMobPdnStatDedicatedBearers indicates the number of
         dedicated bearers being served by this card."
    ::= { tmnxMobPdnStatEntry 6 }

tmnxMobPdnStatIpv4Bearers  OBJECT-TYPE
    SYNTAX      Gauge32
    MAX-ACCESS  read-only
    STATUS      current
    DESCRIPTION
        "The value of tmnxMobPdnStatIpv4Bearers indicates the number of
         IPv4 bearers being served by this card."
    ::= { tmnxMobPdnStatEntry 7 }

tmnxMobPdnStatIpv6Bearers  OBJECT-TYPE
    SYNTAX      Gauge32
    MAX-ACCESS  read-only
    STATUS      current
    DESCRIPTION
        "The value of tmnxMobPdnStatIpv6Bearers indicates the number of
         IPv6 bearers being served by this card."
    ::= { tmnxMobPdnStatEntry 8 }

tmnxMobPdnStatIpv4v6Bearers  OBJECT-TYPE
    SYNTAX      Gauge32
    MAX-ACCESS  read-only
    STATUS      current
    DESCRIPTION
        "The value of tmnxMobPdnStatIpv4v6Bearers indicates the number of
         IPv4v6 bearers being served by this card."
    ::= { tmnxMobPdnStatEntry 9 }

tmnxMobPdnStatRoamers  OBJECT-TYPE
    SYNTAX      Gauge32
    MAX-ACCESS  read-only
    STATUS      current
    DESCRIPTION
        "The value of tmnxMobPdnStatRoamers indicates the number of roamers
         being served by this card."
    ::= { tmnxMobPdnStatEntry 10 }

tmnxMobPdnStatIpv4Sdf  OBJECT-TYPE
    SYNTAX      Gauge32
    MAX-ACCESS  read-only
    STATUS      current
    DESCRIPTION
        "The value of tmnxMobPdnStatIpv4Sdf indicates the number of IPv4
         Service Data Flows (SDFs) on this card."
    ::= { tmnxMobPdnStatEntry 11 }

tmnxMobPdnStatIpv6Sdf  OBJECT-TYPE
    SYNTAX      Gauge32
    MAX-ACCESS  read-only
    STATUS      current
    DESCRIPTION
        "The value of tmnxMobPdnStatIpv6Sdf indicates the number of IPv6
         Service Data Flows (SDFs) on this card."
    ::= { tmnxMobPdnStatEntry 12 }

tmnxMobPdnStatVPRNs  OBJECT-TYPE
    SYNTAX      Gauge32
    MAX-ACCESS  read-only
    STATUS      current
    DESCRIPTION
        "The value of tmnxMobPdnStatVPRNs indicates the number of VPRNs
         being served by this card."
    ::= { tmnxMobPdnStatEntry 13 }

tmnxMobPdnStatPdnSessions  OBJECT-TYPE
    SYNTAX      Gauge32
    MAX-ACCESS  read-only
    STATUS      current
    DESCRIPTION
        "The value of tmnxMobPdnStatPdnSessions indicates the number of PDN
         sessions being served by this card."
    ::= { tmnxMobPdnStatEntry 14 }

tmnxMobPdnStatIpv4PdnSessions  OBJECT-TYPE
    SYNTAX      Gauge32
    MAX-ACCESS  read-only
    STATUS      current
    DESCRIPTION
        "The value of tmnxMobPdnStatIpv4PdnSessions indicates the number of
         IPv4 PDN Sessions being served by this card."
    ::= { tmnxMobPdnStatEntry 15 }

tmnxMobPdnStatIpv6PdnSessions  OBJECT-TYPE
    SYNTAX      Gauge32
    MAX-ACCESS  read-only
    STATUS      current
    DESCRIPTION
        "The value of tmnxMobPdnStatIpv6PdnSessions indicates the number of
         IPv6 PDN Sessions being served by this card."
    ::= { tmnxMobPdnStatEntry 16 }

tmnxMobPdnStatIpv4v6PdnSessions  OBJECT-TYPE
    SYNTAX      Gauge32
    MAX-ACCESS  read-only
    STATUS      current
    DESCRIPTION
        "The value of tmnxMobPdnStatIpv4v6PdnSessions indicates the number of
         IPv4v6 PDN Sessions being served by this card."
    ::= { tmnxMobPdnStatEntry 17 }

tmnxMobPdnStatIpLocalPools  OBJECT-TYPE
    SYNTAX      Gauge32
    MAX-ACCESS  read-only
    STATUS      current
    DESCRIPTION
        "The value of tmnxMobPdnStatIpLocalPools indicates the number of IP
         local pools being served by this card."
    ::= { tmnxMobPdnStatEntry 18 }

tmnxMobPdnStatGnSgsns  OBJECT-TYPE
    SYNTAX      Gauge32
    MAX-ACCESS  read-only
    STATUS      current
    DESCRIPTION
        "The value of tmnxMobPdnStatGnSgsns indicates the number of SGSNs on the 
         Gn interface being served by this card."
    ::= { tmnxMobPdnStatEntry 19 }

tmnxMobPdnStatHomers  OBJECT-TYPE
    SYNTAX      Gauge32
    MAX-ACCESS  read-only
    STATUS      current
    DESCRIPTION
        "The value of tmnxMobPdnStatHomers indicates the number of homers
         being served by this card." 
    ::= { tmnxMobPdnStatEntry 20 }

tmnxMobPdnStatVisitors  OBJECT-TYPE
    SYNTAX      Gauge32
    MAX-ACCESS  read-only
    STATUS      current
    DESCRIPTION
        "The value of tmnxMobPdnStatVisitors indicates the number of visitors
         being served by this card." 
    ::= { tmnxMobPdnStatEntry 21 }    

tmnxMobPdnStatHSSStaticIpv4Sess OBJECT-TYPE
    SYNTAX      Gauge32
    MAX-ACCESS  read-only
    STATUS      current
    DESCRIPTION 
        "The value of tmnxMobPdnStatHSSStaticIpv4Sess indicates the number of
         static IPv4 Packet Data Network (PDN) sessions."
    ::= { tmnxMobPdnStatEntry 22 }

tmnxMobPdnStatHSSStaticIpv6Sess OBJECT-TYPE
    SYNTAX      Gauge32
    MAX-ACCESS  read-only
    STATUS      current
    DESCRIPTION 
        "The value of tmnxMobPdnStatHSSStaticIpv6Sess indicates the number of
         static IPv6 Packet Data Network (PDN) sessions."
    ::= { tmnxMobPdnStatEntry 23 }

tmnxMobPdnStatHSSSttIpv4v6Sess OBJECT-TYPE
    SYNTAX      Gauge32
    MAX-ACCESS  read-only
    STATUS      current
    DESCRIPTION 
        "The value of tmnxMobPdnStatHSSSttIpv4v6Sess indicates the number of
         static IPv4v6 Packet Data Network (PDN) sessions."
    ::= { tmnxMobPdnStatEntry 24 }

tmnxMobPdnStateHRPDPDNSess OBJECT-TYPE
    SYNTAX      Gauge32
    MAX-ACCESS  read-only
    STATUS      current
    DESCRIPTION 
        "The value of tmnxMobPdnStateHRPDPDNSess indicates the number of enhanced
         High Rate Packet Data (eHRPD) Packet Data Network (PDN) sessions."
    ::= { tmnxMobPdnStatEntry 25 }

tmnxMobPdnStatLTEPDNSess OBJECT-TYPE
    SYNTAX      Gauge32
    MAX-ACCESS  read-only
    STATUS      current
    DESCRIPTION 
        "The value of tmnxMobPdnStatLTEPDNSess indicates the number of 
         Long Term Evolution (LTE) Packet Data Network (PDN) sessions."
    ::= { tmnxMobPdnStatEntry 26 }

tmnxMobPdnStat2G3GPDNSess OBJECT-TYPE
    SYNTAX      Gauge32
    MAX-ACCESS  read-only
    STATUS      current
    DESCRIPTION 
        "The value of tmnxMobPdnStat2G3GPDNSess indicates the number of 2G/3G 
         Packet Data Network (PDN) sessions."
    ::= { tmnxMobPdnStatEntry 27 }

tmnxMobPdnStatNumSuspendedPDN OBJECT-TYPE
    SYNTAX      Gauge32
    MAX-ACCESS  read-only
    STATUS      current
    DESCRIPTION 
        "The value of tmnxMobPdnStatNumSuspendedPDN indicates the number of 
         Packet Data Network (PDN) sessions in suspended state."
    ::= { tmnxMobPdnStatEntry 28 }

tmnxMobPdnStatEmergencyPdnSess  OBJECT-TYPE
    SYNTAX      Gauge32
    MAX-ACCESS  read-only
    STATUS      current
    DESCRIPTION
        "The value of tmnxMobPdnStatEmergencyPdnSess indicates the number of
         Emergency PDN sessions on this card."
    ::= { tmnxMobPdnStatEntry 29 }

tmnxMobPdnStatRfPeer  OBJECT-TYPE
    SYNTAX      Gauge32
    MAX-ACCESS  read-only
    STATUS      current
    DESCRIPTION
        "The value of tmnxMobPdnStatRfPeer indicates the number of
         peers on the Rf reference point being served by this card."
    ::= { tmnxMobPdnStatEntry 30 }

tmnxMobPdnStatRfAcctStartBuf  OBJECT-TYPE
    SYNTAX      Gauge32
    MAX-ACCESS  read-only
    STATUS      current
    DESCRIPTION
        "The value of tmnxMobPdnStatRfAcctStartBuf indicates the number of
         Accounting Request (ACR) Start messages buffered by this card."
    ::= { tmnxMobPdnStatEntry 31 }

tmnxMobPdnStatRfAcctIntBuf  OBJECT-TYPE
    SYNTAX      Gauge32
    MAX-ACCESS  read-only
    STATUS      current
    DESCRIPTION
        "The value of tmnxMobPdnStatRfAcctIntBuf indicates the number of
         Accounting Request (ACR) Interim messages buffered by this card."
    ::= { tmnxMobPdnStatEntry 32 }

tmnxMobPdnStatRfAcctStopBuf  OBJECT-TYPE
    SYNTAX      Gauge32
    MAX-ACCESS  read-only
    STATUS      current
    DESCRIPTION
        "The value of tmnxMobPdnStatRfAcctStopBuf indicates the number of
         Accounting Request (ACR) Stop messages buffered by this card."
    ::= { tmnxMobPdnStatEntry 33 }

--
--  Call flows Table
--

tmnxMobPdnProcTable  OBJECT-TYPE
    SYNTAX      SEQUENCE OF TmnxMobPdnProcEntry
    MAX-ACCESS  not-accessible
    STATUS      current
    DESCRIPTION
        "The tmnxMobPdnProcTable has an entry for each each Mobility Service
         Module (MSM) configured in the mobility system group defined
         for a PDN Gateway (PGW)."
    ::= { tmnxMobPdnStatObjs 7 }

tmnxMobPdnProcEntry  OBJECT-TYPE
    SYNTAX      TmnxMobPdnProcEntry
    MAX-ACCESS  not-accessible
    STATUS      current
    DESCRIPTION
        "Each row entry represents a Mobility Service Module (MSM) and contains
         statictics for call flow procedures on this card."
    AUGMENTS { tmnxMobPdnStatEntry }
    ::= { tmnxMobPdnProcTable 1 }

TmnxMobPdnProcEntry ::= SEQUENCE {
        tmnxMobPdnProcAttach                Counter32,
        tmnxMobPdnProcAttachFail            Counter32,
        tmnxMobPdnProcDetach               Counter32,
        tmnxMobPdnProcDetachFail           Counter32,
        tmnxMobPdnProcNwDedBrActv          Counter32,
        tmnxMobPdnProcNwDedBrActvFail      Counter32,
        tmnxMobPdnProcNwDedBrDeActv        Counter32,
        tmnxMobPdnProcNwDedBrDeActvFail    Counter32,
        tmnxMobPdnProcNwDedBrModify        Counter32,
        tmnxMobPdnProcNwDedBrModifyFail    Counter32,
        tmnxMobPdnProcUeDedBrActv          Counter32,
        tmnxMobPdnProcUeDedBrActvFail      Counter32,
        tmnxMobPdnProcUeDedBrDeActv        Counter32,
        tmnxMobPdnProcUeDedBrDeActvFail    Counter32,
        tmnxMobPdnProcUeDedBrModify        Counter32,
        tmnxMobPdnProcUeDedBrModifyFail    Counter32,
        tmnxMobPdnProcHssQosModify         Counter32,
        tmnxMobPdnProcHssQosModifyFail     Counter32,
        tmnxMobPdnProcPcrfQosModify        Counter32,
        tmnxMobPdnProcPcrfQosModifyFail    Counter32,
        tmnxMobPdnProcSgwReloc             Counter32,
        tmnxMobPdnProcSgwRelocFail         Counter32,
        tmnxMobPdnProcPgwPdnSessDel        Counter32,
        tmnxMobPdnProcPgwPdnSessDelFail    Counter32,
        tmnxMobPdnProcAttachPiggyBack      Counter32,
        tmnxMobPdneHRPDAttachSuccess       Counter32,
        tmnxMobPdneHRPDAttachFailure       Counter32, 
        tmnxMobPdneHRPDDetachSuccess       Counter32, 
        tmnxMobPdneHRPDDetachFailure       Counter32,
        tmnxMobPdneHRPDToLTEHandOverSucc   Counter32, 
        tmnxMobPdneHRPDToLTEHandOverFail   Counter32,
        tmnxMobPdnLTEToeHRPDHandOverSucc   Counter32,
        tmnxMobPdnLTEToeHRPDHandOverFail   Counter32, 
        tmnxMobPdnInterHSGWHandOvrSucc     Counter32, 
        tmnxMobPdnInterHSGWHandOvrFail     Counter32,
        tmnxMobPdnProcPDNSuspendNotice     Counter32,
        tmnxMobPdnProcPDNResumeNotice      Counter32,
        tmnxMobPdnProcPDNIRSRP             Counter32,
        tmnxMobPdnProcEmergncyAttachSuc    Counter32,
        tmnxMobPdnProcMmeDedBrDeActiv      Counter32,
        tmnxMobPdnProcMmeDedBrDeAcFails    Counter32,
        tmnxMobPdnProcSessDeactDueToSt     Counter32,
        tmnxMobPdnProcSessDeactDueToIt     Counter32,
        tmnxMobPdnInterRat3gToEutranSucc   Counter32,
        tmnxMobPdnInterRat3gToEutranFail   Counter32,
        tmnxMobPdnInterRatEutranTo3gSucc   Counter32,
        tmnxMobPdnInterRatEutranTo3gFail   Counter32,
        tmnxMobPdneHRPDSessDeactSessTO     Counter32,
        tmnxMobPdneHRPDSessDeactIdleTO     Counter32
    }

tmnxMobPdnProcAttach  OBJECT-TYPE
    SYNTAX      Counter32
    MAX-ACCESS  read-only
    STATUS      current
    DESCRIPTION
        "The value of tmnxMobPdnProcAttach indicates the number of 
         successful default attach-procedures executed on this card."
    ::= { tmnxMobPdnProcEntry 1 }

tmnxMobPdnProcAttachFail    OBJECT-TYPE
    SYNTAX      Counter32
    MAX-ACCESS  read-only
    STATUS      current
    DESCRIPTION
        "The value of tmnxMobPdnProcAttachFail indicates the number of 
         failed default attach-procedures executed on this card."
    ::= { tmnxMobPdnProcEntry 2 }

tmnxMobPdnProcDetach  OBJECT-TYPE
    SYNTAX      Counter32
    MAX-ACCESS  read-only
    STATUS      current
    DESCRIPTION
        "The value of tmnxMobPdnProcDetach indicates the number of
         detach-procedures executed succesfully on this card."
    ::= { tmnxMobPdnProcEntry 3 }

tmnxMobPdnProcDetachFail  OBJECT-TYPE
    SYNTAX      Counter32
    MAX-ACCESS  read-only
    STATUS      current
    DESCRIPTION
        "The value of tmnxMobPdnProcDetachFail indicates the number of 
         detach-procedure failures."
    ::= { tmnxMobPdnProcEntry 4 }

tmnxMobPdnProcNwDedBrActv  OBJECT-TYPE
    SYNTAX      Counter32
    MAX-ACCESS  read-only
    STATUS      current
    DESCRIPTION
        "The value of tmnxMobPdnProcNwDedBrActv indicates the number of
         network initiated dedicated bearer activation procedures served
         by this card."
    ::= { tmnxMobPdnProcEntry 5 }

tmnxMobPdnProcNwDedBrActvFail  OBJECT-TYPE
    SYNTAX      Counter32
    MAX-ACCESS  read-only
    STATUS      current
    DESCRIPTION
        "The value of tmnxMobPdnProcNwDedBrActvFail indicates the number of
         network initiated dedicated bearer activation procedure failures."
    ::= { tmnxMobPdnProcEntry 6 }

tmnxMobPdnProcNwDedBrDeActv  OBJECT-TYPE
    SYNTAX      Counter32
    MAX-ACCESS  read-only
    STATUS      current
    DESCRIPTION
        "The value of tmnxMobPdnProcNwDedBrDeActv indicates the number of
         network initiated dedicated bearer activation procedures served
         by this card."
    ::= { tmnxMobPdnProcEntry 7 }

tmnxMobPdnProcNwDedBrDeActvFail  OBJECT-TYPE
    SYNTAX      Counter32
    MAX-ACCESS  read-only
    STATUS      current
    DESCRIPTION
        "The value of tmnxMobPdnProcNwDedBrDeActvFail indicates the number of
         network initiated dedicated bearer activation procedure failures."
    ::= { tmnxMobPdnProcEntry 8 }

tmnxMobPdnProcNwDedBrModify  OBJECT-TYPE
    SYNTAX      Counter32
    MAX-ACCESS  read-only
    STATUS      current
    DESCRIPTION
        "The value of tmnxMobPdnProcNwDedBrModify indicates the number of
         network initiated dedicated bearer activation procedures served
         by this card."
    ::= { tmnxMobPdnProcEntry 9 }

tmnxMobPdnProcNwDedBrModifyFail  OBJECT-TYPE
    SYNTAX      Counter32
    MAX-ACCESS  read-only
    STATUS      current
    DESCRIPTION
        "The value of tmnxMobPdnProcNwDedBrModifyFail indicates the number of
         network initiated dedicated bearer activation procedure failures."
    ::= { tmnxMobPdnProcEntry 10 }

tmnxMobPdnProcUeDedBrActv  OBJECT-TYPE
    SYNTAX      Counter32
    MAX-ACCESS  read-only
    STATUS      current
    DESCRIPTION
        "The value of tmnxMobPdnProcUeDedBrActv indicates the number of
         User-Equipment (UE) initiated dedicated bearer activation procedures 
         served by this card."
    ::= { tmnxMobPdnProcEntry 11 }

tmnxMobPdnProcUeDedBrActvFail  OBJECT-TYPE
    SYNTAX      Counter32
    MAX-ACCESS  read-only
    STATUS      current
    DESCRIPTION
        "The value of tmnxMobPdnProcUeDedBrActvFail indicates the number of
         User-Equipment (UE) initiated dedicated bearer activation procedure
         failures."
    ::= { tmnxMobPdnProcEntry 12 }

tmnxMobPdnProcUeDedBrDeActv  OBJECT-TYPE
    SYNTAX      Counter32
    MAX-ACCESS  read-only
    STATUS      current
    DESCRIPTION
        "The value of tmnxMobPdnProcUeDedBrDeActv indicates the number of
         User-Equipment (UE) initiated dedicated bearer activation procedures
         served by this card."
    ::= { tmnxMobPdnProcEntry 13 }

tmnxMobPdnProcUeDedBrDeActvFail  OBJECT-TYPE
    SYNTAX      Counter32
    MAX-ACCESS  read-only
    STATUS      current
    DESCRIPTION
        "The value of tmnxMobPdnProcUeDedBrDeActvFail indicates the number of
         User-Equipment (UE) initiated dedicated bearer activation procedure
         failures."
    ::= { tmnxMobPdnProcEntry 14 }

tmnxMobPdnProcUeDedBrModify  OBJECT-TYPE
    SYNTAX      Counter32
    MAX-ACCESS  read-only
    STATUS      current
    DESCRIPTION
        "The value of tmnxMobPdnProcUeDedBrModify indicates the number of
         User-Equipment (UE) initiated dedicated bearer activation procedures
         served by this card."
    ::= { tmnxMobPdnProcEntry 15 }

tmnxMobPdnProcUeDedBrModifyFail  OBJECT-TYPE
    SYNTAX      Counter32
    MAX-ACCESS  read-only
    STATUS      current
    DESCRIPTION
        "The value of tmnxMobPdnProcUeDedBrModifyFail indicates the number of
         User-Equipment (UE) initiated dedicated bearer activation procedure
         failures."
    ::= { tmnxMobPdnProcEntry 16 }

tmnxMobPdnProcHssQosModify  OBJECT-TYPE
    SYNTAX      Counter32
    MAX-ACCESS  read-only
    STATUS      current
    DESCRIPTION
        "The value of tmnxMobPdnProcHssQosModify indicates the number of
         HSS initiated QoS modification procedures served by this card."
    ::= { tmnxMobPdnProcEntry 17 }

tmnxMobPdnProcHssQosModifyFail  OBJECT-TYPE
    SYNTAX      Counter32
    MAX-ACCESS  read-only
    STATUS      current
    DESCRIPTION
        "The value of tmnxMobPdnProcHssQosModifyFail indicates the number of
         HSS initiated QoS modification procedure failures."
    ::= { tmnxMobPdnProcEntry 18 }

tmnxMobPdnProcPcrfQosModify  OBJECT-TYPE
    SYNTAX      Counter32
    MAX-ACCESS  read-only
    STATUS      current
    DESCRIPTION
        "The value of tmnxMobPdnProcPcrfQosModify indicates the number of
         Policy and Charging Rules Function (PCRF) initiated QoS modification
         procedures served by this card."
    ::= { tmnxMobPdnProcEntry 19 }

tmnxMobPdnProcPcrfQosModifyFail  OBJECT-TYPE
    SYNTAX      Counter32
    MAX-ACCESS  read-only
    STATUS      current
    DESCRIPTION
        "The value of tmnxMobPdnProcPcrfQosModifyFail indicates the number of
         Policy and Charging Rules Function (PCRF) initiated QoS modification
         procedure failures."
    ::= { tmnxMobPdnProcEntry 20 }

tmnxMobPdnProcSgwReloc  OBJECT-TYPE
    SYNTAX      Counter32
    MAX-ACCESS  read-only
    STATUS      current
    DESCRIPTION
        "The value of tmnxMobPdnProcSgwReloc indicates the number of
         successful Serving Gateway (SGW) relocations."
    ::= { tmnxMobPdnProcEntry 21 }

tmnxMobPdnProcSgwRelocFail  OBJECT-TYPE
    SYNTAX      Counter32
    MAX-ACCESS  read-only
    STATUS      current
    DESCRIPTION
        "The value of tmnxMobPdnProcSgwRelocFail indicates the number of
         failed Serving Gateway (SGW) relocations."
    ::= { tmnxMobPdnProcEntry 22 }

tmnxMobPdnProcPgwPdnSessDel  OBJECT-TYPE
    SYNTAX      Counter32
    MAX-ACCESS  read-only
    STATUS      current
    DESCRIPTION
        "The value of tmnxMobPdnProcPgwPdnSessDel indicates the number of
         successful PDN session-deletion initiated by PDN Gateway (PGW)."
    ::= { tmnxMobPdnProcEntry 23 }

tmnxMobPdnProcPgwPdnSessDelFail  OBJECT-TYPE
    SYNTAX      Counter32
    MAX-ACCESS  read-only
    STATUS      current
    DESCRIPTION
        "The value of tmnxMobPdnProcPgwPdnSessDelFail indicates the number of
         failed PDN session-deletion initiated by PDN Gateway (PGW)."
    ::= { tmnxMobPdnProcEntry 24 }

tmnxMobPdnProcAttachPiggyBack  OBJECT-TYPE
    SYNTAX      Counter32
    MAX-ACCESS  read-only
    STATUS      current
    DESCRIPTION
        "The value of tmnxMobPdnProcAttachPiggyBack indicates the number
         of successful default attach-procedures executed on this card 
         with piggybacking."
    ::= { tmnxMobPdnProcEntry 25 }

tmnxMobPdneHRPDAttachSuccess OBJECT-TYPE
    SYNTAX     Counter32
    MAX-ACCESS read-only
    STATUS     current
    DESCRIPTION
        "The value of tmnxMobPdneHRPDAttachSuccess indicates the number of
         successful enhanced High Rate Packet Data (eHRPD) attaches."
        ::= { tmnxMobPdnProcEntry 26 }

tmnxMobPdneHRPDAttachFailure OBJECT-TYPE
    SYNTAX     Counter32
    MAX-ACCESS read-only
    STATUS     current
    DESCRIPTION
        "The value of tmnxMobPdneHRPDAttachFailure indicates the number of
         failed enhanced High Rate Packet Data (eHRPD) attaches."
        ::= { tmnxMobPdnProcEntry 27 }

tmnxMobPdneHRPDDetachSuccess OBJECT-TYPE
    SYNTAX     Counter32
    MAX-ACCESS read-only
    STATUS     current
    DESCRIPTION
        "The value of tmnxMobPdneHRPDDetachSuccess indicates the number of
         successful enhanced High Rate Packet Data (eHRPD) detaches."
        ::= { tmnxMobPdnProcEntry 28 }

tmnxMobPdneHRPDDetachFailure OBJECT-TYPE
    SYNTAX     Counter32
    MAX-ACCESS read-only
    STATUS     current
    DESCRIPTION
        "The value of tmnxMobPdneHRPDDetachFailure indicates the number of
         failed enhanced High Rate Packet Data (eHRPD) detaches."
        ::= { tmnxMobPdnProcEntry 29 }

tmnxMobPdneHRPDToLTEHandOverSucc OBJECT-TYPE
    SYNTAX     Counter32
    MAX-ACCESS read-only
    STATUS     current
    DESCRIPTION
        "The value of tmnxMobPdneHRPDToLTEHandOverSucc indicates the number of
         successful enhanced High Rate Packet Data (eHRPD) network to Long Term Evolution
         (LTE) network hand over."
        ::= { tmnxMobPdnProcEntry 30 }

tmnxMobPdneHRPDToLTEHandOverFail OBJECT-TYPE
    SYNTAX     Counter32
    MAX-ACCESS read-only
    STATUS     current
    DESCRIPTION
        "The value of tmnxMobPdneHRPDToLTEHandOverFail indicates the number of
         failed enhanced High Rate Packet Data (eHRPD) network to Long Term Evolution 
         (LTE) network hand over."
        ::= { tmnxMobPdnProcEntry 31 }

tmnxMobPdnLTEToeHRPDHandOverSucc OBJECT-TYPE
    SYNTAX     Counter32
    MAX-ACCESS read-only
    STATUS     current
    DESCRIPTION
        "The value of tmnxMobPdnLTEToeHRPDHandOverSucc indicates the number of
         successful Long Term Evolution (LTE) network to enhanced High Rate Packet Data
         (eHRPD) network hand over."
        ::= { tmnxMobPdnProcEntry 32 }

tmnxMobPdnLTEToeHRPDHandOverFail OBJECT-TYPE
    SYNTAX     Counter32
    MAX-ACCESS read-only
    STATUS     current
    DESCRIPTION
        "The value of tmnxMobPdnLTEToeHRPDHandOverFail indicates the number of
         failed Long Term Evolution (LTE) network to enhanced High Rate Packet 
         Data (eHRPD) network hand over."
        ::= { tmnxMobPdnProcEntry 33 }

tmnxMobPdnInterHSGWHandOvrSucc OBJECT-TYPE
    SYNTAX        Counter32
    MAX-ACCESS read-only
    STATUS     current
    DESCRIPTION
        "The value of tmnxMobPdnInterHSGWHandOvrSucc indicates the number of
         successful inter High Rate Packet Data (HRPD) Serving Gateway (HSGW) 
         hand over."
        ::= { tmnxMobPdnProcEntry 34 }

tmnxMobPdnInterHSGWHandOvrFail OBJECT-TYPE
    SYNTAX     Counter32
    MAX-ACCESS read-only
    STATUS     current
    DESCRIPTION
        "The value of tmnxMobPdnInterHSGWHandOvrFail indicates the number of
         failed inter High Rate Packet Data (HRPD) Serving Gateway (HSGW) hand over."
        ::= { tmnxMobPdnProcEntry 35 }

tmnxMobPdnProcPDNSuspendNotice  OBJECT-TYPE
    SYNTAX      Counter32
    MAX-ACCESS  read-only
    STATUS      current
    DESCRIPTION
        "The value of tmnxMobPdnProcPDNSuspendNotice indicates the number of
         Packet Data Network (PDN) suspend notifications received at the 
         Packet Data Network (PDN) Gateway (PGW)."
    ::= { tmnxMobPdnProcEntry 36 }
    
tmnxMobPdnProcPDNResumeNotice  OBJECT-TYPE
    SYNTAX      Counter32
    MAX-ACCESS  read-only
    STATUS      current
    DESCRIPTION
        "The value of tmnxMobPdnProcPDNResumeNotice indicates the number of
         Packet Data Network (PDN) resume notifications received at the 
         Packet Data Network (PDN) Gateway (PGW)."
    ::= { tmnxMobPdnProcEntry 37 }

tmnxMobPdnProcPDNIRSRP  OBJECT-TYPE
    SYNTAX      Counter32
    MAX-ACCESS  read-only
    STATUS      current
    DESCRIPTION
        "The value of tmnxMobPdnProcPDNIRSRP indicates the number of
         Implicit Resume Service Requests (IRSR) received at the 
         Packet Data Network (PDN) Gateway (PGW)."
    ::= { tmnxMobPdnProcEntry 38 }

tmnxMobPdnProcEmergncyAttachSuc  OBJECT-TYPE
    SYNTAX      Counter32
    MAX-ACCESS  read-only
    STATUS      current
    DESCRIPTION
        "The value of tmnxMobPdnProcEmergncyAttachSuc indicates the number of
         successful Emergency Attach messages served at the Packet Data
         Network (PDN) Gateway (PGW)."
    ::= { tmnxMobPdnProcEntry 39 }

tmnxMobPdnProcMmeDedBrDeActiv  OBJECT-TYPE
    SYNTAX      Counter32
    MAX-ACCESS  read-only
    STATUS      current
    DESCRIPTION
        "The value of tmnxMobPdnProcMmeDedBrDeActiv indicates the number of
         successful Mobility Management Entitiy (MME) initiated dedicated bearer
         de-activation procedures served by this card."
    ::= { tmnxMobPdnProcEntry 40 }

tmnxMobPdnProcMmeDedBrDeAcFails  OBJECT-TYPE
    SYNTAX      Counter32
    MAX-ACCESS  read-only
    STATUS      current
    DESCRIPTION
        "The value of tmnxMobPdnProcMmeDedBrDeAcFails indicates the number of
         Mobility Management Entitiy (MME) initiated dedicated bearer
         de-activation procedure failures."
    ::= { tmnxMobPdnProcEntry 41 }

tmnxMobPdnProcSessDeactDueToSt  OBJECT-TYPE
    SYNTAX      Counter32
    MAX-ACCESS  read-only
    STATUS      current
    DESCRIPTION
        "The value of tmnxMobPdnProcSessDeactDueToSt indicates the number of
         PDN sessions deactivated due to the session time-out."
    ::= { tmnxMobPdnProcEntry 42 }

tmnxMobPdnProcSessDeactDueToIt  OBJECT-TYPE
    SYNTAX      Counter32
    MAX-ACCESS  read-only
    STATUS      current
    DESCRIPTION
        "The value of tmnxMobPdnProcSessDeactDueToIt indicates the number of
         PDN sessions deactivated due to the idle timeout."
    ::= { tmnxMobPdnProcEntry 43 }

tmnxMobPdnInterRat3gToEutranSucc OBJECT-TYPE
    SYNTAX     Counter32
    MAX-ACCESS read-only
    STATUS     current
    DESCRIPTION
        "The value of tmnxMobPdnInterRat3gToEutranSucc indicates the number of
         successful inter Radio Access Type (RAT) handovers from 3G to
         evolved UMTS Terrestrial Radio Access Network (e-UTRAN)."
        ::= { tmnxMobPdnProcEntry 44 }

tmnxMobPdnInterRat3gToEutranFail OBJECT-TYPE
    SYNTAX     Counter32
    MAX-ACCESS read-only
    STATUS     current
    DESCRIPTION
        "The value of tmnxMobPdnInterRat3gToEutranFail indicates the number of
         failed inter RAT handovers from 3G to e-UTRAN."
        ::= { tmnxMobPdnProcEntry 45 }

tmnxMobPdnInterRatEutranTo3gSucc OBJECT-TYPE
    SYNTAX     Counter32
    MAX-ACCESS read-only
    STATUS     current
    DESCRIPTION
        "The value of tmnxMobPdnInterRatEutranTo3gSucc indicates the number of
         successful inter RAT handovers from 3G to e-UTRAN."
        ::= { tmnxMobPdnProcEntry 46 }

tmnxMobPdnInterRatEutranTo3gFail OBJECT-TYPE
    SYNTAX     Counter32
    MAX-ACCESS read-only
    STATUS     current
    DESCRIPTION
        "The value of tmnxMobPdnInterRatEutranTo3gFail indicates the number of
         failed inter RAT handovers from 3G to e-UTRAN."
        ::= { tmnxMobPdnProcEntry 47 }

tmnxMobPdneHRPDSessDeactSessTO      OBJECT-TYPE
    SYNTAX      Counter32
    MAX-ACCESS  read-only
    STATUS      current
    DESCRIPTION
        "The value of tmnxMobPdneHRPDSessDeactSessTO indicates the number of
         evolved High Rate Packet Data (eHRPD) sessions deactivated due to the
         session time-out."
    ::= { tmnxMobPdnProcEntry 48 }

tmnxMobPdneHRPDSessDeactIdleTO      OBJECT-TYPE
    SYNTAX      Counter32
    MAX-ACCESS  read-only
    STATUS      current
    DESCRIPTION
        "The value of tmnxMobPdneHRPDSessDeactIdleTO indicates the number of
         evolved High Rate Packet Data (eHRPD) sessions deactivated due to 
         the idle time-out."
    ::= { tmnxMobPdnProcEntry 49 }

--
--  Gx peer list Table
--

tmnxMobPdnGxPeerTableLastChngd     OBJECT-TYPE
    SYNTAX      TimeStamp
    MAX-ACCESS  read-only
    STATUS      current
    DESCRIPTION
        "The value of tmnxMobPdnGxPeerTableLastChngd indicates the sysUpTime
         at the time of the last modification to tmnxMobPdnGxPeerTable by
         adding, deleting an entry or change to a writable object in the table.

         If no changes were made to the table since the last re-initialization
         of the local network management subsystem, then this object contains
         a zero value."
    ::= { tmnxMobPdnGlobalObjs 14 }

tmnxMobPdnGxPeerTable  OBJECT-TYPE
    SYNTAX      SEQUENCE OF TmnxMobPdnGxPeerEntry
    MAX-ACCESS  not-accessible
    STATUS      current
    DESCRIPTION
        "The tmnxMobPdnGxPeerTable has an entry for each peer on the Gx
         reference point served by a Packet Data Network Gateway (PGW)."
    ::= { tmnxMobPdnStatObjs 8 }

tmnxMobPdnGxPeerEntry  OBJECT-TYPE
    SYNTAX      TmnxMobPdnGxPeerEntry
    MAX-ACCESS  not-accessible
    STATUS      current
    DESCRIPTION
        "Each row entry represents a peer on the Gx reference point."
    INDEX { tmnxMobGwId,
            vRtrID,
            tmnxMobProfDiaPeerName,
            tmnxMobProfDiaPeerListIndex,
            tmnxMobPdnGxPeerAddressType,
            tmnxMobPdnGxPeerAddress,
            tmnxMobPdnGxPeerPort
          }
    ::= { tmnxMobPdnGxPeerTable 1 }

TmnxMobPdnGxPeerEntry ::= SEQUENCE {
        tmnxMobPdnGxPeerAddressType       InetAddressType,
        tmnxMobPdnGxPeerAddress           InetAddress,
        tmnxMobPdnGxPeerPort              InetPortNumber,
        tmnxMobPdnGxPeerLastChanged       TimeStamp,
        tmnxMobPdnGxPeerCreateTime        TimeStamp,
        tmnxMobPdnGxPeerPathMgmtState     TmnxMobDiaPathMgmtState,
        tmnxMobPdnGxPeerDetailState       TmnxMobDiaDetailPathMgmtState
    }

tmnxMobPdnGxPeerAddressType  OBJECT-TYPE
    SYNTAX      InetAddressType
    MAX-ACCESS  not-accessible
    STATUS      current
    DESCRIPTION
        "The value of tmnxMobPdnGxPeerAddressType indicates the type of
         address represented by tmnxMobPdnGxPeerAddress."
    ::= { tmnxMobPdnGxPeerEntry 1 }

tmnxMobPdnGxPeerAddress  OBJECT-TYPE
    SYNTAX      InetAddress (SIZE (0|4|16))
    MAX-ACCESS  not-accessible
    STATUS      current
    DESCRIPTION
        "The value of tmnxMobPdnGxPeerAddress indicates the IP address of the
         peer on Gx reference point."
    ::= { tmnxMobPdnGxPeerEntry 2 }

tmnxMobPdnGxPeerPort  OBJECT-TYPE
    SYNTAX      InetPortNumber
    MAX-ACCESS  not-accessible
    STATUS      current
    DESCRIPTION
        "The value of tmnxMobPdnGxPeerPort indicates the port number of this
         peer."
    ::= { tmnxMobPdnGxPeerEntry 3 }

tmnxMobPdnGxPeerLastChanged  OBJECT-TYPE
    SYNTAX      TimeStamp
    MAX-ACCESS  read-only
    STATUS      current
    DESCRIPTION
        "The value of tmnxMobPdnGxPeerLastChanged indicates the timestamp of
         the last change to this row in tmnxMobPdnGxPeerTable."
    ::= { tmnxMobPdnGxPeerEntry 4 }

tmnxMobPdnGxPeerCreateTime  OBJECT-TYPE
    SYNTAX      TimeStamp
    MAX-ACCESS  read-only
    STATUS      current
    DESCRIPTION
        "The value of tmnxMobPdnGxPeerCreateTime indicates the sysUpTime when
         this entry was created."
    ::= { tmnxMobPdnGxPeerEntry 5 }

tmnxMobPdnGxPeerPathMgmtState  OBJECT-TYPE
    SYNTAX      TmnxMobDiaPathMgmtState
    MAX-ACCESS  read-only
    STATUS      current
    DESCRIPTION
        "The value of tmnxMobPdnGxPeerPathMgmtState indicates the state of
         the path."
    ::= { tmnxMobPdnGxPeerEntry 6 }

tmnxMobPdnGxPeerDetailState  OBJECT-TYPE
    SYNTAX      TmnxMobDiaDetailPathMgmtState
    MAX-ACCESS  read-only
    STATUS      current
    DESCRIPTION
        "The value of tmnxMobPdnGxPeerDetailState indicates the detail state
         of the path."
    ::= { tmnxMobPdnGxPeerEntry 7 }

--
--  Gx Stats Table
--

tmnxMobPdnGxStatTable  OBJECT-TYPE
    SYNTAX      SEQUENCE OF TmnxMobPdnGxStatEntry
    MAX-ACCESS  not-accessible
    STATUS      current
    DESCRIPTION
        "The tmnxMobPdnGxStatTable has an entry for each peer on the Gx
         reference point served by a Packet Data Network Gateway (PGW)."
    ::= { tmnxMobPdnStatObjs 9 }

tmnxMobPdnGxStatEntry  OBJECT-TYPE
    SYNTAX      TmnxMobPdnGxStatEntry
    MAX-ACCESS  not-accessible
    STATUS      current
    DESCRIPTION
        "Each row entry represents a peer on the Gx reference point and
         contain statistics for this peer on a card."
    INDEX { tmnxMobGwId,
            vRtrID,
            tmnxMobProfDiaPeerName,
            tmnxMobProfDiaPeerListIndex,
            tmnxMobPdnGxPeerAddressType,
            tmnxMobPdnGxPeerAddress,
            tmnxMobPdnGxPeerPort,
            tmnxChassisIndex,
            tmnxCardSlotNum
          }
    ::= { tmnxMobPdnGxStatTable 1 }

TmnxMobPdnGxStatEntry ::= SEQUENCE {
        tmnxMobPdnGxStatTxCer               Counter32,
        tmnxMobPdnGxStatRxCea               Counter32,
        tmnxMobPdnGxStatRxDpr               Counter32,
        tmnxMobPdnGxStatTxDpa               Counter32,
        tmnxMobPdnGxStatTxDwr               Counter32,
        tmnxMobPdnGxStatRxDwa               Counter32,
        tmnxMobPdnGxStatConnAttempts        Counter32,
        tmnxMobPdnGxStatConnFailures        Counter32,
        tmnxMobPdnGxStatRxTransportDisc     Counter32,
        tmnxMobPdnGxStatRxMsgUnexpectVer    Counter32,
        tmnxMobPdnGxStatRxMsgTooBig         Counter32,
        tmnxMobPdnGxStatRxMsgTooSmall       Counter32,
        tmnxMobPdnGxStatRxInvalidCea        Counter32,
        tmnxMobPdnGxStatRxMsgs              Counter32,
        tmnxMobPdnGxStatTxMsgs              Counter32,
        tmnxMobPdnGxStatTxRetransmitMsgs    Counter32,
        tmnxMobPdnGxStatTxCcrInitial        Counter32,
        tmnxMobPdnGxStatRxCcaInitial        Counter32,
        tmnxMobPdnGxStatTxCcrUpdate         Counter32,
        tmnxMobPdnGxStatRxCcaUpdate         Counter32,
        tmnxMobPdnGxStatTxCcrTerminate      Counter32,
        tmnxMobPdnGxStatRxCcaTerminate      Counter32,
        tmnxMobPdnGxStatCcrInitFails        Counter32,
        tmnxMobPdnGxStatCcrUpdateFails      Counter32,
        tmnxMobPdnGxStatCcrTermFails        Counter32,
        tmnxMobPdnGxStatRxRar               Counter32,
        tmnxMobPdnGxStatTxRaa               Counter32,
        tmnxMobPdnGxStatTxRaaNack           Counter32,
        tmnxMobPdnGxStatBberfs              Counter32,
        tmnxMobPdnGxStatRxMalformedPkts     Counter32,
        tmnxMobPdnGxStatRxCcaIMalformPkt    Counter32,
        tmnxMobPdnGxStatRxCcaUMalformPkt    Counter32,
        tmnxMobPdnGxStatRxCcaTMalformPkt    Counter32,
        tmnxMobPdnGxStatRxRarMalformPkts    Counter32,
        tmnxMobPdnGxStatRxUnknownPkts       Counter32,
        tmnxMobPdnGxStatRxCcaIUnknownPkt    Counter32,
        tmnxMobPdnGxStatRxCcaUUnknownPkt    Counter32,
        tmnxMobPdnGxStatRxCcaTUnknownPkt    Counter32,
        tmnxMobPdnGxStatRxRarUnknownPkts    Counter32,
        tmnxMobPdnGxStatRxMissingIePkts     Counter32,
        tmnxMobPdnGxStatRxCcaIMissIePkts    Counter32,
        tmnxMobPdnGxStatRxCcaUMissIePkts    Counter32,
        tmnxMobPdnGxStatRxCcaTMissIePkts    Counter32,
        tmnxMobPdnGxStatRxRarMissIePkts     Counter32,
        tmnxMobPdnGxStatRxCcaIUnkSession    Counter32,
        tmnxMobPdnGxStatRxCcaUUnkSession    Counter32,
        tmnxMobPdnGxStatRxCcaTUnkSession    Counter32,
        tmnxMobPdnGxStatRxRarUnkSession     Counter32,
        tmnxMobPdnGxStatTxDpr               Counter32,
        tmnxMobPdnGxStatRxDpa               Counter32,
        tmnxMobPdnGxStatRxDwr               Counter32,
        tmnxMobPdnGxStatTxDwa               Counter32,
        tmnxMobPdnGxStatRxCcaInitialFail    Counter32,
        tmnxMobPdnGxStatRxCcaUpdateFail     Counter32,
        tmnxMobPdnGxStatRxCcaTermFail       Counter32,
        tmnxMobPdnGxStatReTxCcrInitial      Counter32,
        tmnxMobPdnGxStatReTxCcrUpdate       Counter32,
        tmnxMobPdnGxStatReTxCcrTerm         Counter32
    }

tmnxMobPdnGxStatTxCer  OBJECT-TYPE
    SYNTAX      Counter32
    MAX-ACCESS  read-only
    STATUS      current
    DESCRIPTION
        "The value of tmnxMobPdnGxStatTxCer indicates the number of Capabilities
         Exchange Request (CER) messages transmitted to this peer."
    ::= { tmnxMobPdnGxStatEntry 1 }

tmnxMobPdnGxStatRxCea  OBJECT-TYPE
    SYNTAX      Counter32
    MAX-ACCESS  read-only
    STATUS      current
    DESCRIPTION
        "The value of tmnxMobPdnGxStatRxCea indicates the number of Capabilities
         Exchange Answer (CEA) messages received from this peer."
    ::= { tmnxMobPdnGxStatEntry 2 }

tmnxMobPdnGxStatRxDpr  OBJECT-TYPE
    SYNTAX      Counter32
    MAX-ACCESS  read-only
    STATUS      current
    DESCRIPTION
        "The value of tmnxMobPdnGxStatRxDpr indicates the number of Disconnect
         Peer Request (DPR) messages received from this peer."
    ::= { tmnxMobPdnGxStatEntry 3 }

tmnxMobPdnGxStatTxDpa  OBJECT-TYPE
    SYNTAX      Counter32
    MAX-ACCESS  read-only
    STATUS      current
    DESCRIPTION
        "The value of tmnxMobPdnGxStatTxDpa indicates the number of Disconnect
         Peer Answer (DPA) messages transmitted to this peer."
    ::= { tmnxMobPdnGxStatEntry 4 }

tmnxMobPdnGxStatTxDwr  OBJECT-TYPE
    SYNTAX      Counter32
    MAX-ACCESS  read-only
    STATUS      current
    DESCRIPTION
        "The value of tmnxMobPdnGxStatTxDwr indicates the number of Device
         Watchdog Request (DWR) messages transmitted to this peer."
    ::= { tmnxMobPdnGxStatEntry 5 }

tmnxMobPdnGxStatRxDwa  OBJECT-TYPE
    SYNTAX      Counter32
    MAX-ACCESS  read-only
    STATUS      current
    DESCRIPTION
        "The value of tmnxMobPdnGxStatRxDwa indicates the number of Device
         Watchdog Answer (DWA) messages received from this peer."
    ::= { tmnxMobPdnGxStatEntry 6 }

tmnxMobPdnGxStatConnAttempts  OBJECT-TYPE
    SYNTAX      Counter32
    MAX-ACCESS  read-only
    STATUS      current
    DESCRIPTION
        "The value of tmnxMobPdnGxStatConnAttempts indicates the number of 
         connections attempted to this peer."
    ::= { tmnxMobPdnGxStatEntry 7 }

tmnxMobPdnGxStatConnFailures  OBJECT-TYPE
    SYNTAX      Counter32
    MAX-ACCESS  read-only
    STATUS      current
    DESCRIPTION
        "The value of tmnxMobPdnGxStatConnFailures indicates the number of 
         failed connections with this peer."
    ::= { tmnxMobPdnGxStatEntry 8 }

tmnxMobPdnGxStatRxTransportDisc  OBJECT-TYPE
    SYNTAX      Counter32
    MAX-ACCESS  read-only
    STATUS      current
    DESCRIPTION
        "The value of tmnxMobPdnGxStatRxTransportDisc indicates the number of 
         remote transport disconnect messages received from this peer."
    ::= { tmnxMobPdnGxStatEntry 9 }

tmnxMobPdnGxStatRxMsgUnexpectVer  OBJECT-TYPE
    SYNTAX      Counter32
    MAX-ACCESS  read-only
    STATUS      current
    DESCRIPTION
        "The value of tmnxMobPdnGxStatRxMsgUnexpectVer indicates the number of 
         unexpected version messages received from this peer."
    ::= { tmnxMobPdnGxStatEntry 10 }

tmnxMobPdnGxStatRxMsgTooBig  OBJECT-TYPE
    SYNTAX      Counter32
    MAX-ACCESS  read-only
    STATUS      current
    DESCRIPTION
        "The value of tmnxMobPdnGxStatRxMsgTooBig indicates the number of 
         oversize messages received from this peer."
    ::= { tmnxMobPdnGxStatEntry 11 }

tmnxMobPdnGxStatRxMsgTooSmall  OBJECT-TYPE
    SYNTAX      Counter32
    MAX-ACCESS  read-only
    STATUS      current
    DESCRIPTION
        "The value of tmnxMobPdnGxStatRxMsgTooSmall indicates the number of 
         small messages received from this peer."
    ::= { tmnxMobPdnGxStatEntry 12 }

tmnxMobPdnGxStatRxInvalidCea  OBJECT-TYPE
    SYNTAX      Counter32
    MAX-ACCESS  read-only
    STATUS      current
    DESCRIPTION
        "The value of tmnxMobPdnGxStatRxInvalidCea indicates the number of 
         invalid Capabilities Exchange Answer (CEA) messages received from 
         this peer."
    ::= { tmnxMobPdnGxStatEntry 13 }

tmnxMobPdnGxStatRxMsgs  OBJECT-TYPE
    SYNTAX      Counter32
    MAX-ACCESS  read-only
    STATUS      current
    DESCRIPTION
        "The value of tmnxMobPdnGxStatRxMsgs indicates the total number of 
         messages received from this peer."
    ::= { tmnxMobPdnGxStatEntry 14 }

tmnxMobPdnGxStatTxMsgs  OBJECT-TYPE
    SYNTAX      Counter32
    MAX-ACCESS  read-only
    STATUS      current
    DESCRIPTION
        "The value of tmnxMobPdnGxStatTxMsgs indicates the total number of 
         messages transmitted to this peer."
    ::= { tmnxMobPdnGxStatEntry 15 }

tmnxMobPdnGxStatTxRetransmitMsgs  OBJECT-TYPE
    SYNTAX      Counter32
    MAX-ACCESS  read-only
    STATUS      current
    DESCRIPTION
        "The value of tmnxMobPdnGxStatTxRetransmitMsgs indicates the number of 
         retransmit messages transmitted to this peer."
    ::= { tmnxMobPdnGxStatEntry 16 }

tmnxMobPdnGxStatTxCcrInitial  OBJECT-TYPE
    SYNTAX      Counter32
    MAX-ACCESS  read-only
    STATUS      current
    DESCRIPTION
        "The value of tmnxMobPdnGxStatTxCcrInitial indicates the number of
         Credit Control Request (CCR) Initial messages transmitted to
         this peer."
    ::= { tmnxMobPdnGxStatEntry 17 }

tmnxMobPdnGxStatRxCcaInitial  OBJECT-TYPE
    SYNTAX      Counter32
    MAX-ACCESS  read-only
    STATUS      current
    DESCRIPTION
        "The value of tmnxMobPdnGxStatRxCcaInitial indicates the number of
         Credit Control Answer (CCA) Initial messages received from
         this peer."
    ::= { tmnxMobPdnGxStatEntry 18 }

tmnxMobPdnGxStatTxCcrUpdate  OBJECT-TYPE
    SYNTAX      Counter32
    MAX-ACCESS  read-only
    STATUS      current
    DESCRIPTION
        "The value of tmnxMobPdnGxStatTxCcrUpdate indicates the number of
         Credit Control Request (CCR) Update messages transmitted to
         this peer."
    ::= { tmnxMobPdnGxStatEntry 19 }

tmnxMobPdnGxStatRxCcaUpdate  OBJECT-TYPE
    SYNTAX      Counter32
    MAX-ACCESS  read-only
    STATUS      current
    DESCRIPTION
        "The value of tmnxMobPdnGxStatRxCcaUpdate indicates the number of
         Credit Control Answer (CCA) Update messages received from
         this peer."
    ::= { tmnxMobPdnGxStatEntry 20 }

tmnxMobPdnGxStatTxCcrTerminate  OBJECT-TYPE
    SYNTAX      Counter32
    MAX-ACCESS  read-only
    STATUS      current
    DESCRIPTION
        "The value of tmnxMobPdnGxStatTxCcrTerminate indicates the number of
         Credit Control Request (CCR) Termination messages transmitted to
         this peer."
    ::= { tmnxMobPdnGxStatEntry 21 }

tmnxMobPdnGxStatRxCcaTerminate  OBJECT-TYPE
    SYNTAX      Counter32
    MAX-ACCESS  read-only
    STATUS      current
    DESCRIPTION
        "The value of tmnxMobPdnGxStatRxCcaTerminate indicates the number of
         Credit Control Answer (CCA) Termination messages received from
         this peer."
    ::= { tmnxMobPdnGxStatEntry 22 }

tmnxMobPdnGxStatCcrInitFails  OBJECT-TYPE
    SYNTAX      Counter32
    MAX-ACCESS  read-only
    STATUS      current
    DESCRIPTION
        "The value of tmnxMobPdnGxStatCcrInitFails indicates the number of
         Credit Control Request (CCR) Initial message failures."
    ::= { tmnxMobPdnGxStatEntry 23 }

tmnxMobPdnGxStatCcrUpdateFails  OBJECT-TYPE
    SYNTAX      Counter32
    MAX-ACCESS  read-only
    STATUS      current
    DESCRIPTION
        "The value of tmnxMobPdnGxStatCcrUpdateFails indicates the number of
         Credit Control Request (CCR) Update message failures."
    ::= { tmnxMobPdnGxStatEntry 24 }

tmnxMobPdnGxStatCcrTermFails  OBJECT-TYPE
    SYNTAX      Counter32
    MAX-ACCESS  read-only
    STATUS      current
    DESCRIPTION
        "The value of tmnxMobPdnGxStatCcrTermFails indicates the number of
         Credit Control Request (CCR) Termination message failures."
    ::= { tmnxMobPdnGxStatEntry 25 }

tmnxMobPdnGxStatRxRar  OBJECT-TYPE
    SYNTAX      Counter32
    MAX-ACCESS  read-only
    STATUS      current
    DESCRIPTION
        "The value of tmnxMobPdnGxStatRxRar indicates the number of Re-Auth
         Request (RAR) messages received from this peer."
    ::= { tmnxMobPdnGxStatEntry 26 }

tmnxMobPdnGxStatTxRaa  OBJECT-TYPE
    SYNTAX      Counter32
    MAX-ACCESS  read-only
    STATUS      current
    DESCRIPTION
        "The value of tmnxMobPdnGxStatTxRaa indicates the number of Re-Auth
         Answer (RAA) messages transmitted to this peer."
    ::= { tmnxMobPdnGxStatEntry 27 }

tmnxMobPdnGxStatTxRaaNack  OBJECT-TYPE
    SYNTAX      Counter32
    MAX-ACCESS  read-only
    STATUS      current
    DESCRIPTION
        "The value of tmnxMobPdnGxStatTxRaaNack indicates the number of Re-Auth
         Answer (RAA) negative acknowledgement (NACK) messages transmitted to
         this peer."
    ::= { tmnxMobPdnGxStatEntry 28 }

tmnxMobPdnGxStatBberfs  OBJECT-TYPE
    SYNTAX      Counter32
    MAX-ACCESS  read-only
    STATUS      current
    DESCRIPTION
        "The value of tmnxMobPdnGxStatBberfs indicates the number of Bearer
         Binding and Event Reporting Function (BBERF) procedures transmitted
         by this peer."
    ::= { tmnxMobPdnGxStatEntry 29 }

tmnxMobPdnGxStatRxMalformedPkts  OBJECT-TYPE
    SYNTAX      Counter32
    MAX-ACCESS  read-only
    STATUS      current
    DESCRIPTION
        "The value of tmnxMobPdnGxStatRxMalformedPkts indicates the number of
         malformed packets received from this peer."
    ::= { tmnxMobPdnGxStatEntry 30 }

tmnxMobPdnGxStatRxCcaIMalformPkt  OBJECT-TYPE
    SYNTAX      Counter32
    MAX-ACCESS  read-only
    STATUS      current
    DESCRIPTION
        "The value of tmnxMobPdnGxStatRxCcaIMalformPkt indicates the number of
         Credit Control Answer (CCA) Initial malformed packets received
         from this peer."
    ::= { tmnxMobPdnGxStatEntry 31 }

tmnxMobPdnGxStatRxCcaUMalformPkt  OBJECT-TYPE
    SYNTAX      Counter32
    MAX-ACCESS  read-only
    STATUS      current
    DESCRIPTION
        "The value of tmnxMobPdnGxStatRxCcaUMalformPkt indicates the number of
         Credit Control Answer (CCA) Update malformed packets received
         from this peer."
    ::= { tmnxMobPdnGxStatEntry 32 }

tmnxMobPdnGxStatRxCcaTMalformPkt  OBJECT-TYPE
    SYNTAX      Counter32
    MAX-ACCESS  read-only
    STATUS      current
    DESCRIPTION
        "The value of tmnxMobPdnGxStatRxCcaTMalformPkt indicates the number of
         Credit Control Answer (CCA) Termination malformed packets received
         from this peer."
    ::= { tmnxMobPdnGxStatEntry 33 }

tmnxMobPdnGxStatRxRarMalformPkts  OBJECT-TYPE
    SYNTAX      Counter32
    MAX-ACCESS  read-only
    STATUS      current
    DESCRIPTION
        "The value of tmnxMobPdnGxStatRxRarMalformPkts indicates the number of
         Re-Auth Request (RAR) malformed packets received from this peer."
    ::= { tmnxMobPdnGxStatEntry 34 }

tmnxMobPdnGxStatRxUnknownPkts  OBJECT-TYPE
    SYNTAX      Counter32
    MAX-ACCESS  read-only
    STATUS      current
    DESCRIPTION
        "The value of tmnxMobPdnGxStatRxRarMalformPkts indicates the number of
         unknown packets received from this peer."
    ::= { tmnxMobPdnGxStatEntry 35 }

tmnxMobPdnGxStatRxCcaIUnknownPkt  OBJECT-TYPE
    SYNTAX      Counter32
    MAX-ACCESS  read-only
    STATUS      current
    DESCRIPTION
        "The value of tmnxMobPdnGxStatRxCcaIUnknownPkt indicates the number of
         Credit Control Answer (CCA) Initial unknown packets received
         from this peer."
    ::= { tmnxMobPdnGxStatEntry 36 }

tmnxMobPdnGxStatRxCcaUUnknownPkt  OBJECT-TYPE
    SYNTAX      Counter32
    MAX-ACCESS  read-only
    STATUS      current
    DESCRIPTION
        "The value of tmnxMobPdnGxStatRxCcaUUnknownPkt indicates the number of
         Credit Control Answer (CCA) Update unknown packets received
         from this peer."
    ::= { tmnxMobPdnGxStatEntry 37 }

tmnxMobPdnGxStatRxCcaTUnknownPkt  OBJECT-TYPE
    SYNTAX      Counter32
    MAX-ACCESS  read-only
    STATUS      current
    DESCRIPTION
        "The value of tmnxMobPdnGxStatRxCcaTUnknownPkt indicates the number of
         Credit Control Answer (CCA) Termination unknown packets received
         from this peer."
    ::= { tmnxMobPdnGxStatEntry 38 }

tmnxMobPdnGxStatRxRarUnknownPkts  OBJECT-TYPE
    SYNTAX      Counter32
    MAX-ACCESS  read-only
    STATUS      current
    DESCRIPTION
        "The value of tmnxMobPdnGxStatRxRarUnknownPkts indicates the number of
         Re-Auth Request (RAR) unknown packets received from this peer."
    ::= { tmnxMobPdnGxStatEntry 39 }

tmnxMobPdnGxStatRxMissingIePkts  OBJECT-TYPE
    SYNTAX      Counter32
    MAX-ACCESS  read-only
    STATUS      current
    DESCRIPTION
        "The value of tmnxMobPdnGxStatRxMissingIePkts indicates the number of
         missing mandatory Information Element (IE) packets received from
         this peer."
    ::= { tmnxMobPdnGxStatEntry 40 }

tmnxMobPdnGxStatRxCcaIMissIePkts  OBJECT-TYPE
    SYNTAX      Counter32
    MAX-ACCESS  read-only
    STATUS      current
    DESCRIPTION
        "The value of tmnxMobPdnGxStatRxCcaIMissIePkts indicates the number of
         Credit Control Answer (CCA) Initial missing mandatory Information
         Element (IE) packets received from this peer."
    ::= { tmnxMobPdnGxStatEntry 41 }

tmnxMobPdnGxStatRxCcaUMissIePkts  OBJECT-TYPE
    SYNTAX      Counter32
    MAX-ACCESS  read-only
    STATUS      current
    DESCRIPTION
        "The value of tmnxMobPdnGxStatRxCcaUMissIePkts indicates the number of
         Credit Control Answer (CCA) Update missing mandatory Information
         Element (IE) packets received from this peer."
    ::= { tmnxMobPdnGxStatEntry 42 }

tmnxMobPdnGxStatRxCcaTMissIePkts  OBJECT-TYPE
    SYNTAX      Counter32
    MAX-ACCESS  read-only
    STATUS      current
    DESCRIPTION
        "The value of tmnxMobPdnGxStatRxCcaTMissIePkts indicates the number of
         Credit Control Answer (CCA) Termination missing mandatory Information
         Element (IE) packets received from this peer."
    ::= { tmnxMobPdnGxStatEntry 43 }

tmnxMobPdnGxStatRxRarMissIePkts  OBJECT-TYPE
    SYNTAX      Counter32
    MAX-ACCESS  read-only
    STATUS      current
    DESCRIPTION
        "The value of tmnxMobPdnGxStatRxRarMissIePkts indicates the number of
         Re-Auth Request (RAR) missing mandatory Information Element (IE)
         packets received from this peer."
    ::= { tmnxMobPdnGxStatEntry 44 }

tmnxMobPdnGxStatRxCcaIUnkSession  OBJECT-TYPE
    SYNTAX      Counter32
    MAX-ACCESS  read-only
    STATUS      current
    DESCRIPTION
        "The value of tmnxMobPdnGxStatRxCcaIUnkSession indicates the number of
         Credit Control Answer (CCA) Initial unknown session packets received
         from this peer."
    ::= { tmnxMobPdnGxStatEntry 45 }

tmnxMobPdnGxStatRxCcaUUnkSession  OBJECT-TYPE
    SYNTAX      Counter32
    MAX-ACCESS  read-only
    STATUS      current
    DESCRIPTION
        "The value of tmnxMobPdnGxStatRxCcaUUnkSession indicates the number of
         Credit Control Answer (CCA) Update unknown session packets received
         from this peer."
    ::= { tmnxMobPdnGxStatEntry 46 }

tmnxMobPdnGxStatRxCcaTUnkSession  OBJECT-TYPE
    SYNTAX      Counter32
    MAX-ACCESS  read-only
    STATUS      current
    DESCRIPTION
        "The value of tmnxMobPdnGxStatRxCcaTUnkSession indicates the number of
         Credit Control Answer (CCA) Termination unknown session packets
         received from this peer."
    ::= { tmnxMobPdnGxStatEntry 47 }

tmnxMobPdnGxStatRxRarUnkSession  OBJECT-TYPE
    SYNTAX      Counter32
    MAX-ACCESS  read-only
    STATUS      current
    DESCRIPTION
        "The value of tmnxMobPdnGxStatRxRarUnkSession indicates the number of
         Re-Auth Request (RAR) unknown session packets received from this peer."
    ::= { tmnxMobPdnGxStatEntry 48 }

tmnxMobPdnGxStatTxDpr               OBJECT-TYPE
    SYNTAX      Counter32
    MAX-ACCESS  read-only
    STATUS      current
    DESCRIPTION
        "The value of tmnxMobPdnGxStatTxDpr indicates the number of Disconnect
         Peer Request (DPR) messages transmitted to this peer."
    ::= { tmnxMobPdnGxStatEntry 49 }

tmnxMobPdnGxStatRxDpa               OBJECT-TYPE
    SYNTAX      Counter32
    MAX-ACCESS  read-only
    STATUS      current
    DESCRIPTION
        "The value of tmnxMobPdnGxStatRxDpa indicates the number of Disconnect
         Peer Answer (DPA) messages received from this peer."
    ::= { tmnxMobPdnGxStatEntry 50 }

tmnxMobPdnGxStatRxDwr               OBJECT-TYPE
    SYNTAX      Counter32
    MAX-ACCESS  read-only
    STATUS      current
    DESCRIPTION
        "The value of tmnxMobPdnGxStatRxDwr indicates the number of Device
         Watchdog Request (DWR) messages received from this peer."
    ::= { tmnxMobPdnGxStatEntry 51 }

tmnxMobPdnGxStatTxDwa               OBJECT-TYPE
    SYNTAX      Counter32
    MAX-ACCESS  read-only
    STATUS      current
    DESCRIPTION
        "The value of tmnxMobPdnGxStatTxDwa indicates the number of Device
         Watchdog Answer (DWA) messages transmitted to this peer."
    ::= { tmnxMobPdnGxStatEntry 52 }

tmnxMobPdnGxStatRxCcaInitialFail    OBJECT-TYPE
    SYNTAX      Counter32
    MAX-ACCESS  read-only
    STATUS      current
    DESCRIPTION
        "The value of tmnxMobPdnGxStatRxCcaInitialFail indicates the number of
         Credit Control Answer (CCA) Initial message failures received from 
         this peer."
    ::= { tmnxMobPdnGxStatEntry 53 }

tmnxMobPdnGxStatRxCcaUpdateFail     OBJECT-TYPE
    SYNTAX      Counter32
    MAX-ACCESS  read-only
    STATUS      current
    DESCRIPTION
        "The value of tmnxMobPdnGxStatRxCcaUpdateFail indicates the number of
         Credit Control Answer (CCA) Update message failures received from this
         peer."
    ::= { tmnxMobPdnGxStatEntry 54 }

tmnxMobPdnGxStatRxCcaTermFail       OBJECT-TYPE
    SYNTAX      Counter32
    MAX-ACCESS  read-only
    STATUS      current
    DESCRIPTION
        "The value of tmnxMobPdnGxStatRxCcaTermFail indicates the number of
         Credit Control Answer (CCA) Termination message failures received 
         from this peer."
    ::= { tmnxMobPdnGxStatEntry 55 }

tmnxMobPdnGxStatReTxCcrInitial    OBJECT-TYPE
    SYNTAX      Counter32
    MAX-ACCESS  read-only
    STATUS      current
    DESCRIPTION
        "The value of tmnxMobPdnGxStatReTxCcrInitial indicates the number of
         Credit Control Request (CCR) Initial messages re-transmitted to
         this peer."
    ::= { tmnxMobPdnGxStatEntry 56 }

tmnxMobPdnGxStatReTxCcrUpdate     OBJECT-TYPE
    SYNTAX      Counter32
    MAX-ACCESS  read-only
    STATUS      current
    DESCRIPTION
        "The value of tmnxMobPdnGxStatReTxCcrUpdate indicates the number of
         Credit Control Request (CCR) Update messages re-transmitted to
         this peer."
    ::= { tmnxMobPdnGxStatEntry 57 }

tmnxMobPdnGxStatReTxCcrTerm       OBJECT-TYPE
    SYNTAX      Counter32
    MAX-ACCESS  read-only
    STATUS      current
    DESCRIPTION
        "The value of tmnxMobPdnGxStatReTxCcrTerm indicates the number of
         Credit Control Request (CCR) Termination messages re-transmitted to
         this peer."
    ::= { tmnxMobPdnGxStatEntry 58 }
 
--
--  Gn peer list table
--

tmnxMobPdnGnPeerTableLastChanged     OBJECT-TYPE
    SYNTAX      TimeStamp
    MAX-ACCESS  read-only
    STATUS      current
    DESCRIPTION
        "The value of tmnxMobPdnGnPeerTableLastChanged indicates the sysUpTime at
         the time of the last modification to tmnxMobPdnGnPeerTable by adding,
         deleting an entry or change to a writable object in the table.

         If no changes were made to the table since the last re-initialization
         of the local network management subsystem, then this object contains
         a zero value."
    ::= { tmnxMobPdnGlobalObjs 18 }

tmnxMobPdnGnPeerTable  OBJECT-TYPE
    SYNTAX      SEQUENCE OF TmnxMobPdnGnPeerEntry
    MAX-ACCESS  not-accessible
    STATUS      current
    DESCRIPTION
        "The tmnxMobPdnGnPeerTable has an entry for each peer on the Gn
         reference point."
    ::= { tmnxMobPdnConfObjs 17 }

tmnxMobPdnGnPeerEntry  OBJECT-TYPE
    SYNTAX      TmnxMobPdnGnPeerEntry
    MAX-ACCESS  not-accessible
    STATUS      current
    DESCRIPTION
        "Each row entry represents a peer on the Gn reference point."
    INDEX { vRtrID,
            tmnxMobPdnGnPeerAddressType,
            tmnxMobPdnGnPeerAddress,
            tmnxMobPdnGnPeerPort
          }
    ::= { tmnxMobPdnGnPeerTable 1 }

TmnxMobPdnGnPeerEntry ::= SEQUENCE {
        tmnxMobPdnGnPeerAddressType        InetAddressType,
        tmnxMobPdnGnPeerAddress            InetAddress,
        tmnxMobPdnGnPeerPort               InetPortNumber,
        tmnxMobPdnGnPeerLastChanged        TimeStamp,
        tmnxMobPdnGnPeerCreateTime         TimeStamp,
        tmnxMobPdnGnPeerPathMgmtState      TmnxMobPathMgmtState,
        tmnxMobPdnGnPeerGatewayId          TmnxMobGwId,
        tmnxMobPdnGnPeerType               TmnxMobPeerType
    }

tmnxMobPdnGnPeerAddressType  OBJECT-TYPE
    SYNTAX      InetAddressType
    MAX-ACCESS  not-accessible
    STATUS      current
    DESCRIPTION
        "The value of tmnxMobPdnGnPeerAddressType indicates the type of
         address represented by tmnxMobPdnGnPeerAddress."
    ::= { tmnxMobPdnGnPeerEntry 1 }

tmnxMobPdnGnPeerAddress  OBJECT-TYPE
    SYNTAX      InetAddress (SIZE (4|16))
    MAX-ACCESS  not-accessible
    STATUS      current
    DESCRIPTION
        "The value of tmnxMobPdnGnPeerAddress indicates the IP address of the
         peer on Gn reference point."
    ::= { tmnxMobPdnGnPeerEntry 2 }

tmnxMobPdnGnPeerPort  OBJECT-TYPE
    SYNTAX      InetPortNumber
    MAX-ACCESS  not-accessible
    STATUS      current
    DESCRIPTION
        "The value of tmnxMobPdnGnPeerPort indicates the port number of this
         peer."
    ::= { tmnxMobPdnGnPeerEntry 3 }

tmnxMobPdnGnPeerLastChanged  OBJECT-TYPE
    SYNTAX      TimeStamp
    MAX-ACCESS  read-only
    STATUS      current
    DESCRIPTION
        "The value of tmnxMobPdnGnPeerLastChanged indicates the timestamp of
         the last change to this row in tmnxMobPdnGnPeerTable."
    ::= { tmnxMobPdnGnPeerEntry 4 }

tmnxMobPdnGnPeerCreateTime  OBJECT-TYPE
    SYNTAX      TimeStamp
    MAX-ACCESS  read-only
    STATUS      current
    DESCRIPTION
        "The value of tmnxMobPdnGnPeerCreateTime indicates the sysUpTime when
         this entry was created."
    ::= { tmnxMobPdnGnPeerEntry 5 }

tmnxMobPdnGnPeerPathMgmtState  OBJECT-TYPE
    SYNTAX      TmnxMobPathMgmtState
    MAX-ACCESS  read-only
    STATUS      current
    DESCRIPTION
        "The value of tmnxMobPdnGnPeerPathMgmtState indicates the state of
         path."
    ::= { tmnxMobPdnGnPeerEntry 6 }

tmnxMobPdnGnPeerGatewayId  OBJECT-TYPE
    SYNTAX      TmnxMobGwId
    MAX-ACCESS  read-only
    STATUS      current
    DESCRIPTION
        "The value of tmnxMobPdnGnPeerGatewayId indicates the gateway 
         to which this peer belongs."
    ::= { tmnxMobPdnGnPeerEntry 7 }

tmnxMobPdnGnPeerType  OBJECT-TYPE
    SYNTAX      TmnxMobPeerType
    MAX-ACCESS  read-only
    STATUS      current
    DESCRIPTION
        "The value of tmnxMobPdnGnPeerType indicates the type of this peer."
    ::= { tmnxMobPdnGnPeerEntry 8 }

--
--  Radius table
--

tmnxMobPdnRadiusTableLastChanged  OBJECT-TYPE
    SYNTAX      TimeStamp
    MAX-ACCESS  read-only
    STATUS      current
    DESCRIPTION
        "The value of tmnxMobPdnRadiusTableLastChanged indicates the sysUpTime 
         at the time of the last modification to tmnxMobPdnRadiusTable by 
         adding, deleting an entry or change to a writable object in the table.

         If no changes were made to the table since the last re-initialization
         of the local network management subsystem, then this object contains
         a zero value."
    ::= { tmnxMobPdnGlobalObjs 19 }

tmnxMobPdnRadiusTable  OBJECT-TYPE
    SYNTAX      SEQUENCE OF TmnxMobPdnRadiusEntry
    MAX-ACCESS  not-accessible
    STATUS      current
    DESCRIPTION
        "The tmnxMobPdnRadiusTable provides an extension of the tmnxMobPdnTable
         for the radius configuration."
    ::= { tmnxMobPdnConfObjs 18 }

tmnxMobPdnRadiusEntry  OBJECT-TYPE
    SYNTAX      TmnxMobPdnRadiusEntry
    MAX-ACCESS  not-accessible
    STATUS      current
    DESCRIPTION
        "Each row entry represents additional columns for radius configuration 
         for a Packet Data Network Gateway (PGW)."
    AUGMENTS { tmnxMobPdnEntry }
    ::= { tmnxMobPdnRadiusTable 1 }

TmnxMobPdnRadiusEntry ::= SEQUENCE {
        tmnxMobPdnRadiusLastChanged    TimeStamp,
        tmnxMobPdnRadiusIfVRtrId       TmnxVRtrID,
        tmnxMobPdnRadiusIfIndex        InterfaceIndexOrZero,
        tmnxMobPdnRadiusDisconnect     TmnxEnabledDisabled
    }

tmnxMobPdnRadiusLastChanged  OBJECT-TYPE
    SYNTAX      TimeStamp
    MAX-ACCESS  read-only
    STATUS      current
    DESCRIPTION
        "The value of tmnxMobPdnRadiusLastChanged indicates the timestamp of
         the last change to this row in tmnxMobPdnRadiusTable."
    ::= { tmnxMobPdnRadiusEntry 1 }

tmnxMobPdnRadiusIfVRtrId  OBJECT-TYPE
    SYNTAX      TmnxVRtrID
    MAX-ACCESS  read-write
    STATUS      current
    DESCRIPTION
        "The value of tmnxMobPdnRadiusIfVRtrId specifies the virtual
         router to which the interface specified by tmnxMobPdnRadiusIfIndex 
         belongs."
    DEFVAL { 1 }
    ::= { tmnxMobPdnRadiusEntry 2 }

tmnxMobPdnRadiusIfIndex  OBJECT-TYPE
    SYNTAX      InterfaceIndexOrZero
    MAX-ACCESS  read-write
    STATUS      current
    DESCRIPTION
        "The value of tmnxMobPdnRadiusIfIndex specifies the interface
         index of the interface used for radius authentication and accounting."
    DEFVAL { 0 }
    ::= { tmnxMobPdnRadiusEntry 3 }

tmnxMobPdnRadiusDisconnect  OBJECT-TYPE
    SYNTAX      TmnxEnabledDisabled
    MAX-ACCESS  read-write
    STATUS      current
    DESCRIPTION
        "The value of tmnxMobPdnRadiusDisconnect specifies whether the 
         support for radius initiated disconnect is enabled or not.

         When the value of tmnxMobPdnRadiusDisconnect is not specifed, 
         the PGW/GGSN shall ignore the disconnect messages."
    DEFVAL { disabled }
    ::= { tmnxMobPdnRadiusEntry 4 }

--
--  Duplicate radius peer table
--

tmnxMobPdnApnDaccGrpTblLastChngd  OBJECT-TYPE
    SYNTAX      TimeStamp
    MAX-ACCESS  read-only
    STATUS      current
    DESCRIPTION
        "The value of tmnxMobPdnApnDaccGrpTblLastChngd indicates the 
         sysUpTime at the time of the last modification to the 
         tmnxMobPdnApnDaccGrpTable by adding, deleting an entry or change to a 
         writable object in the table.

         If no changes were made to the table since the last re-initialization
         of the local network management subsystem, then this object contains
         a zero value."
    ::= { tmnxMobPdnGlobalObjs 20 }

tmnxMobPdnApnDaccGrpTable  OBJECT-TYPE
    SYNTAX      SEQUENCE OF TmnxMobPdnApnDaccGrpEntry
    MAX-ACCESS  not-accessible
    STATUS      current
    DESCRIPTION
        "The tmnxMobPdnApnDaccGrpTable has an entry for each duplicate radius
         accounting server group configured on the system."
    ::= { tmnxMobPdnConfObjs 19 }

tmnxMobPdnApnDaccGrpEntry  OBJECT-TYPE
    SYNTAX      TmnxMobPdnApnDaccGrpEntry
    MAX-ACCESS  not-accessible
    STATUS      current
    DESCRIPTION
        "Each row entry represents a duplicate radius accounting server group."
    INDEX { tmnxMobGwId,
            tmnxMobPdnApnName,
            tmnxMobPdnApnDaccGrpName
          }
    ::= { tmnxMobPdnApnDaccGrpTable 1 }

TmnxMobPdnApnDaccGrpEntry ::= SEQUENCE {
        tmnxMobPdnApnDaccGrpName          TmnxMobProfName,
        tmnxMobPdnApnDaccGrpRowStatus     RowStatus,
        tmnxMobPdnApnDaccGrpLastChngd     TimeStamp
    }

tmnxMobPdnApnDaccGrpName  OBJECT-TYPE
    SYNTAX      TmnxMobProfName
    MAX-ACCESS  not-accessible
    STATUS      current
    DESCRIPTION
        "The value of tmnxMobPdnApnDaccGrpName specifies the unique name of this
         duplicate radius accounting server group."
    ::= { tmnxMobPdnApnDaccGrpEntry 1 }

tmnxMobPdnApnDaccGrpRowStatus  OBJECT-TYPE
    SYNTAX      RowStatus
    MAX-ACCESS  read-create
    STATUS      current
    DESCRIPTION
        "The value of tmnxMobPdnApnDaccGrpRowStatus specifies the row status of 
         this entry. It is used for creation and deletion of this duplicate
         radius accounting server group."
    ::= { tmnxMobPdnApnDaccGrpEntry 2 }

tmnxMobPdnApnDaccGrpLastChngd  OBJECT-TYPE
    SYNTAX      TimeStamp
    MAX-ACCESS  read-only
    STATUS      current
    DESCRIPTION
        "The value of tmnxMobPdnApnDaccGrpLastChngd indicates the timestamp of 
         the last change to this row in tmnxMobPdnApnDaccGrpTable."
    ::= { tmnxMobPdnApnDaccGrpEntry 3 }

--
--  Gy table
--

tmnxMobPdnGyTableLastChanged  OBJECT-TYPE
    SYNTAX      TimeStamp
    MAX-ACCESS  read-only
    STATUS      current
    DESCRIPTION
        "The value of tmnxMobPdnGyTableLastChanged indicates the sysUpTime at
         the time of the last modification to tmnxMobPdnGyTable by
         adding, deleting an entry or change to a writable object in the table.

         If no changes were made to the table since the last re-initialization
         of the local network management subsystem, then this object contains
         a zero value."
    ::= { tmnxMobPdnGlobalObjs 21 }

tmnxMobPdnGyTable  OBJECT-TYPE
    SYNTAX      SEQUENCE OF TmnxMobPdnGyEntry
    MAX-ACCESS  not-accessible
    STATUS      current
    DESCRIPTION
        "The tmnxMobPdnGyTable provides an extension of the tmnxMobPdnTable
         for Online Charging (Gy) interface configuration."
    ::= { tmnxMobPdnConfObjs 20 }

tmnxMobPdnGyEntry  OBJECT-TYPE
    SYNTAX      TmnxMobPdnGyEntry
    MAX-ACCESS  not-accessible
    STATUS      current
    DESCRIPTION
        "Each row entry represents additional columns for Online Charging (Gy)
         interface configuration for the Packet Data Network Gateway (PGW)."
    AUGMENTS { tmnxMobPdnEntry }
    ::= { tmnxMobPdnGyTable 1 }

TmnxMobPdnGyEntry ::= SEQUENCE {
        tmnxMobPdnGyLastChanged             TimeStamp,
        tmnxMobPdnGyVRtrId                  TmnxVRtrID,
        tmnxMobPdnGyIfIndex                 InterfaceIndexOrZero,
        tmnxMobPdnGyPriDiaPeer              TmnxMobProfNameOrEmpty,
        tmnxMobPdnGySecDiaPeer              TmnxMobProfNameOrEmpty,
        tmnxMobPdnGyDccaProf                TmnxMobProfNameOrEmpty,
        tmnxMobPdnGyDiaSession              INTEGER,
        tmnxMobPdnGyOcsSelIdType            INTEGER,
        tmnxMobPdnGyOcsSelIdMappingStyle    INTEGER
    }

tmnxMobPdnGyLastChanged  OBJECT-TYPE
    SYNTAX      TimeStamp
    MAX-ACCESS  read-only
    STATUS      current
    DESCRIPTION
        "The value of tmnxMobPdnGyLastChanged indicates the timestamp of
         the last change to this row in tmnxMobPdnGyTable."
    ::= { tmnxMobPdnGyEntry 1 }

tmnxMobPdnGyVRtrId  OBJECT-TYPE
    SYNTAX      TmnxVRtrID
    MAX-ACCESS  read-write
    STATUS      current
    DESCRIPTION
        "The value of tmnxMobPdnGyVRtrId specifies the virtual
         router to which the interface specified by tmnxMobPdnGyVRtrId
         belongs."
    DEFVAL { 1 }
    ::= { tmnxMobPdnGyEntry 2 }

tmnxMobPdnGyIfIndex  OBJECT-TYPE
    SYNTAX      InterfaceIndexOrZero
    MAX-ACCESS  read-write
    STATUS      current
    DESCRIPTION
        "The value of tmnxMobPdnGyIfIndex specifies the interface index of
         the local interface used by diameter applications."
    DEFVAL { 0 }
    ::= { tmnxMobPdnGyEntry 3 }

tmnxMobPdnGyPriDiaPeer  OBJECT-TYPE
    SYNTAX      TmnxMobProfNameOrEmpty
    MAX-ACCESS  read-write
    STATUS      current
    DESCRIPTION
        "The value of tmnxMobPdnGyPriDiaPeer specifies the diameter peer 
         profile to be used for the primary Online Charging System (OCS) at the 
         Gateway level.

         If a corresponding diameter peer profile does not exist in
         TIMETRA-MOBILE-PROFILE-MIB::tmnxMobProfDiaPeerTable,
         an 'inconsistentValue' error will be returned."
    DEFVAL { ''H }
    ::= { tmnxMobPdnGyEntry 4 }

tmnxMobPdnGySecDiaPeer  OBJECT-TYPE
    SYNTAX      TmnxMobProfNameOrEmpty
    MAX-ACCESS  read-write
    STATUS      current
    DESCRIPTION
        "The value of tmnxMobPdnGySecDiaPeer specifies the diameter peer 
         profile to be used for the secondary Online Charging System (OCS) at
         the Gateway level.

         If a corresponding diameter peer profile does not exist in
         TIMETRA-MOBILE-PROFILE-MIB::tmnxMobProfDiaPeerTable,
         an 'inconsistentValue' error will be returned."
    DEFVAL { ''H }
    ::= { tmnxMobPdnGyEntry 5 }

tmnxMobPdnGyDccaProf  OBJECT-TYPE
    SYNTAX      TmnxMobProfNameOrEmpty
    MAX-ACCESS  read-write
    STATUS      current
    DESCRIPTION
        "The value of tmnxMobPdnGyDccaProf specifies the Diameter Credit Control
         Application (DCCA) profile used for the primary and secondary 
         Online Charging System (OCS) at the Gateway level."
    DEFVAL { ''H }
    ::= { tmnxMobPdnGyEntry 6 }

tmnxMobPdnGyDiaSession OBJECT-TYPE
    SYNTAX      INTEGER {
                    pdnLevel      (1),
                    bearerLevel   (2)
                }
    MAX-ACCESS  read-write
    STATUS      current
    DESCRIPTION
        "The value of tmnxMobPdnGyDiaSession specifies whether the diameter
         credit control charging sessions to the Online Charging System (OCS)
         peer are set up on a per IP-CAN session basis or on a per bearer
         basis."
    DEFVAL { bearerLevel }
    ::= { tmnxMobPdnGyEntry 7 }

tmnxMobPdnGyOcsSelIdType OBJECT-TYPE
    SYNTAX      INTEGER {
                    none    (0),
                    imsi    (1),
                    msisdn  (2)
                }
    MAX-ACCESS  read-write
    STATUS      current
    DESCRIPTION
        "The value of tmnxMobPdnGyOcsSelIdType specifies whether the Online
         Charging System (OCS) selection criteria is based on the International
         Mobile Subscriber Identity (IMSI) or the Mobile Subscriber Integrated
         Services Digital Network (MSISDN)."
    DEFVAL { none }
    ::= { tmnxMobPdnGyEntry 8 }

tmnxMobPdnGyOcsSelIdMappingStyle OBJECT-TYPE
    SYNTAX      INTEGER {
                    none    (0),
                    prefix  (1),
                    fullId  (2)
                }
    MAX-ACCESS  read-write
    STATUS      current
    DESCRIPTION
        "The value of tmnxMobPdnGyOcsSelIdMappingStyle specifies whether the 
         Online Charging System (OCS) selection criteria mapping style is based
         on a full identifier or prefix."
    DEFVAL { none }
    ::= { tmnxMobPdnGyEntry 9 }

--
--  Gy Rating Group table
--

tmnxMobPdnRatingGrpTableLastChgd  OBJECT-TYPE
    SYNTAX      TimeStamp
    MAX-ACCESS  read-only
    STATUS      current
    DESCRIPTION
        "The value of tmnxMobPdnRatingGrpTableLastChgd indicates the sysUpTime
         at the time of the last modification to tmnxMobPdnRatingGrpTable by
         adding, deleting an entry or change to a writable object in the table.

         If no changes were made to the table since the last re-initialization
         of the local network management subsystem, then this object contains
         a zero value."
    ::= { tmnxMobPdnGlobalObjs 22 }

tmnxMobPdnRatingGrpTable  OBJECT-TYPE
    SYNTAX      SEQUENCE OF TmnxMobPdnRatingGrpEntry
    MAX-ACCESS  not-accessible
    STATUS      current
    DESCRIPTION
        "The tmnxMobPdnRatingGrpTable has an entry for each Rating Group
         configured for Online Charging (Gy) interface configuration."
    ::= { tmnxMobPdnConfObjs 21 }

tmnxMobPdnRatingGrpEntry  OBJECT-TYPE
    SYNTAX      TmnxMobPdnRatingGrpEntry
    MAX-ACCESS  not-accessible
    STATUS      current
    DESCRIPTION
        "Each row entry represents additional columns for Online Charging (Gy)
         Rating Group configuration for the Packet Data Network Gateway (PGW)."
    INDEX { tmnxMobGwId,
            tmnxMobPdnGyRatingGroupId
          }
    ::= { tmnxMobPdnRatingGrpTable 1 }

TmnxMobPdnRatingGrpEntry ::= SEQUENCE {
        tmnxMobPdnGyRatingGroupId           Unsigned32,
        tmnxMobPdnRatingGrpRowStatus        RowStatus,
        tmnxMobPdnRatingGrpLastChanged      TimeStamp,
        tmnxMobPdnRatingGrpActvtThresold    Unsigned32
    }

tmnxMobPdnGyRatingGroupId  OBJECT-TYPE
    SYNTAX      Unsigned32 (0..4294967295)
    MAX-ACCESS  not-accessible
    STATUS      current
    DESCRIPTION
        "The value of tmnxMobPdnGyRatingGroupId specifies the Rating-Group 
         associated with the system."
    ::= { tmnxMobPdnRatingGrpEntry 1 }

tmnxMobPdnRatingGrpRowStatus  OBJECT-TYPE
    SYNTAX      RowStatus
    MAX-ACCESS  read-create
    STATUS      current
    DESCRIPTION
        "The value of tmnxMobPdnRatingGrpRowStatus specifies the row status
         of this entry. It is used for creation and deletion of this Rating 
         Group entry.

         In order for the row creation to succeed, values for 
         tmnxMobPdnRatingGrpActvtThresold must be included in the same SNMP
         SET PDU as tmnxMobPdnRatingGrpRowStatus. Otherwise,
         the SET request will fail with an 'inconsistentValue' error."
    ::= { tmnxMobPdnRatingGrpEntry 2 }

tmnxMobPdnRatingGrpLastChanged  OBJECT-TYPE
    SYNTAX      TimeStamp
    MAX-ACCESS  read-only
    STATUS      current
    DESCRIPTION
        "The value of tmnxMobPdnGyLastChanged indicates the timestamp of
         the last change to this row in tmnxMobPdnRatingGrpTable."
    ::= { tmnxMobPdnRatingGrpEntry 3 }

tmnxMobPdnRatingGrpActvtThresold  OBJECT-TYPE
    SYNTAX      Unsigned32 (0..100000000)
    UNITS       "kbps"
    MAX-ACCESS  read-create
    STATUS      current
    DESCRIPTION
        "The value of tmnxMobPdnRatingGrpActvtThresold specifies the activity  
         thresold for time based metering. 
         
         The value must be specified at the time of row creation."
    ::= { tmnxMobPdnRatingGrpEntry 4 }

--
--  Gn Stats Table
--

tmnxMobPdnGnStatTable  OBJECT-TYPE
    SYNTAX      SEQUENCE OF TmnxMobPdnGnStatEntry
    MAX-ACCESS  not-accessible
    STATUS      current
    DESCRIPTION
        "The tmnxMobPdnGnStatTable has an entry for each peer on the Gn
         reference point."
    ::= { tmnxMobPdnStatObjs 10 }

tmnxMobPdnGnStatEntry  OBJECT-TYPE
    SYNTAX      TmnxMobPdnGnStatEntry
    MAX-ACCESS  not-accessible
    STATUS      current
    DESCRIPTION
        "Each row entry represents a peer on the Gn reference point
         and contains statistics for this peer on a card."
    INDEX { vRtrID,
            tmnxMobPdnGnPeerAddressType,
            tmnxMobPdnGnPeerAddress,
            tmnxMobPdnGnPeerPort,
            tmnxChassisIndex,
            tmnxCardSlotNum
          }
    ::= { tmnxMobPdnGnStatTable 1 }

TmnxMobPdnGnStatEntry ::= SEQUENCE {
        tmnxMobPdnGnStatCreatePdpReq       Counter32,
        tmnxMobPdnGnStatCreatePdpRsp       Counter32,
        tmnxMobPdnGnStatDeletePdpReq       Counter32,
        tmnxMobPdnGnStatDeletePdpRsp       Counter32,
        tmnxMobPdnGnStatModifyPdpReq       Counter32,
        tmnxMobPdnGnStatModifyPdpRsp       Counter32,
        tmnxMobPdnGnStatRxEchoRequests     Counter32,
        tmnxMobPdnGnStatTxEchoResponses    Counter32,
        tmnxMobPdnGnStatTxEchoRequests     Counter32,
        tmnxMobPdnGnStatRxEchoResponses    Counter32,
        tmnxMobPdnGnStatRxErrorsIndCnt     Counter32,
        tmnxMobPdnGnStatTxErrorsIndCnt     Counter32,
        tmnxMobPdnGnStatRxMalformedPkts    Counter32,
        tmnxMobPdnGnStatRxUnknownPkts      Counter32,
        tmnxMobPdnGnStatRxMissingIePkts    Counter32,
        tmnxMobPdnGnStatPeerRestarts       Counter32,
        tmnxMobPdnGnStatPeerRestrtCount    Counter32,
        tmnxMobPdnGnStatPathMgmtFails      Counter32        
    }
tmnxMobPdnGnStatCreatePdpReq  OBJECT-TYPE
    SYNTAX      Counter32
    MAX-ACCESS  read-only
    STATUS      current
    DESCRIPTION
        "The value of tmnxMobPdnGnStatCreatePdpReq indicates the number of
         create Packet Data Protocol (PDP) request messages received from this
         peer or transmitted to this peer."
    ::= { tmnxMobPdnGnStatEntry 1 }

tmnxMobPdnGnStatCreatePdpRsp  OBJECT-TYPE
    SYNTAX      Counter32
    MAX-ACCESS  read-only
    STATUS      current
    DESCRIPTION
        "The value of tmnxMobPdnGnStatCreatePdpRsp indicates the number of
         create Packet Data Protocol (PDP) response messages received from this
         peer or transmitted to this peer."
    ::= { tmnxMobPdnGnStatEntry 2 }

tmnxMobPdnGnStatDeletePdpReq  OBJECT-TYPE
    SYNTAX      Counter32
    MAX-ACCESS  read-only
    STATUS      current
    DESCRIPTION
        "The value of tmnxMobPdnGnStatDeletePdpReq indicates the number of
         delete Packet Data Protocol (PDP) request messages received from this
         peer or transmitted to this peer."
    ::= { tmnxMobPdnGnStatEntry 3 }

tmnxMobPdnGnStatDeletePdpRsp  OBJECT-TYPE
    SYNTAX      Counter32
    MAX-ACCESS  read-only
    STATUS      current
    DESCRIPTION
        "The value of tmnxMobPdnGnStatDeletePdpRsp indicates the number of
         delete Packet Data Protocol (PDP) response messages received from this
         peer or transmitted to this peer."
    ::= { tmnxMobPdnGnStatEntry 4 }

tmnxMobPdnGnStatModifyPdpReq  OBJECT-TYPE
    SYNTAX      Counter32
    MAX-ACCESS  read-only
    STATUS      current
    DESCRIPTION
        "The value of tmnxMobPdnGnStatModifyPdpReq indicates the number of
         modify Packet Data Protocol (PDP) request messages received from this
         peer or transmitted to this peer."
    ::= { tmnxMobPdnGnStatEntry 5 }

tmnxMobPdnGnStatModifyPdpRsp  OBJECT-TYPE
    SYNTAX      Counter32
    MAX-ACCESS  read-only
    STATUS      current
    DESCRIPTION
        "The value of tmnxMobPdnGnStatModifyPdpRsp indicates the number of
         modify Packet Data Protocol (PDP) response messages received from this
         peer or transmitted to this peer."
    ::= { tmnxMobPdnGnStatEntry 6 }

tmnxMobPdnGnStatRxEchoRequests  OBJECT-TYPE
    SYNTAX      Counter32
    MAX-ACCESS  read-only
    STATUS      current
    DESCRIPTION
        "The value of tmnxMobPdnGnStatRxEchoRequests indicates the number of
         echo request messages received from this peer."
    ::= { tmnxMobPdnGnStatEntry 7 }

tmnxMobPdnGnStatTxEchoResponses  OBJECT-TYPE
    SYNTAX      Counter32
    MAX-ACCESS  read-only
    STATUS      current
    DESCRIPTION
        "The value of tmnxMobPdnGnStatTxEchoResponses indicates the number of
         echo response messages transmitted to this peer."
    ::= { tmnxMobPdnGnStatEntry 8 }

tmnxMobPdnGnStatTxEchoRequests  OBJECT-TYPE
    SYNTAX      Counter32
    MAX-ACCESS  read-only
    STATUS      current
    DESCRIPTION
        "The value of tmnxMobPdnGnStatTxEchoRequests indicates the number of
         echo request messages transmitted to this peer."
    ::= { tmnxMobPdnGnStatEntry 9 }

tmnxMobPdnGnStatRxEchoResponses  OBJECT-TYPE
    SYNTAX      Counter32
    MAX-ACCESS  read-only
    STATUS      current
    DESCRIPTION
        "The value of tmnxMobPdnGnStatRxEchoResponses indicates the number of
         echo response messages received from this peer."
    ::= { tmnxMobPdnGnStatEntry 10 }

tmnxMobPdnGnStatRxErrorsIndCnt  OBJECT-TYPE
    SYNTAX      Counter32
    MAX-ACCESS  read-only
    STATUS      current
    DESCRIPTION
        "The value of tmnxMobPdnGnStatRxErrorsIndCnt indicates the number of
         indication request errors transmitted to this peer."
    ::= { tmnxMobPdnGnStatEntry 11 }

tmnxMobPdnGnStatTxErrorsIndCnt  OBJECT-TYPE
    SYNTAX      Counter32
    MAX-ACCESS  read-only
    STATUS      current
    DESCRIPTION
        "The value of tmnxMobPdnGnStatTxErrorsIndCnt indicates the number of
         indication response errors received from this peer."
    ::= { tmnxMobPdnGnStatEntry 12 }

tmnxMobPdnGnStatRxMalformedPkts  OBJECT-TYPE
    SYNTAX      Counter32
    MAX-ACCESS  read-only
    STATUS      current
    DESCRIPTION
        "The value of tmnxMobPdnGnStatRxMalformedPkts indicates the number of
         malformed packets received from this peer."
    ::= { tmnxMobPdnGnStatEntry 13 }

tmnxMobPdnGnStatRxUnknownPkts  OBJECT-TYPE
    SYNTAX      Counter32
    MAX-ACCESS  read-only
    STATUS      current
    DESCRIPTION
        "The value of tmnxMobPdnGnStatRxUnknownPkts indicates the number of
         unknown message type packets received from this peer."
    ::= { tmnxMobPdnGnStatEntry 14 }

tmnxMobPdnGnStatRxMissingIePkts  OBJECT-TYPE
    SYNTAX      Counter32
    MAX-ACCESS  read-only
    STATUS      current
    DESCRIPTION
        "The value of tmnxMobPdnGnStatRxMissingIePkts indicates the number of
         missing mandatory Information Element (IE) packets received from this
         peer."
    ::= { tmnxMobPdnGnStatEntry 15 }

tmnxMobPdnGnStatPeerRestarts  OBJECT-TYPE
    SYNTAX      Counter32
    MAX-ACCESS  read-only
    STATUS      current
    DESCRIPTION
        "The value of tmnxMobPdnGnStatPeerRestarts indicates the number of
         times this peer restarted after registering with the system."
    ::= { tmnxMobPdnGnStatEntry 16 }

tmnxMobPdnGnStatPeerRestrtCount  OBJECT-TYPE
    SYNTAX      Counter32
    MAX-ACCESS  read-only
    STATUS      current
    DESCRIPTION
        "The value of tmnxMobPdnGnStatPeerRestrtCount indicates the counter
         value of the number of times this peer restarted."
    ::= { tmnxMobPdnGnStatEntry 17 }

tmnxMobPdnGnStatPathMgmtFails  OBJECT-TYPE
    SYNTAX      Counter32
    MAX-ACCESS  read-only
    STATUS      current
    DESCRIPTION
        "The value of tmnxMobPdnGnStatPathMgmtFails indicates the number of
         path management failures for this peer."
    ::= { tmnxMobPdnGnStatEntry 18 }

--
--  Ga Stats Table
--

tmnxMobPdnGaStatTable  OBJECT-TYPE
    SYNTAX      SEQUENCE OF TmnxMobPdnGaStatEntry
    MAX-ACCESS  not-accessible
    STATUS      current
    DESCRIPTION
        "The tmnxMobPdnGaStatTable has an entry for each peer on the Ga
         reference point served by a Packet Data Network Gateway (PGW)."
    ::= { tmnxMobPdnStatObjs 11 }

tmnxMobPdnGaStatEntry  OBJECT-TYPE
    SYNTAX      TmnxMobPdnGaStatEntry
    MAX-ACCESS  not-accessible
    STATUS      current
    DESCRIPTION
        "Each row entry represents a peer on the Ga reference point and
         contain statistics for this peer on a card."
    INDEX { tmnxMobGwId,
            vRtrID,
            tmnxMobGtpPriGrpName,
            tmnxMobGtpPriServerIndex,
            tmnxMobPdnGaStatAddressType,
            tmnxMobPdnGaStatAddress,
            tmnxMobPdnGaStatPort,
            tmnxChassisIndex,
            tmnxCardSlotNum
          }
    ::= { tmnxMobPdnGaStatTable 1 }

TmnxMobPdnGaStatEntry ::= SEQUENCE {
        tmnxMobPdnGaStatAddressType         InetAddressType,
        tmnxMobPdnGaStatAddress             InetAddress,
        tmnxMobPdnGaStatPort                InetPortNumber,
        tmnxMobPdnGaStatLastChanged         TimeStamp,
        tmnxMobPdnGaStatCreateTime          TimeStamp,
        tmnxMobPdnGaStatRxEchoRequests      Counter32,
        tmnxMobPdnGaStatTxEchoResponses     Counter32,
        tmnxMobPdnGaStatTxEchoRequests      Counter32,
        tmnxMobPdnGaStatRxEchoResponses     Counter32,
        tmnxMobPdnGaStatRxNodeAlRequests    Counter32,
        tmnxMobPdnGaStatTxNodeAlResps       Counter32,
        tmnxMobPdnGaStatTxDataRecReqs       Counter32,
        tmnxMobPdnGaStatTxDataRecTferReq    Counter32,
        tmnxMobPdnGaStatRetrDataRecReqs     Counter32,
        tmnxMobPdnGaStatRxDataRecReqs       Counter32,
        tmnxMobPdnGaStatUnackDataRexReqs    Counter32,
        tmnxMobPdnGaStatRxRedirectionReq    Counter32,
        tmnxMobPdnGaStatTxRedrnResp         Counter32,
        tmnxMobPdnGaStatRxInvalidMsgs       Counter32,
        tmnxMobPdnGaStatRxVerNotSupp        Counter32,            
        tmnxMobPdnGaStatTxCdrTermination    Counter32,
        tmnxMobPdnGaStatTxCdrMaxChngCond    Counter32,
        tmnxMobPdnGaStatTxCdrMsTmzChng      Counter32,
        tmnxMobPdnGaStatTxCdrRatChng        Counter32,
        tmnxMobPdnGaStatTxCdrTimeLimit      Counter32,
        tmnxMobPdnGaStatTxCdrVolLimit       Counter32,        
        tmnxMobPdnGaStatRxCdrReqAcc         Counter32,
        tmnxMobPdnGaStatRxCdrNoResAva       Counter32,
        tmnxMobPdnGaStatRxCdrReqNotFf       Counter32,
        tmnxMobPdnGaStatRxCdrReqFfilled     Counter32,
        tmnxMobPdnGaStatRxCdrDupReqFf       Counter32,
        tmnxMobPdnGaStatRxCdrInvMsgFmat     Counter32,
        tmnxMobPdnGaStatRxCdrVerNotSupp     Counter32,
        tmnxMobPdnGaStatRxCdrSrvcNotSupp    Counter32,
        tmnxMobPdnGaStatRxCdrMandIeInc      Counter32,
        tmnxMobPdnGaStatRxCdrMandIeMiss     Counter32,
        tmnxMobPdnGaStatRxCdrOptIeInc       Counter32,
        tmnxMobPdnGaStatRxCdrSystemFail     Counter32,
        tmnxMobPdnGaStatRtrEchoRequests     Counter32,
        tmnxMobPdnGaStatGtpPrimeFail        Counter32,
        tmnxMobPdnGaStatOperState           INTEGER,
        tmnxMobPdnGaStatUpTime              TimeStamp,
        tmnxMobPdnGaStatTxNodeAlRequests    Counter32,
        tmnxMobPdnGaStatRxNodeAlResps       Counter32,
        tmnxMobPdnGaStatNodeAlReqRetried    Counter32,
        tmnxMobPdnGaStatCdrsTx              Counter32,
        tmnxMobPdnGaStatCdrsRx              Counter32,
        tmnxMobPdnGaStatTxCdrPlmnChange     Counter32,
        tmnxMobPdnGaStatTxCdrSerNdChLmt     Counter32,
        tmnxMobPdnGaStatTxVerNotSupp        Counter32,
        tmnxMobPdnGaStatTxCdrMgmtInterv     Counter32
    }

tmnxMobPdnGaStatAddressType  OBJECT-TYPE
    SYNTAX      InetAddressType
    MAX-ACCESS  not-accessible
    STATUS      current
    DESCRIPTION
        "The value of tmnxMobPdnGaStatAddressType indicates the type of
         address represented by tmnxMobPdnGaStatAddress.

         When the value of tmnxMobPdnGaStatAddressType is unknown then the peer 
         is a Fully Qualified Domain Name (FQDN) address and this entry 
         represents an aggregate of all the peer IP addresses that this FQDN 
         resolves to."
    ::= { tmnxMobPdnGaStatEntry 1 }

tmnxMobPdnGaStatAddress  OBJECT-TYPE
    SYNTAX      InetAddress (SIZE (0|4|16))
    MAX-ACCESS  not-accessible
    STATUS      current
    DESCRIPTION
        "The value of tmnxMobPdnGaStatAddress indicates the IP address of the
         peer on Ga reference point.

         When the length of tmnxMobPdnGaStatAddress is equal to 0 then the peer 
         is a Fully Qualified Domain Name (FQDN) address and this entry 
         represents an aggregate of all the peer IP addresses that this FQDN 
         resolves to. In this case the value of tmnxMobPdnGaStatAddressType is 
         unknown and the value of tmnxMobPdnGaStatPort is equal to 0."
    ::= { tmnxMobPdnGaStatEntry 2 }

tmnxMobPdnGaStatPort  OBJECT-TYPE
    SYNTAX      InetPortNumber
    MAX-ACCESS  not-accessible
    STATUS      current
    DESCRIPTION
        "The value of tmnxMobPdnGaStatPort indicates the port number of this
         peer.

         When the value of tmnxMobPdnGaStatPort is equal to 0 then the peer is 
         a Fully Qualified Domain Name (FQDN) address and this entry represents 
         an aggregate of all the peer IP addresses that this FQDN resolves to."
    ::= { tmnxMobPdnGaStatEntry 3 }

tmnxMobPdnGaStatLastChanged  OBJECT-TYPE
    SYNTAX      TimeStamp
    MAX-ACCESS  read-only
    STATUS      current
    DESCRIPTION
        "The value of tmnxMobPdnGaStatLastChanged indicates the timestamp of
         the last change to this row in tmnxMobPdnGaStatTable."
    ::= { tmnxMobPdnGaStatEntry 4 }

tmnxMobPdnGaStatCreateTime  OBJECT-TYPE
    SYNTAX      TimeStamp
    MAX-ACCESS  read-only
    STATUS      current
    DESCRIPTION
        "The value of tmnxMobPdnGaStatCreateTime indicates the sysUpTime when
         this entry was created."
    ::= { tmnxMobPdnGaStatEntry 5 }

tmnxMobPdnGaStatRxEchoRequests  OBJECT-TYPE
    SYNTAX      Counter32
    MAX-ACCESS  read-only
    STATUS      current
    DESCRIPTION
        "The value of tmnxMobPdnGaStatRxEchoRequests indicates the number of
         echo request messages received from this peer."
    ::= { tmnxMobPdnGaStatEntry 6 }

tmnxMobPdnGaStatTxEchoResponses  OBJECT-TYPE
    SYNTAX      Counter32
    MAX-ACCESS  read-only
    STATUS      current
    DESCRIPTION
        "The value of tmnxMobPdnGaStatTxEchoResponses indicates the number of
         echo response messages transmitted to this peer."
    ::= { tmnxMobPdnGaStatEntry 7 }

tmnxMobPdnGaStatTxEchoRequests  OBJECT-TYPE
    SYNTAX      Counter32
    MAX-ACCESS  read-only
    STATUS      current
    DESCRIPTION
        "The value of tmnxMobPdnGaStatTxEchoRequests indicates the number of
         echo request messages transmitted to this peer."
    ::= { tmnxMobPdnGaStatEntry 8 }

tmnxMobPdnGaStatRxEchoResponses  OBJECT-TYPE
    SYNTAX      Counter32
    MAX-ACCESS  read-only
    STATUS      current
    DESCRIPTION
        "The value of tmnxMobPdnGaStatRxEchoResponses indicates the number of
         echo response messages received from this peer."
    ::= { tmnxMobPdnGaStatEntry 9 }

tmnxMobPdnGaStatRxNodeAlRequests  OBJECT-TYPE
    SYNTAX      Counter32
    MAX-ACCESS  read-only
    STATUS      current
    DESCRIPTION
        "The value of tmnxMobPdnGaStatRxNodeAlRequests indicates the number of
         node alive request messages received from this peer."
    ::= { tmnxMobPdnGaStatEntry 10 }

tmnxMobPdnGaStatTxNodeAlResps  OBJECT-TYPE
    SYNTAX      Counter32
    MAX-ACCESS  read-only
    STATUS      current
    DESCRIPTION
        "The value of tmnxMobPdnGaStatTxNodeAlResps indicates the number of
         node alive response messages transmitted to this peer."
    ::= { tmnxMobPdnGaStatEntry 11 }

tmnxMobPdnGaStatTxDataRecReqs  OBJECT-TYPE
    SYNTAX      Counter32
    MAX-ACCESS  read-only
    STATUS      current
    DESCRIPTION
        "The value of tmnxMobPdnGaStatTxDataRecReqs indicates the number of
         Data record requests transmitted to this peer."
    ::= { tmnxMobPdnGaStatEntry 12 }

tmnxMobPdnGaStatTxDataRecTferReq  OBJECT-TYPE
    SYNTAX      Counter32
    MAX-ACCESS  read-only
    STATUS      current
    DESCRIPTION
        "The value of tmnxMobPdnGaStatTxDataRecTferReq indicates the number of
         duplicate Data record transfer requests transmitted to this peer."
    ::= { tmnxMobPdnGaStatEntry 13 }

tmnxMobPdnGaStatRetrDataRecReqs  OBJECT-TYPE
    SYNTAX      Counter32
    MAX-ACCESS  read-only
    STATUS      current
    DESCRIPTION
        "The value of tmnxMobPdnGaStatRetrDataRecReqs indicates the number 
        of Data record transfer requests retried to this peer."
    ::= { tmnxMobPdnGaStatEntry 14 }

tmnxMobPdnGaStatRxDataRecReqs  OBJECT-TYPE
    SYNTAX      Counter32
    MAX-ACCESS  read-only
    STATUS      current
    DESCRIPTION
        "The value of tmnxMobPdnGaStatRxDataRecReqs indicates the number of
         Data record transfer requests received by this peer."
    ::= { tmnxMobPdnGaStatEntry 15 }

tmnxMobPdnGaStatUnackDataRexReqs  OBJECT-TYPE
    SYNTAX      Counter32
    MAX-ACCESS  read-only
    STATUS      current
    DESCRIPTION
        "The value of tmnxMobPdnGaStatUnackDataRexReqs indicates the number of
         Data record transfer requests unacknowledged by this peer."
    ::= { tmnxMobPdnGaStatEntry 16 }

tmnxMobPdnGaStatRxRedirectionReq  OBJECT-TYPE
    SYNTAX      Counter32
    MAX-ACCESS  read-only
    STATUS      current
    DESCRIPTION
        "The value of tmnxMobPdnGaStatRxRedirectionReq indicates the number of
         redirection request messages received from this peer."
    ::= { tmnxMobPdnGaStatEntry 17 }

tmnxMobPdnGaStatTxRedrnResp  OBJECT-TYPE
    SYNTAX      Counter32
    MAX-ACCESS  read-only
    STATUS      current
    DESCRIPTION
        "The value of tmnxMobPdnGaStatTxRedrnResp indicates the number of
         redirection request messages transmitted to this peer."
    ::= { tmnxMobPdnGaStatEntry 18 }

tmnxMobPdnGaStatRxInvalidMsgs  OBJECT-TYPE
    SYNTAX      Counter32
    MAX-ACCESS  read-only
    STATUS      current
    DESCRIPTION
        "The value of tmnxMobPdnGaStatRxInvalidMsgs indicates the number of
         invalid messages received from this peer."
    ::= { tmnxMobPdnGaStatEntry 19 }

tmnxMobPdnGaStatRxVerNotSupp  OBJECT-TYPE
    SYNTAX      Counter32
    MAX-ACCESS  read-only
    STATUS      current
    DESCRIPTION
        "The value of tmnxMobPdnGaStatRxVerNotSupp indicates the number of
         version not supported messages received from this peer."
    ::= { tmnxMobPdnGaStatEntry 20 }

tmnxMobPdnGaStatTxCdrTermination  OBJECT-TYPE
    SYNTAX      Counter32
    MAX-ACCESS  read-only
    STATUS      current
    DESCRIPTION
        "The value of tmnxMobPdnGaStatTxCdrTermination indicates the number of
         Charging Data Records (CDR) termination requests transmitted to this
         peer."
    ::= { tmnxMobPdnGaStatEntry 21 }

tmnxMobPdnGaStatTxCdrMaxChngCond  OBJECT-TYPE
    SYNTAX      Counter32
    MAX-ACCESS  read-only
    STATUS      current
    DESCRIPTION
        "The value of tmnxMobPdnGaStatTxCdrMaxChngCond indicates the number of
         Charging Data Records (CDR) maximum change condition requests 
         transmitted to this peer."
    ::= { tmnxMobPdnGaStatEntry 22 }

tmnxMobPdnGaStatTxCdrMsTmzChng  OBJECT-TYPE
    SYNTAX      Counter32
    MAX-ACCESS  read-only
    STATUS      current
    DESCRIPTION
        "The value of tmnxMobPdnGaStatTxCdrMsTmzChng indicates the number 
        of Charging Data Records (CDR) MS Time Zone Change requests transmitted 
        to this peer."
    ::= { tmnxMobPdnGaStatEntry 23 }

tmnxMobPdnGaStatTxCdrRatChng  OBJECT-TYPE
    SYNTAX      Counter32
    MAX-ACCESS  read-only
    STATUS      current
    DESCRIPTION
        "The value of tmnxMobPdnGaStatTxCdrRatChng indicates the number of
         Charging Data Records (CDR) Radio Access Type (RAT) change requests 
         transmitted to this peer."
    ::= { tmnxMobPdnGaStatEntry 24 }

tmnxMobPdnGaStatTxCdrTimeLimit  OBJECT-TYPE
    SYNTAX      Counter32
    MAX-ACCESS  read-only
    STATUS      current
    DESCRIPTION
        "The value of tmnxMobPdnGaStatTxCdrTimeLimit indicates the number of
         Charging Data Records (CDR) time limit requests transmitted to this
         peer."
    ::= { tmnxMobPdnGaStatEntry 25 }

tmnxMobPdnGaStatTxCdrVolLimit  OBJECT-TYPE
    SYNTAX      Counter32
    MAX-ACCESS  read-only
    STATUS      current
    DESCRIPTION
        "The value of tmnxMobPdnGaStatTxCdrVolLimit indicates the number of
         Charging Data Records (CDR) volume limit requests transmitted to this
         peer."
    ::= { tmnxMobPdnGaStatEntry 26 }

tmnxMobPdnGaStatRxCdrReqAcc  OBJECT-TYPE
    SYNTAX      Counter32
    MAX-ACCESS  read-only
    STATUS      current
    DESCRIPTION
        "The value of tmnxMobPdnGaStatRxCdrReqAcc indicates the number of
         Charging Data Records (CDR) responses with cause value 'requests 
         accepted' received from this peer."
    ::= { tmnxMobPdnGaStatEntry 27 }

tmnxMobPdnGaStatRxCdrNoResAva  OBJECT-TYPE
    SYNTAX      Counter32
    MAX-ACCESS  read-only
    STATUS      current
    DESCRIPTION
        "The value of tmnxMobPdnGaStatRxCdrNoResAva indicates the number of
         Charging Data Records (CDR) responses with cause value 'no resources 
         available' received from this peer."
    ::= { tmnxMobPdnGaStatEntry 28 }    

tmnxMobPdnGaStatRxCdrReqNotFf  OBJECT-TYPE
    SYNTAX      Counter32
    MAX-ACCESS  read-only
    STATUS      current
    DESCRIPTION
        "The value of tmnxMobPdnGaStatRxCdrReqNotFf indicates the number of
         Charging Data Records (CDR) responses with cause value 'requests not 
         fulfilled' received from this peer."
    ::= { tmnxMobPdnGaStatEntry 29 }     

tmnxMobPdnGaStatRxCdrReqFfilled  OBJECT-TYPE
    SYNTAX      Counter32
    MAX-ACCESS  read-only
    STATUS      current
    DESCRIPTION
        "The value of tmnxMobPdnGaStatRxCdrReqFfilled indicates the number of
         Charging Data Records (CDR) responses with cause value 'requests 
         already fulfilled' received from this peer."
    ::= { tmnxMobPdnGaStatEntry 30 }        

tmnxMobPdnGaStatRxCdrDupReqFf  OBJECT-TYPE
    SYNTAX      Counter32
    MAX-ACCESS  read-only
    STATUS      current
    DESCRIPTION
        "The value of tmnxMobPdnGaStatRxCdrDupReqFf indicates the number of
         Charging Data Records (CDR) responses with cause value 'duplicate 
         requests already fulfilled' received from this peer."
    ::= { tmnxMobPdnGaStatEntry 31 }     

tmnxMobPdnGaStatRxCdrInvMsgFmat  OBJECT-TYPE
    SYNTAX      Counter32
    MAX-ACCESS  read-only
    STATUS      current
    DESCRIPTION
        "The value of tmnxMobPdnGaStatRxCdrInvMsgFmat indicates the number of
         Charging Data Records (CDR) responses with cause value 'invalid message 
         format' received from this peer."
    ::= { tmnxMobPdnGaStatEntry 32 }   

tmnxMobPdnGaStatRxCdrVerNotSupp  OBJECT-TYPE
    SYNTAX      Counter32
    MAX-ACCESS  read-only
    STATUS      current
    DESCRIPTION
        "The value of tmnxMobPdnGaStatRxCdrVerNotSupp indicates the number of
         Charging Data Records (CDR) responses with cause value 'version not 
         supported' received from this peer."
    ::= { tmnxMobPdnGaStatEntry 33 }              

tmnxMobPdnGaStatRxCdrSrvcNotSupp  OBJECT-TYPE
    SYNTAX      Counter32
    MAX-ACCESS  read-only
    STATUS      current
    DESCRIPTION
        "The value of tmnxMobPdnGaStatRxCdrSrvcNotSupp indicates the number of
         Charging Data Records (CDR) responses with cause value 'service not 
         supported' received from this peer."
    ::= { tmnxMobPdnGaStatEntry 34 }         

tmnxMobPdnGaStatRxCdrMandIeInc  OBJECT-TYPE
    SYNTAX      Counter32
    MAX-ACCESS  read-only
    STATUS      current
    DESCRIPTION
        "The value of tmnxMobPdnGaStatRxCdrMandIeInc indicates the number of
         Charging Data Records (CDR) responses with cause value 'mandatory 
         Information Element (IE) incorrect' received from this peer."
    ::= { tmnxMobPdnGaStatEntry 35 }         

tmnxMobPdnGaStatRxCdrMandIeMiss  OBJECT-TYPE
    SYNTAX      Counter32
    MAX-ACCESS  read-only
    STATUS      current
    DESCRIPTION
        "The value of tmnxMobPdnGaStatRxCdrMandIeMiss indicates the number of
         Charging Data Records (CDR) responses with cause value 'mandatory 
         Information Element (IE) missing' received from this peer."
    ::= { tmnxMobPdnGaStatEntry 36 }         

tmnxMobPdnGaStatRxCdrOptIeInc  OBJECT-TYPE
    SYNTAX      Counter32
    MAX-ACCESS  read-only
    STATUS      current
    DESCRIPTION
        "The value of tmnxMobPdnGaStatRxCdrOptIeInc indicates the number of
         Charging Data Records (CDR) responses with cause value 'optional 
         Information Element (IE) incorrect' received from this peer."
    ::= { tmnxMobPdnGaStatEntry 37 }         

tmnxMobPdnGaStatRxCdrSystemFail  OBJECT-TYPE
    SYNTAX      Counter32
    MAX-ACCESS  read-only
    STATUS      current
    DESCRIPTION
        "The value of tmnxMobPdnGaStatRxCdrSystemFail indicates the number of
         Charging Data Records (CDR) responses with cause value 'system failure'
         received from this peer."
    ::= { tmnxMobPdnGaStatEntry 38 }                     

tmnxMobPdnGaStatRtrEchoRequests  OBJECT-TYPE
    SYNTAX      Counter32
    MAX-ACCESS  read-only
    STATUS      current
    DESCRIPTION
        "The value of tmnxMobPdnGaStatRtrEchoRequests indicates the number of
         echo request messages retried to this peer."
    ::= { tmnxMobPdnGaStatEntry 39 }


tmnxMobPdnGaStatGtpPrimeFail  OBJECT-TYPE
    SYNTAX      Counter32
    MAX-ACCESS  read-only
    STATUS      current
    DESCRIPTION
        "The value of tmnxMobPdnGaStatGtpPrimeFail indicates the number of
         GPRS Tunneling Protocol (GTP) prime message failures 
         transmitted to this peer."
    ::= { tmnxMobPdnGaStatEntry 40 }

tmnxMobPdnGaStatOperState OBJECT-TYPE
    SYNTAX      INTEGER {
                    up      (1),
                    down    (2),
                    active  (3)
                }
    MAX-ACCESS     read-only
    STATUS         current
    DESCRIPTION
        "The value of tmnxMobPdnGaStatOperState indicates the current
         operational state of this group. The operational state may be one of:
         'up'     - connection goes 'up' and is used by the Ga module to send 
                    Charging Data Records (CDRs).
         'down'   - connection goes 'down' and is used by the Ga module to send
                    Charging Data Records (CDRs).
         'active' - connection is 'active' and is used by the Ga module to send
                    Charging Data Records (CDRs)."
    ::= { tmnxMobPdnGaStatEntry 41 }

tmnxMobPdnGaStatUpTime OBJECT-TYPE
    SYNTAX      TimeStamp
    MAX-ACCESS  read-only
    STATUS      current
    DESCRIPTION
        "The value of tmnxMobPdnGaStatUpTime indicates the time when the
         connection comes up." 
    ::= { tmnxMobPdnGaStatEntry 42 }

tmnxMobPdnGaStatTxNodeAlRequests  OBJECT-TYPE
    SYNTAX      Counter32
    MAX-ACCESS  read-only
    STATUS      current
    DESCRIPTION
        "The value of tmnxMobPdnGaStatTxNodeAlRequests indicates the number of
         node alive request messages transmitted from this peer."
    ::= { tmnxMobPdnGaStatEntry 43 }

tmnxMobPdnGaStatRxNodeAlResps  OBJECT-TYPE
    SYNTAX      Counter32
    MAX-ACCESS  read-only
    STATUS      current
    DESCRIPTION
        "The value of tmnxMobPdnGaStatRxNodeAlResps indicates the number of
         node alive response messages received on this peer."
    ::= { tmnxMobPdnGaStatEntry 44 }

tmnxMobPdnGaStatNodeAlReqRetried  OBJECT-TYPE
    SYNTAX      Counter32
    MAX-ACCESS  read-only
    STATUS      current
    DESCRIPTION
        "The value of tmnxMobPdnGaStatNodeAlReqRetried indicates the number of
         node alive request retry messages transmitted from this peer."
    ::= { tmnxMobPdnGaStatEntry 45 }

tmnxMobPdnGaStatCdrsTx  OBJECT-TYPE
    SYNTAX      Counter32
    MAX-ACCESS  read-only
    STATUS      current
    DESCRIPTION
        "The value of tmnxMobPdnGaStatCdrsTx indicates the total number of
         Charging Data Records (CDR) sent from this peer."
    ::= { tmnxMobPdnGaStatEntry 46 }

tmnxMobPdnGaStatCdrsRx  OBJECT-TYPE
    SYNTAX      Counter32
    MAX-ACCESS  read-only
    STATUS      current
    DESCRIPTION
        "The value of tmnxMobPdnGaStatCdrsRx indicates the total number of
         Charging Data Records (CDR) received on this peer."
    ::= { tmnxMobPdnGaStatEntry 47 }

tmnxMobPdnGaStatTxCdrPlmnChange  OBJECT-TYPE
    SYNTAX      Counter32
    MAX-ACCESS  read-only
    STATUS      current
    DESCRIPTION
        "The value of tmnxMobPdnGaStatTxCdrPlmnChange indicates the number of
         Charging Data Records (CDR) Public Land Mobile Network (PLMN) change 
         requests transmitted to this peer."
    ::= { tmnxMobPdnGaStatEntry 48 }

tmnxMobPdnGaStatTxCdrSerNdChLmt  OBJECT-TYPE
    SYNTAX      Counter32
    MAX-ACCESS  read-only
    STATUS      current
    DESCRIPTION
        "The value of tmnxMobPdnGaStatTxCdrSerNdChLmt indicates the number of 
         Charging Data Records (CDR) Serving Node Change Limit requests 
         transmitted to this peer."
    ::= { tmnxMobPdnGaStatEntry 49 }

tmnxMobPdnGaStatTxVerNotSupp  OBJECT-TYPE
    SYNTAX      Counter32
    MAX-ACCESS  read-only
    STATUS      current
    DESCRIPTION
        "The value of tmnxMobPdnGaStatTxVerNotSupp indicates the number of
         version not supported messages transmitted to this peer."
    ::= { tmnxMobPdnGaStatEntry 50 }

tmnxMobPdnGaStatTxCdrMgmtInterv  OBJECT-TYPE
    SYNTAX      Counter32
    MAX-ACCESS  read-only
    STATUS      current
    DESCRIPTION
        "The value of tmnxMobPdnGaStatTxCdrMgmtInterv indicates the number of
         Charging Data Records (CDR) transferred due to management intervention
         on this peer."
    ::= { tmnxMobPdnGaStatEntry 51 }

--
--  Gy peer list Table
--

tmnxMobPdnGyPeerTableLastChngd     OBJECT-TYPE
    SYNTAX      TimeStamp
    MAX-ACCESS  read-only
    STATUS      current
    DESCRIPTION
        "The value of tmnxMobPdnGyPeerTableLastChngd indicates the sysUpTime
         at the time of the last modification to tmnxMobPdnGyPeerTable by
         adding, deleting an entry or change to a writable object in the table.

         If no changes were made to the table since the last re-initialization
         of the local network management subsystem, then this object contains
         a zero value."
    ::= { tmnxMobPdnGlobalObjs 23 }

tmnxMobPdnGyPeerTable  OBJECT-TYPE
    SYNTAX      SEQUENCE OF TmnxMobPdnGyPeerEntry
    MAX-ACCESS  not-accessible
    STATUS      current
    DESCRIPTION
        "The tmnxMobPdnGyPeerTable has an entry for each peer on the Gy
         reference point served by a Packet Data Network Gateway (PGW)."
    ::= { tmnxMobPdnStatObjs 12 }

tmnxMobPdnGyPeerEntry  OBJECT-TYPE
    SYNTAX      TmnxMobPdnGyPeerEntry
    MAX-ACCESS  not-accessible
    STATUS      current
    DESCRIPTION
        "Each row entry represents a peer on the Gy reference point."
    INDEX { tmnxMobGwId,
            vRtrID,
            tmnxMobProfDiaPeerName,
            tmnxMobProfDiaPeerListIndex,
            tmnxMobPdnGyPeerAddressType,
            tmnxMobPdnGyPeerAddress,
            tmnxMobPdnGyPeerPort
          }
    ::= { tmnxMobPdnGyPeerTable 1 }

TmnxMobPdnGyPeerEntry ::= SEQUENCE {
        tmnxMobPdnGyPeerAddressType       InetAddressType,
        tmnxMobPdnGyPeerAddress           InetAddress,
        tmnxMobPdnGyPeerPort              InetPortNumber,
        tmnxMobPdnGyPeerLastChanged       TimeStamp,
        tmnxMobPdnGyPeerCreateTime        TimeStamp,
        tmnxMobPdnGyPeerPathMgmtState     TmnxMobDiaPathMgmtState,
        tmnxMobPdnGyPeerDetailState       TmnxMobDiaDetailPathMgmtState
    }

tmnxMobPdnGyPeerAddressType  OBJECT-TYPE
    SYNTAX      InetAddressType
    MAX-ACCESS  not-accessible
    STATUS      current
    DESCRIPTION
        "The value of tmnxMobPdnGyPeerAddressType indicates the type of
         address represented by tmnxMobPdnGyPeerAddress."
    ::= { tmnxMobPdnGyPeerEntry 1 }

tmnxMobPdnGyPeerAddress  OBJECT-TYPE
    SYNTAX      InetAddress (SIZE (0|4|16))
    MAX-ACCESS  not-accessible
    STATUS      current
    DESCRIPTION
        "The value of tmnxMobPdnGyPeerAddress indicates the IP address of the
         peer on Gy reference point."
    ::= { tmnxMobPdnGyPeerEntry 2 }

tmnxMobPdnGyPeerPort  OBJECT-TYPE
    SYNTAX      InetPortNumber
    MAX-ACCESS  not-accessible
    STATUS      current
    DESCRIPTION
        "The value of tmnxMobPdnGyPeerPort indicates the port number of this
         peer."
    ::= { tmnxMobPdnGyPeerEntry 3 }

tmnxMobPdnGyPeerLastChanged  OBJECT-TYPE
    SYNTAX      TimeStamp
    MAX-ACCESS  read-only
    STATUS      current
    DESCRIPTION
        "The value of tmnxMobPdnGyPeerLastChanged indicates the timestamp of
         the last change to this row in tmnxMobPdnGyPeerTable."
    ::= { tmnxMobPdnGyPeerEntry 4 }

tmnxMobPdnGyPeerCreateTime  OBJECT-TYPE
    SYNTAX      TimeStamp
    MAX-ACCESS  read-only
    STATUS      current
    DESCRIPTION
        "The value of tmnxMobPdnGyPeerCreateTime indicates the sysUpTime when
         this entry was created."
    ::= { tmnxMobPdnGyPeerEntry 5 }

tmnxMobPdnGyPeerPathMgmtState  OBJECT-TYPE
    SYNTAX      TmnxMobDiaPathMgmtState
    MAX-ACCESS  read-only
    STATUS      current
    DESCRIPTION
        "The value of tmnxMobPdnGyPeerPathMgmtState indicates the state of
         the path."
    ::= { tmnxMobPdnGyPeerEntry 6 }

tmnxMobPdnGyPeerDetailState  OBJECT-TYPE
    SYNTAX      TmnxMobDiaDetailPathMgmtState
    MAX-ACCESS  read-only
    STATUS      current
    DESCRIPTION
        "The value of tmnxMobPdnGyPeerDetailState indicates the detail state
         of the path."
    ::= { tmnxMobPdnGyPeerEntry 7 }

--
--  Gy Stats Table
--

tmnxMobPdnGyStatTable  OBJECT-TYPE
    SYNTAX      SEQUENCE OF TmnxMobPdnGyStatEntry
    MAX-ACCESS  not-accessible
    STATUS      current
    DESCRIPTION
        "The tmnxMobPdnGyStatTable has an entry for each peer on the Gy
         reference point served by a Packet Data Network Gateway (PGW)."
    ::= { tmnxMobPdnStatObjs 13 }

tmnxMobPdnGyStatEntry  OBJECT-TYPE
    SYNTAX      TmnxMobPdnGyStatEntry
    MAX-ACCESS  not-accessible
    STATUS      current
    DESCRIPTION
        "Each row entry represents a peer on the Gy reference point and
         contain statistics for this peer on a card."
    INDEX { tmnxMobGwId,
            vRtrID,
            tmnxMobProfDiaPeerName,
            tmnxMobProfDiaPeerListIndex,
            tmnxMobPdnGyPeerAddressType,
            tmnxMobPdnGyPeerAddress,
            tmnxMobPdnGyPeerPort,
            tmnxChassisIndex,
            tmnxCardSlotNum
          }
    ::= { tmnxMobPdnGyStatTable 1 }

TmnxMobPdnGyStatEntry ::= SEQUENCE {
        tmnxMobPdnGyStatCcrGranted          Counter32,
        tmnxMobPdnGyStatCcrDenied           Counter32,
        tmnxMobPdnGyStatCcrInitialMsgTx     Counter32,
        tmnxMobPdnGyStatCcrUpdateMsgTx      Counter32,
        tmnxMobPdnGyStatCcrTermMsgTx        Counter32,
        tmnxMobPdnGyStatCcaInitialMsgRx     Counter32,
        tmnxMobPdnGyStatCcaUpdateMsgRx      Counter32,
        tmnxMobPdnGyStatCcaTermMsgRx        Counter32,
        tmnxMobPdnGyStatCcrInitMsgFails     Counter32,
        tmnxMobPdnGyStatCcrUpdMsgFails      Counter32,
        tmnxMobPdnGyStatCcrTermMsgFails     Counter32,
        tmnxMobPdnGyStatAsrMsgRx            Counter32,
        tmnxMobPdnGyStatAsaMsgTx            Counter32,
        tmnxMobPdnGyStatAsaNackMsgTx        Counter32,
        tmnxMobPdnGyStatRarMsgRx            Counter32,
        tmnxMobPdnGyStatRaaMsgTx            Counter32,
        tmnxMobPdnGyStatRaaNackMsgTx        Counter32,
        tmnxMobPdnGyStatMalformedPktsRx     Counter32,
        tmnxMobPdnGyStatCCAInitMalfPktRx    Counter32,
        tmnxMobPdnGyStatCCAUpdtMalfPktRx    Counter32,
        tmnxMobPdnGyStatCCATermMalfPktRx    Counter32,
        tmnxMobPdnGyStatRarMalfPktRx        Counter32,
        tmnxMobPdnGyStatAsrMalfPktRx        Counter32,
        tmnxMobPdnGyStatUnkwnPktsRx         Counter32,
        tmnxMobPdnGyStatCcaInitUnkPktRx     Counter32,
        tmnxMobPdnGyStatCcaUpdUnkPktRx      Counter32,
        tmnxMobPdnGyStatCcaTermUnkPktRx     Counter32,
        tmnxMobPdnGyStatRarUnkPktRx         Counter32,
        tmnxMobPdnGyStatAsrUnkPktRx         Counter32,
        tmnxMobPdnGyStatMissingAvpPktRx     Counter32,
        tmnxMobPdnGyStatCcaIMisAvpPktRx     Counter32,
        tmnxMobPdnGyStatCcaUMisAvpPktRx     Counter32,
        tmnxMobPdnGyStatCcaTMisAvpPktRx     Counter32,
        tmnxMobPdnGyStatRarMisAvpPktRx      Counter32,
        tmnxMobPdnGyStatAsrMisAvpPktRx      Counter32,
        tmnxMobPdnGyStatCcaIUnkSessPkts     Counter32,
        tmnxMobPdnGyStatCcaUUnkSessPkts     Counter32,
        tmnxMobPdnGyStatCcaTUnkSessPkts     Counter32,
        tmnxMobPdnGyStatRarUnkSessPkts      Counter32,
        tmnxMobPdnGyStatAsrUnkSessPkts      Counter32,
        tmnxMobPdnGyStatTxCer               Counter32,
        tmnxMobPdnGyStatRxCea               Counter32,
        tmnxMobPdnGyStatRxDpr               Counter32,
        tmnxMobPdnGyStatTxDpa               Counter32,
        tmnxMobPdnGyStatTxDwr               Counter32,
        tmnxMobPdnGyStatRxDwa               Counter32,
        tmnxMobPdnGyStatConnAttempts        Counter32,
        tmnxMobPdnGyStatConnFailures        Counter32,
        tmnxMobPdnGyStatRxTransportDisc     Counter32,
        tmnxMobPdnGyStatRxMsgUnexpectVer    Counter32,
        tmnxMobPdnGyStatRxMsgTooBig         Counter32,
        tmnxMobPdnGyStatRxMsgTooSmall       Counter32,
        tmnxMobPdnGyStatRxInvalidCea        Counter32,
        tmnxMobPdnGyStatRxMsgs              Counter32,
        tmnxMobPdnGyStatTxMsgs              Counter32,
        tmnxMobPdnGyStatTxRetransmitMsgs    Counter32,
        tmnxMobPdnGyStatTxDpr               Counter32,
        tmnxMobPdnGyStatRxDpa               Counter32,
        tmnxMobPdnGyStatRxDwr               Counter32,
        tmnxMobPdnGyStatTxDwa               Counter32
    }

tmnxMobPdnGyStatCcrGranted  OBJECT-TYPE
    SYNTAX      Counter32
    MAX-ACCESS  read-only
    STATUS      current
    DESCRIPTION
        "The value of tmnxMobPdnGyStatCcrGranted indicates the number of 
         Credit Control Request (CCR) message requests granted."  
    ::= { tmnxMobPdnGyStatEntry 1 }

tmnxMobPdnGyStatCcrDenied  OBJECT-TYPE
    SYNTAX      Counter32
    MAX-ACCESS  read-only
    STATUS      current
    DESCRIPTION
        "The value of tmnxMobPdnGyStatCcrDenied indicates the number of 
         Credit Control Request (CCR) message requests denied."
    ::= { tmnxMobPdnGyStatEntry 2 }

tmnxMobPdnGyStatCcrInitialMsgTx  OBJECT-TYPE
    SYNTAX      Counter32
    MAX-ACCESS  read-only
    STATUS      current
    DESCRIPTION
        "The value of tmnxMobPdnGyStatCcrInitialMsgTx indicates the number of 
         Credit Control Request (CCR) initial message requests transmitted."
    ::= { tmnxMobPdnGyStatEntry 3 }

tmnxMobPdnGyStatCcrUpdateMsgTx  OBJECT-TYPE
    SYNTAX      Counter32
    MAX-ACCESS  read-only
    STATUS      current
    DESCRIPTION
        "The value of tmnxMobPdnGyStatCcrUpdateMsgTx indicates the number of
         Credit Control Request (CCR) update message requests transmitted."
    ::= { tmnxMobPdnGyStatEntry 4 }

tmnxMobPdnGyStatCcrTermMsgTx  OBJECT-TYPE
    SYNTAX      Counter32
    MAX-ACCESS  read-only
    STATUS      current
    DESCRIPTION
        "The value of tmnxMobPdnGyStatCcrTermMsgTx indicates the number of 
         Credit Control Request (CCR) termination message requests transmitted."
    ::= { tmnxMobPdnGyStatEntry 5 }

tmnxMobPdnGyStatCcaInitialMsgRx  OBJECT-TYPE
    SYNTAX      Counter32
    MAX-ACCESS  read-only
    STATUS      current
    DESCRIPTION
        "The value of tmnxMobPdnGyStatCcaInitialMsgRx indicates the number of
         Credit Control Answer (CCA) initial message requests received."
    ::= { tmnxMobPdnGyStatEntry 6 }

tmnxMobPdnGyStatCcaUpdateMsgRx  OBJECT-TYPE
    SYNTAX      Counter32
    MAX-ACCESS  read-only
    STATUS      current
    DESCRIPTION
        "The value of tmnxMobPdnGyStatCcaUpdateMsgRx indicates the number of
         Credit Control Answer (CCA) update message requests received."
    ::= { tmnxMobPdnGyStatEntry 7 }

tmnxMobPdnGyStatCcaTermMsgRx  OBJECT-TYPE
    SYNTAX      Counter32
    MAX-ACCESS  read-only
    STATUS      current
    DESCRIPTION
        "The value of tmnxMobPdnGyStatCcaTermMsgRx indicates the number of
         Credit Control Answer (CCA) termination message requests received."
    ::= { tmnxMobPdnGyStatEntry 8 }

tmnxMobPdnGyStatCcrInitMsgFails  OBJECT-TYPE
    SYNTAX      Counter32
    MAX-ACCESS  read-only
    STATUS      current
    DESCRIPTION
        "The value of tmnxMobPdnGyStatCcrInitMsgFails indicates the number of
         Credit Control Request (CCR) initial message requests failed."
    ::= { tmnxMobPdnGyStatEntry 9 }

tmnxMobPdnGyStatCcrUpdMsgFails  OBJECT-TYPE
    SYNTAX      Counter32
    MAX-ACCESS  read-only
    STATUS      current
    DESCRIPTION
        "The value of tmnxMobPdnGyStatCcrUpdMsgFails indicates the number of
         Credit Control Request (CCR) update message requests failed."
    ::= { tmnxMobPdnGyStatEntry 10 }

tmnxMobPdnGyStatCcrTermMsgFails  OBJECT-TYPE
    SYNTAX      Counter32
    MAX-ACCESS  read-only
    STATUS      current
    DESCRIPTION
        "The value of tmnxMobPdnGyStatCcrTermMsgFails indicates the number of
         Credit Control Request (CCR) termination message requests failed."
    ::= { tmnxMobPdnGyStatEntry 11 }

tmnxMobPdnGyStatAsrMsgRx  OBJECT-TYPE
    SYNTAX      Counter32
    MAX-ACCESS  read-only
    STATUS      current
    DESCRIPTION
        "The value of tmnxMobPdnGyStatAsrMsgRx indicates the number of 
         Abort Session Request (ASR) messages received."
    ::= { tmnxMobPdnGyStatEntry 12 }

tmnxMobPdnGyStatAsaMsgTx  OBJECT-TYPE
    SYNTAX      Counter32
    MAX-ACCESS  read-only
    STATUS      current
    DESCRIPTION
        "The value of tmnxMobPdnGyStatAsaMsgTx indicates the number of 
         Abort Session Answer (ASA) messages transmitted."
    ::= { tmnxMobPdnGyStatEntry 13 }

tmnxMobPdnGyStatAsaNackMsgTx  OBJECT-TYPE
    SYNTAX      Counter32
    MAX-ACCESS  read-only
    STATUS      current
    DESCRIPTION
        "The value of tmnxMobPdnGyStatAsaNackMsgTx indicates the number of
         Abort Session Answer (ASA) negative acknowledgement messages
         transmitted."
    ::= { tmnxMobPdnGyStatEntry 14 }

tmnxMobPdnGyStatRarMsgRx  OBJECT-TYPE
    SYNTAX      Counter32
    MAX-ACCESS  read-only
    STATUS      current
    DESCRIPTION
        "The value of tmnxMobPdnGyStatRarMsgRx indicates the number of 
         Re-authorization Request (RAR) messages received."
    ::= { tmnxMobPdnGyStatEntry 15 }

tmnxMobPdnGyStatRaaMsgTx  OBJECT-TYPE
    SYNTAX      Counter32
    MAX-ACCESS  read-only
    STATUS      current
    DESCRIPTION
        "The value of tmnxMobPdnGyStatRaaMsgTx indicates the number of
         Re-authorization Answer (RAA) messages transmitted."
    ::= { tmnxMobPdnGyStatEntry 16 }

tmnxMobPdnGyStatRaaNackMsgTx  OBJECT-TYPE
    SYNTAX      Counter32
    MAX-ACCESS  read-only
    STATUS      current
    DESCRIPTION
        "The value of tmnxMobPdnGyStatRaaNackMsgTx indicates the number of
         Re-authorization Answer (RAA) negative acknowledgement messages
         transmitted."
    ::= { tmnxMobPdnGyStatEntry 17 }

tmnxMobPdnGyStatMalformedPktsRx  OBJECT-TYPE
    SYNTAX      Counter32
    MAX-ACCESS  read-only
    STATUS      current
    DESCRIPTION
        "The value of tmnxMobPdnGyStatMalformedPktsRx indicates the number of
         malformed packets received."
    ::= { tmnxMobPdnGyStatEntry 18 }

tmnxMobPdnGyStatCCAInitMalfPktRx  OBJECT-TYPE
    SYNTAX      Counter32
    MAX-ACCESS  read-only
    STATUS      current
    DESCRIPTION
        "The value of tmnxMobPdnGyStatCCAInitMalfPktRx indicates the number of
         Credit Control Answer (CCA) initial malformed packets received."
    ::= { tmnxMobPdnGyStatEntry 19 }

tmnxMobPdnGyStatCCAUpdtMalfPktRx  OBJECT-TYPE
    SYNTAX      Counter32
    MAX-ACCESS  read-only
    STATUS      current
    DESCRIPTION
        "The value of tmnxMobPdnGyStatCCAUpdtMalfPktRx indicates the number of
         Credit Control Answer (CCA) update malformed packets received."
    ::= { tmnxMobPdnGyStatEntry 20 }

tmnxMobPdnGyStatCCATermMalfPktRx  OBJECT-TYPE
    SYNTAX      Counter32
    MAX-ACCESS  read-only
    STATUS      current
    DESCRIPTION
        "The value of tmnxMobPdnGyStatCCATermMalfPktRx indicates the number of
         Credit Control Answer (CCA) termination malformed packets received."
    ::= { tmnxMobPdnGyStatEntry 21 }

tmnxMobPdnGyStatRarMalfPktRx  OBJECT-TYPE
    SYNTAX      Counter32
    MAX-ACCESS  read-only
    STATUS      current
    DESCRIPTION
        "The value of tmnxMobPdnGyStatRarMalfPktRx indicates the number of
         Re-authorization Request (RAR) malformed packets received."
    ::= { tmnxMobPdnGyStatEntry 22 }

tmnxMobPdnGyStatAsrMalfPktRx  OBJECT-TYPE
    SYNTAX      Counter32
    MAX-ACCESS  read-only
    STATUS      current
    DESCRIPTION
        "The value of tmnxMobPdnGyStatAsrMalfPktRx indicates the number of 
         Abort Session Request (ASR) malformed packets received."
    ::= { tmnxMobPdnGyStatEntry 23 }

tmnxMobPdnGyStatUnkwnPktsRx  OBJECT-TYPE
    SYNTAX      Counter32
    MAX-ACCESS  read-only
    STATUS      current
    DESCRIPTION
        "The value of tmnxMobPdnGyStatUnkwnPktsRx indicates the number of 
         unknown packets received."
    ::= { tmnxMobPdnGyStatEntry 24 }

tmnxMobPdnGyStatCcaInitUnkPktRx  OBJECT-TYPE
    SYNTAX      Counter32
    MAX-ACCESS  read-only
    STATUS      current
    DESCRIPTION
        "The value of tmnxMobPdnGyStatCcaInitUnkPktRx indicates the number of
         Credit Control Answer (CCA) initial unknown packets received."
    ::= { tmnxMobPdnGyStatEntry 25 }

tmnxMobPdnGyStatCcaUpdUnkPktRx  OBJECT-TYPE
    SYNTAX      Counter32
    MAX-ACCESS  read-only
    STATUS      current
    DESCRIPTION
        "The value of tmnxMobPdnGyStatCcaUpdUnkPktRx indicates the number of
         Credit Control Answer (CCA) update unknown packets received."
    ::= { tmnxMobPdnGyStatEntry 26 }

tmnxMobPdnGyStatCcaTermUnkPktRx  OBJECT-TYPE
    SYNTAX      Counter32
    MAX-ACCESS  read-only
    STATUS      current
    DESCRIPTION
        "The value of tmnxMobPdnGyStatCcaTermUnkPktRx indicates the number of
         Credit Control Answer (CCA) termination unknown packets received."
    ::= { tmnxMobPdnGyStatEntry 27 }

tmnxMobPdnGyStatRarUnkPktRx  OBJECT-TYPE
    SYNTAX      Counter32
    MAX-ACCESS  read-only
    STATUS      current
    DESCRIPTION
        "The value of tmnxMobPdnGyStatRarUnkPktRx indicates the number of
         Re-authorization Request (RAR) unknown packets received."
    ::= { tmnxMobPdnGyStatEntry 28 }

tmnxMobPdnGyStatAsrUnkPktRx  OBJECT-TYPE
    SYNTAX      Counter32
    MAX-ACCESS  read-only
    STATUS      current
    DESCRIPTION
        "The value of tmnxMobPdnGyStatAsrUnkPktRx indicates the number of 
         Abort Session Request (ASR) unknown packets received."
    ::= { tmnxMobPdnGyStatEntry 29 }

tmnxMobPdnGyStatMissingAvpPktRx  OBJECT-TYPE
    SYNTAX      Counter32
    MAX-ACCESS  read-only
    STATUS      current
    DESCRIPTION
        "The value of tmnxMobPdnGyStatMissingAvpPktRx indicates the number of
         missing Attribute Value Pair (AVP) packets received."
    ::= { tmnxMobPdnGyStatEntry 30 }

tmnxMobPdnGyStatCcaIMisAvpPktRx  OBJECT-TYPE
    SYNTAX      Counter32
    MAX-ACCESS  read-only
    STATUS      current
    DESCRIPTION
        "The value of tmnxMobPdnGyStatCcaIMisAvpPktRx indicates the number of
         missing Attribute Value Pair (AVP) packets received for Credit Control
         Answer (CCA) initial message."
    ::= { tmnxMobPdnGyStatEntry 31 }

tmnxMobPdnGyStatCcaUMisAvpPktRx  OBJECT-TYPE
    SYNTAX      Counter32
    MAX-ACCESS  read-only
    STATUS      current
    DESCRIPTION
        "The value of tmnxMobPdnGyStatCcaUMisAvpPktRx indicates the number of
         missing Attribute Value Pair (AVP) packets received for Credit Control
         Answer (CCA) update message."
    ::= { tmnxMobPdnGyStatEntry 32 }

tmnxMobPdnGyStatCcaTMisAvpPktRx  OBJECT-TYPE
    SYNTAX      Counter32
    MAX-ACCESS  read-only
    STATUS      current
    DESCRIPTION
        "The value of tmnxMobPdnGyStatCcaTMisAvpPktRx indicates the number of 
         missing Attribute Value Pair (AVP) packets received for Credit Control
         Answer (CCA) termination message."
    ::= { tmnxMobPdnGyStatEntry 33 }

tmnxMobPdnGyStatRarMisAvpPktRx  OBJECT-TYPE
    SYNTAX      Counter32
    MAX-ACCESS  read-only
    STATUS      current
    DESCRIPTION
        "The value of tmnxMobPdnGyStatRarMisAvpPktRx indicates the number of 
         missing Attribute Value Pair (AVP) packets received for 
         Re-authorization Request (RAR) message."
    ::= { tmnxMobPdnGyStatEntry 34 }

tmnxMobPdnGyStatAsrMisAvpPktRx  OBJECT-TYPE
    SYNTAX      Counter32
    MAX-ACCESS  read-only
    STATUS      current
    DESCRIPTION
        "The value of tmnxMobPdnGyStatAsrMisAvpPktRx indicates the number of 
         missing Attribute Value Pair (AVP) packets received for 
         Abort Session Request (ASR) message."
    ::= { tmnxMobPdnGyStatEntry 35 }

tmnxMobPdnGyStatCcaIUnkSessPkts  OBJECT-TYPE
    SYNTAX      Counter32
    MAX-ACCESS  read-only
    STATUS      current
    DESCRIPTION
        "The value of tmnxMobPdnGyStatCcaIUnkSessPkts indicates the number of 
         unknown session packets received for Credit Control Answer (CCA) 
         initial messages."
    ::= { tmnxMobPdnGyStatEntry 36 }

tmnxMobPdnGyStatCcaUUnkSessPkts  OBJECT-TYPE
    SYNTAX      Counter32
    MAX-ACCESS  read-only
    STATUS      current
    DESCRIPTION
        "The value of tmnxMobPdnGyStatCcaUUnkSessPkts indicates the number of 
         unknown session packets received for Credit Control Answer (CCA) 
         update messages."
    ::= { tmnxMobPdnGyStatEntry 37 }

tmnxMobPdnGyStatCcaTUnkSessPkts  OBJECT-TYPE
    SYNTAX      Counter32
    MAX-ACCESS  read-only
    STATUS      current
    DESCRIPTION
        "The value of tmnxMobPdnGyStatCcaTUnkSessPkts indicates the number of 
         unknown session packets received for Credit Control Answer (CCA) 
         termination messages."
    ::= { tmnxMobPdnGyStatEntry 38 }

tmnxMobPdnGyStatRarUnkSessPkts  OBJECT-TYPE
    SYNTAX      Counter32
    MAX-ACCESS  read-only
    STATUS      current
    DESCRIPTION
        "The value of tmnxMobPdnGyStatRarUnkSessPkts indicates the number of
         unknown session packets received for Re-authorization Request (RAR) 
         messages."
    ::= { tmnxMobPdnGyStatEntry 39 }

tmnxMobPdnGyStatAsrUnkSessPkts  OBJECT-TYPE
    SYNTAX      Counter32
    MAX-ACCESS  read-only
    STATUS      current
    DESCRIPTION
        "The value of tmnxMobPdnGyStatAsrUnkSessPkts indicates the number of 
         unknown session packets received for Abort Session Request (ASR) 
         messages."
    ::= { tmnxMobPdnGyStatEntry 40 }

tmnxMobPdnGyStatTxCer  OBJECT-TYPE
    SYNTAX      Counter32
    MAX-ACCESS  read-only
    STATUS      current
    DESCRIPTION
        "The value of tmnxMobPdnGyStatTxCer indicates the number of Capabilities
         Exchange Request (CER) messages transmitted to this peer."
    ::= { tmnxMobPdnGyStatEntry 41 }

tmnxMobPdnGyStatRxCea  OBJECT-TYPE
    SYNTAX      Counter32
    MAX-ACCESS  read-only
    STATUS      current
    DESCRIPTION
        "The value of tmnxMobPdnGyStatRxCea indicates the number of Capabilities
         Exchange Answer (CEA) messages received from this peer."
    ::= { tmnxMobPdnGyStatEntry 42 }

tmnxMobPdnGyStatRxDpr  OBJECT-TYPE
    SYNTAX      Counter32
    MAX-ACCESS  read-only
    STATUS      current
    DESCRIPTION
        "The value of tmnxMobPdnGyStatRxDpr indicates the number of Disconnect
         Peer Request (DPR) messages received from this peer."
    ::= { tmnxMobPdnGyStatEntry 43 }

tmnxMobPdnGyStatTxDpa  OBJECT-TYPE
    SYNTAX      Counter32
    MAX-ACCESS  read-only
    STATUS      current
    DESCRIPTION
        "The value of tmnxMobPdnGyStatTxDpa indicates the number of Disconnect
         Peer Answer (DPA) messages transmitted to this peer."
    ::= { tmnxMobPdnGyStatEntry 44 }

tmnxMobPdnGyStatTxDwr  OBJECT-TYPE
    SYNTAX      Counter32
    MAX-ACCESS  read-only
    STATUS      current
    DESCRIPTION
        "The value of tmnxMobPdnGyStatTxDwr indicates the number of Device
         Watchdog Request (DWR) messages transmitted to this peer."
    ::= { tmnxMobPdnGyStatEntry 45 }

tmnxMobPdnGyStatRxDwa  OBJECT-TYPE
    SYNTAX      Counter32
    MAX-ACCESS  read-only
    STATUS      current
    DESCRIPTION
        "The value of tmnxMobPdnGyStatRxDwa indicates the number of Device
         Watchdog Answer (DWA) messages received from this peer."
    ::= { tmnxMobPdnGyStatEntry 46 }

tmnxMobPdnGyStatConnAttempts  OBJECT-TYPE
    SYNTAX      Counter32
    MAX-ACCESS  read-only
    STATUS      current
    DESCRIPTION
        "The value of tmnxMobPdnGyStatConnAttempts indicates the number of 
         connections attempted to this peer."
    ::= { tmnxMobPdnGyStatEntry 47 }

tmnxMobPdnGyStatConnFailures  OBJECT-TYPE
    SYNTAX      Counter32
    MAX-ACCESS  read-only
    STATUS      current
    DESCRIPTION
        "The value of tmnxMobPdnGyStatConnFailures indicates the number of 
         failed connections with this peer."
    ::= { tmnxMobPdnGyStatEntry 48 }

tmnxMobPdnGyStatRxTransportDisc  OBJECT-TYPE
    SYNTAX      Counter32
    MAX-ACCESS  read-only
    STATUS      current
    DESCRIPTION
        "The value of tmnxMobPdnGyStatRxTransportDisc indicates the number of 
         remote transport disconnect messages received from this peer."
    ::= { tmnxMobPdnGyStatEntry 49 }

tmnxMobPdnGyStatRxMsgUnexpectVer  OBJECT-TYPE
    SYNTAX      Counter32
    MAX-ACCESS  read-only
    STATUS      current
    DESCRIPTION
        "The value of tmnxMobPdnGyStatRxMsgUnexpectVer indicates the number of 
         unexpected version messages received from this peer."
    ::= { tmnxMobPdnGyStatEntry 50 }

tmnxMobPdnGyStatRxMsgTooBig  OBJECT-TYPE
    SYNTAX      Counter32
    MAX-ACCESS  read-only
    STATUS      current
    DESCRIPTION
        "The value of tmnxMobPdnGyStatRxMsgTooBig indicates the number of 
         oversize messages received from this peer."
    ::= { tmnxMobPdnGyStatEntry 51 }

tmnxMobPdnGyStatRxMsgTooSmall  OBJECT-TYPE
    SYNTAX      Counter32
    MAX-ACCESS  read-only
    STATUS      current
    DESCRIPTION
        "The value of tmnxMobPdnGyStatRxMsgTooSmall indicates the number of 
         small messages received from this peer."
    ::= { tmnxMobPdnGyStatEntry 52 }

tmnxMobPdnGyStatRxInvalidCea  OBJECT-TYPE
    SYNTAX      Counter32
    MAX-ACCESS  read-only
    STATUS      current
    DESCRIPTION
        "The value of tmnxMobPdnGyStatRxInvalidCea indicates the number of 
         invalid Capabilities Exchange Answer (CEA) messages received from 
         this peer."
    ::= { tmnxMobPdnGyStatEntry 53 }

tmnxMobPdnGyStatRxMsgs  OBJECT-TYPE
    SYNTAX      Counter32
    MAX-ACCESS  read-only
    STATUS      current
    DESCRIPTION
        "The value of tmnxMobPdnGyStatRxMsgs indicates the total number of 
         messages received from this peer."
    ::= { tmnxMobPdnGyStatEntry 54 }

tmnxMobPdnGyStatTxMsgs  OBJECT-TYPE
    SYNTAX      Counter32
    MAX-ACCESS  read-only
    STATUS      current
    DESCRIPTION
        "The value of tmnxMobPdnGyStatTxMsgs indicates the total number of 
         messages transmitted to this peer."
    ::= { tmnxMobPdnGyStatEntry 55 }

tmnxMobPdnGyStatTxRetransmitMsgs  OBJECT-TYPE
    SYNTAX      Counter32
    MAX-ACCESS  read-only
    STATUS      current
    DESCRIPTION
        "The value of tmnxMobPdnGyStatTxRetransmitMsgs indicates the number of 
         retransmit messages transmitted to this peer."
    ::= { tmnxMobPdnGyStatEntry 56 }

tmnxMobPdnGyStatTxDpr             OBJECT-TYPE
    SYNTAX      Counter32
    MAX-ACCESS  read-only
    STATUS      current
    DESCRIPTION
        "The value of tmnxMobPdnGyStatTxDpr indicates the number of Disconnect
         Peer Request (DPR) messages transmitted to this peer."
    ::= { tmnxMobPdnGyStatEntry 57 }

tmnxMobPdnGyStatRxDpa             OBJECT-TYPE
    SYNTAX      Counter32
    MAX-ACCESS  read-only
    STATUS      current
    DESCRIPTION
        "The value of tmnxMobPdnGyStatRxDpa indicates the number of Disconnect
         Peer Answer (DPA) messages received from this peer."
    ::= { tmnxMobPdnGyStatEntry 58 }

tmnxMobPdnGyStatRxDwr             OBJECT-TYPE
    SYNTAX      Counter32
    MAX-ACCESS  read-only
    STATUS      current
    DESCRIPTION
        "The value of tmnxMobPdnGyStatRxDwr indicates the number of Device
         Watchdog Request (DWR) messages received from this peer."
    ::= { tmnxMobPdnGyStatEntry 59 }

tmnxMobPdnGyStatTxDwa             OBJECT-TYPE
    SYNTAX      Counter32
    MAX-ACCESS  read-only
    STATUS      current
    DESCRIPTION
        "The value of tmnxMobPdnGyStatTxDwa indicates the number of Device
         Watchdog Answer (DWA) messages transmitted to this peer."
    ::= { tmnxMobPdnGyStatEntry 60 }

--
--  Ga peer list Table
--

tmnxMobPdnGaPeerTableLastChngd     OBJECT-TYPE
    SYNTAX      TimeStamp
    MAX-ACCESS  read-only
    STATUS      current
    DESCRIPTION
        "The value of tmnxMobPdnGaPeerTableLastChngd indicates the sysUpTime
         at the time of the last modification to tmnxMobPdnGaPeerTable by
         adding, deleting an entry or change to a writable object in the table.

         If no changes were made to the table since the last re-initialization
         of the local network management subsystem, then this object contains
         a zero value."
    ::= { tmnxMobPdnGlobalObjs 24 }

tmnxMobPdnGaPeerTable  OBJECT-TYPE
    SYNTAX      SEQUENCE OF TmnxMobPdnGaPeerEntry
    MAX-ACCESS  not-accessible
    STATUS      current
    DESCRIPTION
        "The tmnxMobPdnGaPeerTable has an entry for each peer on the Ga
         reference point served by a Packet Data Network Gateway (PGW)."
    ::= { tmnxMobPdnStatObjs 14 }

tmnxMobPdnGaPeerEntry  OBJECT-TYPE
    SYNTAX      TmnxMobPdnGaPeerEntry
    MAX-ACCESS  not-accessible
    STATUS      current
    DESCRIPTION
        "Each row entry represents a peer on the Ga reference point."
    INDEX { tmnxMobGwId,
            vRtrID,
            tmnxMobGtpPriGrpName,
            tmnxMobGtpPriServerIndex,
            tmnxMobPdnGaStatAddressType,
            tmnxMobPdnGaStatAddress,
            tmnxMobPdnGaStatPort
          }
    ::= { tmnxMobPdnGaPeerTable 1 }

TmnxMobPdnGaPeerEntry ::= SEQUENCE {
        tmnxMobPdnGaPeerLastChanged       TimeStamp,
        tmnxMobPdnGaPeerCreateTime        TimeStamp,
        tmnxMobPdnGaPeerPathMgmtState     TmnxMobDiaPathMgmtState,
        tmnxMobPdnGaPeerDetailState       TmnxMobDiaDetailPathMgmtState
    }

tmnxMobPdnGaPeerLastChanged  OBJECT-TYPE
    SYNTAX      TimeStamp
    MAX-ACCESS  read-only
    STATUS      current
    DESCRIPTION
        "The value of tmnxMobPdnGaPeerLastChanged indicates the timestamp of
         the last change to this row in tmnxMobPdnGaPeerTable."
    ::= { tmnxMobPdnGaPeerEntry 1 }

tmnxMobPdnGaPeerCreateTime  OBJECT-TYPE
    SYNTAX      TimeStamp
    MAX-ACCESS  read-only
    STATUS      current
    DESCRIPTION
        "The value of tmnxMobPdnGaPeerCreateTime indicates the sysUpTime when
         this entry was created."
    ::= { tmnxMobPdnGaPeerEntry 2 }

tmnxMobPdnGaPeerPathMgmtState  OBJECT-TYPE
    SYNTAX      TmnxMobDiaPathMgmtState
    MAX-ACCESS  read-only
    STATUS      current
    DESCRIPTION
        "The value of tmnxMobPdnGaPeerPathMgmtState indicates the state of
         the path."
    ::= { tmnxMobPdnGaPeerEntry 3 }

tmnxMobPdnGaPeerDetailState  OBJECT-TYPE
    SYNTAX      TmnxMobDiaDetailPathMgmtState
    MAX-ACCESS  read-only
    STATUS      current
    DESCRIPTION
        "The value of tmnxMobPdnGaPeerDetailState indicates the detail state
         of the path."
    ::= { tmnxMobPdnGaPeerEntry 4 }

--
--  Radius peer list Table
--

tmnxMobPdnRadPeerTableLastChngd     OBJECT-TYPE
    SYNTAX      TimeStamp
    MAX-ACCESS  read-only
    STATUS      current
    DESCRIPTION
        "The value of tmnxMobPdnRadPeerTableLastChngd indicates the sysUpTime
         at the time of the last modification to tmnxMobPdnRadPeerTable by
         adding, deleting an entry or change to a writable object in the table.

         If no changes were made to the table since the last re-initialization
         of the local network management subsystem, then this object contains
         a zero value."
    ::= { tmnxMobPdnGlobalObjs 25 }

tmnxMobPdnRadPeerTable  OBJECT-TYPE
    SYNTAX      SEQUENCE OF TmnxMobPdnRadPeerEntry
    MAX-ACCESS  not-accessible
    STATUS      current
    DESCRIPTION
        "The tmnxMobPdnRadPeerTable has an entry for each peer on the Radius
         Server served by a Packet Data Network Gateway (PGW)."
    ::= { tmnxMobPdnStatObjs 15 }

tmnxMobPdnRadPeerEntry  OBJECT-TYPE
    SYNTAX      TmnxMobPdnRadPeerEntry
    MAX-ACCESS  not-accessible
    STATUS      current
    DESCRIPTION
        "Each row entry represents a peer on the Radius Server."
    INDEX { tmnxMobGwId,
            vRtrID,
            tmnxMobProfRadGrpName,
            tmnxMobProfRadPeerIndex,
            tmnxMobPdnRadPeerAddressType,
            tmnxMobPdnRadPeerAddress
          }
    ::= { tmnxMobPdnRadPeerTable 1 }

TmnxMobPdnRadPeerEntry ::= SEQUENCE {
        tmnxMobPdnRadPeerAddressType       InetAddressType,
        tmnxMobPdnRadPeerAddress           InetAddress, 
        tmnxMobPdnRadPeerLastChanged       TimeStamp,
        tmnxMobPdnRadPeerCreateTime        TimeStamp,
        tmnxMobPdnRadPeerPathMgmtState     TmnxMobDiaPathMgmtState,
        tmnxMobPdnRadPeerDetailState       TmnxMobDiaDetailPathMgmtState
    }

tmnxMobPdnRadPeerAddressType  OBJECT-TYPE
    SYNTAX      InetAddressType
    MAX-ACCESS  not-accessible
    STATUS      current
    DESCRIPTION
        "The value of tmnxMobPdnRadPeerAddressType indicates the type of
         address represented by tmnxMobPdnRadPeerAddress."
    ::= { tmnxMobPdnRadPeerEntry 1 }

tmnxMobPdnRadPeerAddress  OBJECT-TYPE
    SYNTAX      InetAddress (SIZE (0|4|16))
    MAX-ACCESS  not-accessible
    STATUS      current
    DESCRIPTION
        "The value of tmnxMobPdnRadPeerAddress indicates the IP address of the
         Radius peer."
    ::= { tmnxMobPdnRadPeerEntry 2 }

tmnxMobPdnRadPeerLastChanged  OBJECT-TYPE
    SYNTAX      TimeStamp
    MAX-ACCESS  read-only
    STATUS      current
    DESCRIPTION
        "The value of tmnxMobPdnRadPeerLastChanged indicates the timestamp of
         the last change to this row in tmnxMobPdnRadPeerTable."
    ::= { tmnxMobPdnRadPeerEntry 3 }

tmnxMobPdnRadPeerCreateTime  OBJECT-TYPE
    SYNTAX      TimeStamp
    MAX-ACCESS  read-only
    STATUS      current
    DESCRIPTION
        "The value of tmnxMobPdnRadPeerCreateTime indicates the sysUpTime when
         this entry was created."
    ::= { tmnxMobPdnRadPeerEntry 4 }

tmnxMobPdnRadPeerPathMgmtState  OBJECT-TYPE
    SYNTAX      TmnxMobDiaPathMgmtState
    MAX-ACCESS  read-only
    STATUS      current
    DESCRIPTION
        "The value of tmnxMobPdnRadPeerPathMgmtState indicates the state of
         the path."
    ::= { tmnxMobPdnRadPeerEntry 5 }

tmnxMobPdnRadPeerDetailState  OBJECT-TYPE
    SYNTAX      TmnxMobDiaDetailPathMgmtState
    MAX-ACCESS  read-only
    STATUS      current
    DESCRIPTION
        "The value of tmnxMobPdnRadPeerDetailState indicates the detail state
         of the path."
    ::= { tmnxMobPdnRadPeerEntry 6 }

--
--  Radius Stats Table
--

tmnxMobPdnRadStatTable  OBJECT-TYPE
    SYNTAX      SEQUENCE OF TmnxMobPdnRadStatEntry
    MAX-ACCESS  not-accessible
    STATUS      current
    DESCRIPTION
        "The tmnxMobPdnRadStatTable has an entry for each peer on the Radius
         Server served by a Packet Data Network Gateway (PGW)."
    ::= { tmnxMobPdnStatObjs 16 }

tmnxMobPdnRadStatEntry  OBJECT-TYPE
    SYNTAX      TmnxMobPdnRadStatEntry
    MAX-ACCESS  not-accessible
    STATUS      current
    DESCRIPTION
        "Each row entry represents a peer on the Radius Server and
         contain statistics for this peer on a card."
    INDEX { tmnxMobGwId,
            vRtrID,
            tmnxMobProfRadGrpName,
            tmnxMobProfRadPeerIndex,
            tmnxMobPdnRadPeerAddressType,
            tmnxMobPdnRadPeerAddress,
            tmnxChassisIndex,
            tmnxCardSlotNum
          }
    ::= { tmnxMobPdnRadStatTable 1 }

TmnxMobPdnRadStatEntry ::= SEQUENCE {
        tmnxMobPdnRadStatLastChanged        TimeStamp,
        tmnxMobPdnRadStatAccessReqTx        Counter32,
        tmnxMobPdnRadStatAccessAcceptRx     Counter32,
        tmnxMobPdnRadStatAccessRejectRx     Counter32,
        tmnxMobPdnRadStatAcctReqStartTx     Counter32,
        tmnxMobPdnRadStatAcctReqIntrmTx     Counter32,
        tmnxMobPdnRadStatAcctReqStopTx      Counter32,
        tmnxMobPdnRadStatAcctResponseRx     Counter32,
        tmnxMobPdnRadStatMandAttrMissing    Counter32,
        tmnxMobPdnRadStatMandAttrErrors     Counter32,
        tmnxMobPdnRadStatUnsupportedAttr    Counter32,
        tmnxMobPdnRadStatOptionalAttrErr    Counter32,
        tmnxMobPdnRadStatAuthError          Counter32,
        tmnxMobPdnRadStatUnexpectedCode     Counter32,
        tmnxMobPdnRadStatRespTimeBelow1     Counter32,
        tmnxMobPdnRadStatRespTime1to4       Counter32,
        tmnxMobPdnRadStatRespTimeAbove4     Counter32,
        tmnxMobPdnRadStatRetries            Counter32,
        tmnxMobPdnRadStatPrFinalTimeout     Counter32,
        tmnxMobPdnRadStatDiscReqRx          Counter32,
        tmnxMobPdnRadStatDiscAckTx          Counter32,
        tmnxMobPdnRadStatDiscNakTx          Counter32,
        tmnxMobPdnRadStatDiscMandAtrMiss    Counter32,
        tmnxMobPdnRadStatDiscUnsupprAttr    Counter32,
        tmnxMobPdnRadStatDiscSessNotFnd     Counter32,
        tmnxMobPdnRadStatDiscAuthError      Counter32,
        tmnxMobPdnRadStatDiscUnexpcCode     Counter32,
        tmnxMobPdnRadStatMsgFinalTimeout    Counter32
    }

tmnxMobPdnRadStatLastChanged  OBJECT-TYPE
    SYNTAX      TimeStamp
    MAX-ACCESS  read-only
    STATUS      current
    DESCRIPTION
        "The value of tmnxMobPdnRadStatLastChanged indicates the timestamp of
         the last change to this row in tmnxMobPdnRadStatTable."
    ::= { tmnxMobPdnRadStatEntry 1 }

tmnxMobPdnRadStatAccessReqTx  OBJECT-TYPE
    SYNTAX      Counter32
    MAX-ACCESS  read-only
    STATUS      current
    DESCRIPTION
        "The value of tmnxMobPdnRadStatAccessReqTx indicates the number of 
         Access-Request messages sent by the Packet Data Network 
         Gateway (PGW)/Gateway GPRS Service Node (GGSN)."
    ::= { tmnxMobPdnRadStatEntry 2 }

tmnxMobPdnRadStatAccessAcceptRx  OBJECT-TYPE
    SYNTAX      Counter32
    MAX-ACCESS  read-only
    STATUS      current
    DESCRIPTION
        "The value of tmnxMobPdnRadStatAccessAcceptRx indicates the number of
         Access-Accept messages received by the PGW/GGSN.  This includes
         messages that may be discarded due to errors."
    ::= { tmnxMobPdnRadStatEntry 3 }

tmnxMobPdnRadStatAccessRejectRx  OBJECT-TYPE
    SYNTAX      Counter32
    MAX-ACCESS  read-only
    STATUS      current
    DESCRIPTION
        "The value of tmnxMobPdnRadStatAccessRejectRx indicates the number of
         Access-Reject messages received by the PGW/GGSN."
    ::= { tmnxMobPdnRadStatEntry 4 }

tmnxMobPdnRadStatAcctReqStartTx  OBJECT-TYPE
    SYNTAX      Counter32
    MAX-ACCESS  read-only
    STATUS      current
    DESCRIPTION
        "The value of tmnxMobPdnRadStatAcctReqStartTx indicates the number of
         Accounting-Request start messages sent by the PGW/GGSN."
    ::= { tmnxMobPdnRadStatEntry 5 }

tmnxMobPdnRadStatAcctReqIntrmTx  OBJECT-TYPE
    SYNTAX      Counter32
    MAX-ACCESS  read-only
    STATUS      current 
    DESCRIPTION
        "The value of tmnxMobPdnRadStatAcctReqIntrmTx indicates the number of
         Accounting-Request interim messages sent by the PGW/GGSN."
    ::= { tmnxMobPdnRadStatEntry 6 }

tmnxMobPdnRadStatAcctReqStopTx  OBJECT-TYPE
    SYNTAX      Counter32
    MAX-ACCESS  read-only
    STATUS      current
    DESCRIPTION
        "The value of tmnxMobPdnRadStatAcctReqStopTx indicates the number of
         Accounting-Request stop messages sent by the PGW/GGSN."
    ::= { tmnxMobPdnRadStatEntry 7 }

tmnxMobPdnRadStatAcctResponseRx  OBJECT-TYPE
    SYNTAX      Counter32
    MAX-ACCESS  read-only
    STATUS      current
    DESCRIPTION
        "The value of tmnxMobPdnRadStatAcctResponseRx indicates the number of
         Accounting-Response messages received by the PGW/GGSN."
    ::= { tmnxMobPdnRadStatEntry 8 }

tmnxMobPdnRadStatMandAttrMissing  OBJECT-TYPE
    SYNTAX      Counter32
    MAX-ACCESS  read-only
    STATUS      current
    DESCRIPTION
        "The value of tmnxMobPdnRadStatMandAttrMissing indicates the number of
         Access-Accept messages with missing mandatory attribute. When the
         Access-Request is intended for IP address allocation, the response must
         contain a Framed-IP-Address, Framed-Pool, Framed-IPv6-Prefix or
         Framed-IPv6-Pool. When the Access-Request is used for
         pre-authentication, the Timetra-APN-Name attribute should be considered
         mandatory."
    ::= { tmnxMobPdnRadStatEntry 9 }

tmnxMobPdnRadStatMandAttrErrors   OBJECT-TYPE
    SYNTAX      Counter32
    MAX-ACCESS  read-only
    STATUS      current
    DESCRIPTION
        "The value of tmnxMobPdnRadStatMandAttrErrors indicates the number of
         Access-Accept messages contains an invalid or errored mandatory
         attribute."
    ::= { tmnxMobPdnRadStatEntry 10 }

tmnxMobPdnRadStatUnsupportedAttr   OBJECT-TYPE
    SYNTAX      Counter32
    MAX-ACCESS  read-only
    STATUS      current
    DESCRIPTION
        "The value of tmnxMobPdnRadStatUnsupportedAttr indicates the number of
         Access-Accept messages contains an unrecognized/unsupported attribute."
    ::= { tmnxMobPdnRadStatEntry 11 }

tmnxMobPdnRadStatOptionalAttrErr   OBJECT-TYPE
    SYNTAX      Counter32
    MAX-ACCESS  read-only
    STATUS      current
    DESCRIPTION
        "The value of tmnxMobPdnRadStatOptionalAttrErr indicates the number of
         Access-Accept messages contains an invalid or errored optional
         attribute."
    ::= { tmnxMobPdnRadStatEntry 12 }

tmnxMobPdnRadStatAuthError   OBJECT-TYPE
    SYNTAX      Counter32
    MAX-ACCESS  read-only
    STATUS      current
    DESCRIPTION
        "The value of tmnxMobPdnRadStatAuthError indicates the number of invalid
         authenticator values in the Access-Response or Accounting-Response
         messages."
    ::= { tmnxMobPdnRadStatEntry 13 }

tmnxMobPdnRadStatUnexpectedCode   OBJECT-TYPE
    SYNTAX      Counter32
    MAX-ACCESS  read-only
    STATUS      current
    DESCRIPTION
        "The value of tmnxMobPdnRadStatUnexpectedCode indicates the number of
         unexpected messages recieved by the PGW/GGSN. The unexpected messages
         can be such as an Access-Request, Accounting-Request or any response
         for a request that it did not send or it received for the RADIUS code
         that is not supported."
    ::= { tmnxMobPdnRadStatEntry 14 }

tmnxMobPdnRadStatRespTimeBelow1   OBJECT-TYPE
    SYNTAX      Counter32
    MAX-ACCESS  read-only
    STATUS      current
    DESCRIPTION
        "The value of tmnxMobPdnRadStatRespTimeBelow1 indicates the number of 
         Access-Request/Access-Response messages received in less than 1 second
         after the Access-Request/Accounting-Request was generated."
    ::= { tmnxMobPdnRadStatEntry 15 }

tmnxMobPdnRadStatRespTime1to4   OBJECT-TYPE
    SYNTAX      Counter32
    MAX-ACCESS  read-only
    STATUS      current
    DESCRIPTION
        "The value of tmnxMobPdnRadStatRespTime1to4 indicates the number of 
         Access-Request/Access-Response messages received between 1 and 4 
         seconds after the Access-Request/Accounting-Request was generated."
    ::= { tmnxMobPdnRadStatEntry 16 }

tmnxMobPdnRadStatRespTimeAbove4   OBJECT-TYPE
    SYNTAX      Counter32
    UNITS       "seconds"
    MAX-ACCESS  read-only
    STATUS      current
    DESCRIPTION
        "The value of tmnxMobPdnRadStatRespTimeAbove4 indicates the number of 
         Access-Request/Access-Response messages received in more than 4 
         seconds after the Access-Request/Accounting-Request was generated.
         This should include messages received after the configured
         retry-timeout."
    ::= { tmnxMobPdnRadStatEntry 17 }

tmnxMobPdnRadStatRetries   OBJECT-TYPE
    SYNTAX      Counter32
    MAX-ACCESS  read-only
    STATUS      current
    DESCRIPTION
        "The value of tmnxMobPdnRadStatRetries indicates the number of
         retries done to send a RADIUS message. This counter covers all RADIUS
         message types the PGW/GGSN is sending."
    ::= { tmnxMobPdnRadStatEntry 18 }

tmnxMobPdnRadStatPrFinalTimeout  OBJECT-TYPE
    SYNTAX      Counter32
    MAX-ACCESS  read-only
    STATUS      current
    DESCRIPTION
        "The value of tmnxMobPdnRadStatPrFinalTimeout indicates the number of 
         times when PGW/GGSN has exhausted retries and timeouts for 
         Access-Request or Accounting-Request. "
    ::= { tmnxMobPdnRadStatEntry 19 }

tmnxMobPdnRadStatDiscReqRx   OBJECT-TYPE
    SYNTAX      Counter32
    MAX-ACCESS  read-only
    STATUS      current
    DESCRIPTION
        "The value of tmnxMobPdnRadStatDiscReqRx indicates the number of
         Disconnect-Request messages received by the PGW/GGSN."
    ::= { tmnxMobPdnRadStatEntry 20 }

tmnxMobPdnRadStatDiscAckTx   OBJECT-TYPE
    SYNTAX      Counter32
    MAX-ACCESS  read-only
    STATUS      current
    DESCRIPTION
        "The value of tmnxMobPdnRadStatDiscAckTx indicates the number of 
         Disconnect-ACK messages sent by the PGW/GGSN."
    ::= { tmnxMobPdnRadStatEntry 21 }

tmnxMobPdnRadStatDiscNakTx   OBJECT-TYPE
    SYNTAX      Counter32
    MAX-ACCESS  read-only
    STATUS      current
    DESCRIPTION
        "The value of tmnxMobPdnRadStatDiscNakTx indicates the number of
         The number of Disconnect-NAK messages sent by the PGW/GGSN."
    ::= { tmnxMobPdnRadStatEntry 22 }

tmnxMobPdnRadStatDiscMandAtrMiss   OBJECT-TYPE
    SYNTAX      Counter32
    MAX-ACCESS  read-only
    STATUS      current
    DESCRIPTION
        "The value of tmnxMobPdnRadStatDiscMandAtrMiss indicates the number of
         Disconnect-Request messages with missing mandatory attribute."
    ::= { tmnxMobPdnRadStatEntry 23 }

tmnxMobPdnRadStatDiscUnsupprAttr   OBJECT-TYPE
    SYNTAX      Counter32
    MAX-ACCESS  read-only
    STATUS      current
    DESCRIPTION
        "The value of tmnxMobPdnRadStatDiscUnsupprAttr indicates the number of
         Disconnect-Request messages with an unrecognized/unsupported
         attribute."
    ::= { tmnxMobPdnRadStatEntry 24 }

tmnxMobPdnRadStatDiscSessNotFnd   OBJECT-TYPE
    SYNTAX      Counter32
    MAX-ACCESS  read-only
    STATUS      current
    DESCRIPTION
        "The value of tmnxMobPdnRadStatDiscSessNotFnd indicates the number of
         inactive sessions found by Disconnect-Request messages."
    ::= { tmnxMobPdnRadStatEntry 25 }

tmnxMobPdnRadStatDiscAuthError   OBJECT-TYPE
    SYNTAX      Counter32
    MAX-ACCESS  read-only
    STATUS      current
    DESCRIPTION
        "The value of tmnxMobPdnRadStatDiscAuthError indicates the number of
         invalid authenticator values in the Disconnect-Request messages."
    ::= { tmnxMobPdnRadStatEntry 26 }

tmnxMobPdnRadStatDiscUnexpcCode   OBJECT-TYPE
    SYNTAX      Counter32
    MAX-ACCESS  read-only
    STATUS      current
    DESCRIPTION
        "The value of tmnxMobPdnRadStatDiscUnexpcCode indicates the number of
         unexpected messages recieved by the PGW/GGSN for Disconnect Requests."
    ::= { tmnxMobPdnRadStatEntry 27 }

tmnxMobPdnRadStatMsgFinalTimeout   OBJECT-TYPE
    SYNTAX      Counter32
    MAX-ACCESS  read-only
    STATUS      current
    DESCRIPTION
        "The value of tmnxMobPdnRadStatMsgFinalTimeout indicates the number of 
         times when PGW/GGSN has exhuasted its attempts to deliver this 
         message. "
    ::= { tmnxMobPdnRadStatEntry 28 }

--
--  Thresholds counters Table
--

tmnxMobPdnThresTable  OBJECT-TYPE
    SYNTAX      SEQUENCE OF TmnxMobPdnThresEntry
    MAX-ACCESS  not-accessible
    STATUS      current
    DESCRIPTION
        "The tmnxMobPdnThresTable has an entry for the set of thresholds  
         in each Packet Data Network Gateway (PGW)."
    ::= { tmnxMobPdnStatObjs 17 }

tmnxMobPdnThresEntry  OBJECT-TYPE
    SYNTAX      TmnxMobPdnThresEntry
    MAX-ACCESS  not-accessible
    STATUS      current
    DESCRIPTION
        "Each row entry represents a set of thresholds."
    INDEX { tmnxMobGwId }
    ::= { tmnxMobPdnThresTable 1 }

TmnxMobPdnThresEntry ::= SEQUENCE {
        tmnxMobPdnThresLastChanged        TimeStamp,
        tmnxMobPdnThresBrMgmtLmtUe        Gauge32,
        tmnxMobPdnThresBrMgmtLmtBr        Gauge32,
        tmnxMobPdnThresBrMgmtLmtDefBr     Gauge32,
        tmnxMobPdnThresBrMgmtLmtDedBr     Gauge32,
        tmnxMobPdnThresBrMgmtLmtActBr     Gauge32,
        tmnxMobPdnThresBrMgmtLmtUePgd     Gauge32,
        tmnxMobPdnThresBrMgmtCfsAttch     Gauge32,
        tmnxMobPdnThresBrMgmtCfsDedBr     Gauge32,
        tmnxMobPdnThresBrMgmtCfsReloc     Gauge32,
        tmnxMobPdnThresBrMgmtCffAttch     Gauge32,
        tmnxMobPdnThresBrMgmtCffDedBr     Gauge32,
        tmnxMobPdnThresBrMgmtCffHdOver    Gauge32,
        tmnxMobPdnThresBrMgmtCffSrUnavl   Gauge32,
        tmnxMobPdnThresBrTrfcThrptUL      Gauge32,
        tmnxMobPdnThresBrTrfcThrptDL      Gauge32,
        tmnxMobPdnThresBrTrfcAspFail      Gauge32,
        tmnxMobPdnThresBrTrfcBrBdvErr     Gauge32,
        tmnxMobPdnThresPthMgmtS5Fail      Gauge32,
        tmnxMobPdnThresPthMgmtS5Restart   Gauge32,
        tmnxMobPdnThresPthMgmtS5NoResp    Gauge32,
        tmnxMobPdnThresPthMgmtS5Peer      Gauge32,
        tmnxMobPdnThresPthMgmtS8Peer      Gauge32,
        tmnxMobPdnThresPthMgmtGxFail      Gauge32,
        tmnxMobPdnThresPthMgmtRfFail      Gauge32
    }

tmnxMobPdnThresLastChanged  OBJECT-TYPE
    SYNTAX      TimeStamp
    MAX-ACCESS  read-only
    STATUS      current
    DESCRIPTION
        "The value of tmnxMobPdnThresLastChanged indicates the timestamp of
         the last change to this row in tmnxMobPdnThresTable."
    ::= { tmnxMobPdnThresEntry 1 }

tmnxMobPdnThresBrMgmtLmtUe  OBJECT-TYPE
    SYNTAX      Gauge32
    MAX-ACCESS  read-only
    STATUS      current
    DESCRIPTION
        "The value of tmnxMobPdnThresBrMgmtLmtUe indicates the number of 
         User Equipments(UE)."
    ::= { tmnxMobPdnThresEntry 2 }  

tmnxMobPdnThresBrMgmtLmtBr  OBJECT-TYPE
    SYNTAX      Gauge32
    MAX-ACCESS  read-only
    STATUS      current
    DESCRIPTION
        "The value of tmnxMobPdnThresBrMgmtLmtBr indicates the number of 
         bearers."
    ::= { tmnxMobPdnThresEntry 3 }  

tmnxMobPdnThresBrMgmtLmtDefBr  OBJECT-TYPE
    SYNTAX      Gauge32
    MAX-ACCESS  read-only
    STATUS      current
    DESCRIPTION
        "The value of tmnxMobPdnThresBrMgmtLmtDefBr indicates the number of 
         default bearers."
    ::= { tmnxMobPdnThresEntry 4 }  

tmnxMobPdnThresBrMgmtLmtDedBr  OBJECT-TYPE
    SYNTAX      Gauge32
    MAX-ACCESS  read-only
    STATUS      current
    DESCRIPTION
        "The value of tmnxMobPdnThresBrMgmtLmtDedBr indicates the number of 
         dedicated bearers."
    ::= { tmnxMobPdnThresEntry 5 }  

tmnxMobPdnThresBrMgmtLmtActBr  OBJECT-TYPE
    SYNTAX      Gauge32
    MAX-ACCESS  read-only
    STATUS      current
    DESCRIPTION
        "The value of tmnxMobPdnThresBrMgmtLmtActBr indicates the number of 
         active bearers."
    ::= { tmnxMobPdnThresEntry 6 }  

tmnxMobPdnThresBrMgmtLmtUePgd  OBJECT-TYPE
    SYNTAX      Gauge32
    MAX-ACCESS  read-only
    STATUS      current
    DESCRIPTION
        "The value of tmnxMobPdnThresBrMgmtLmtUePgd indicates the number of 
         idle User Equipment (UE) paged."
    ::= { tmnxMobPdnThresEntry 7 }  

tmnxMobPdnThresBrMgmtCfsAttch  OBJECT-TYPE
    SYNTAX      Gauge32
    MAX-ACCESS  read-only
    STATUS      current
    DESCRIPTION
        "The value of tmnxMobPdnThresBrMgmtCfsAttch indicates the number of 
         attaches (call setups)."
    ::= { tmnxMobPdnThresEntry 8 }  

tmnxMobPdnThresBrMgmtCfsDedBr  OBJECT-TYPE
    SYNTAX      Gauge32
    MAX-ACCESS  read-only
    STATUS      current
    DESCRIPTION
        "The value of tmnxMobPdnThresBrMgmtCfsDedBr indicates the number of 
         dedicated bearers setups (call-flows)."
    ::= { tmnxMobPdnThresEntry 9 }  

tmnxMobPdnThresBrMgmtCfsReloc  OBJECT-TYPE
    SYNTAX      Gauge32
    MAX-ACCESS  read-only
    STATUS      current
    DESCRIPTION
        "The value of tmnxMobPdnThresBrMgmtCfsReloc indicates the number of 
         inter Serving Gateway relocations."
    ::= { tmnxMobPdnThresEntry 10 }  

tmnxMobPdnThresBrMgmtCffAttch  OBJECT-TYPE
    SYNTAX      Gauge32 (0..100)
    UNITS       "Percent"
    MAX-ACCESS  read-only
    STATUS      current
    DESCRIPTION
        "The value of tmnxMobPdnThresBrMgmtCffAttch indicates the percentage 
         of default bearer setup failures. It is calculated as 
         (default bearer setup failures / all default bearer setups) * 100"
    ::= { tmnxMobPdnThresEntry 11 }  

tmnxMobPdnThresBrMgmtCffDedBr  OBJECT-TYPE
    SYNTAX      Gauge32 (0..100)
    UNITS       "Percent"
    MAX-ACCESS  read-only
    STATUS      current
    DESCRIPTION
        "The value of tmnxMobPdnThresBrMgmtCffDedBr indicates the percentage of 
         dedicated bearer setup failures. It is calculated as
         (dedicated bearer setup failures / all dedicated bearer setups) * 100"
    ::= { tmnxMobPdnThresEntry 12 }  

tmnxMobPdnThresBrMgmtCffHdOver  OBJECT-TYPE
    SYNTAX      Gauge32 (0..100)
    UNITS       "Percent"
    MAX-ACCESS  read-only
    STATUS      current
    DESCRIPTION
        "The value of tmnxMobPdnThresBrMgmtCffHdOver indicates the percentage 
         of inter Serving Gateway handover failures. It is calculated as
         (inter serving gateway handover failures / all inter serving gateway
         handovers) * 100"
    ::= { tmnxMobPdnThresEntry 13 }  

tmnxMobPdnThresBrMgmtCffSrUnavl  OBJECT-TYPE
    SYNTAX      Gauge32 (0..100)
    UNITS       "Percent"
    MAX-ACCESS  read-only
    STATUS      current
    DESCRIPTION
        "The value of tmnxMobPdnThresBrMgmtCffSrUnavl indicates the percentage 
         of failures due to system resources unavailable. It is calculated as
        (failures due to system resources unavailable / total failures) * 100"
    ::= { tmnxMobPdnThresEntry 14 }  

tmnxMobPdnThresBrTrfcThrptUL  OBJECT-TYPE
    SYNTAX      Gauge32
    UNITS       "megabytes"
    MAX-ACCESS  read-only
    STATUS      current
    DESCRIPTION
        "The value of tmnxMobPdnThresBrTrfcThrptUL indicates the uplink 
         traffic throughput in mega-bytes per polling period."
    ::= { tmnxMobPdnThresEntry 15 }  

tmnxMobPdnThresBrTrfcThrptDL  OBJECT-TYPE
    SYNTAX      Gauge32
    UNITS       "megabytes"
    MAX-ACCESS  read-only
    STATUS      current
    DESCRIPTION
        "The value of tmnxMobPdnThresBrTrfcThrptDL indicates the downlink 
         traffic throughput in mega-bytes per polling period."
    ::= { tmnxMobPdnThresEntry 16 }  

tmnxMobPdnThresBrTrfcAspFail  OBJECT-TYPE
    SYNTAX      Gauge32
    MAX-ACCESS  read-only
    STATUS      current
    DESCRIPTION
        "The value of tmnxMobPdnThresBrTrfcAspFail indicates the number of 
         anti-spoof failure detections."
    ::= { tmnxMobPdnThresEntry 17 }  

tmnxMobPdnThresBrTrfcBrBdvErr  OBJECT-TYPE
    SYNTAX      Gauge32
    MAX-ACCESS  read-only
    STATUS      current
    DESCRIPTION
        "The value of tmnxMobPdnThresBrTrfcBrBdvErr indicates the number of 
         bearer binding verification errros."
    ::= { tmnxMobPdnThresEntry 18 }  

tmnxMobPdnThresPthMgmtS5Fail  OBJECT-TYPE
    SYNTAX      Gauge32
    MAX-ACCESS  read-only
    STATUS      current
    DESCRIPTION
        "The value of tmnxMobPdnThresPthMgmtS5Fail indicates the number of 
         S5 path management failures."
    ::= { tmnxMobPdnThresEntry 19 }  

tmnxMobPdnThresPthMgmtS5Restart  OBJECT-TYPE
    SYNTAX      Gauge32
    MAX-ACCESS  read-only
    STATUS      current
    DESCRIPTION
        "The value of tmnxMobPdnThresPthMgmtS5Restart indicates the number of 
         S5 restarts."
    ::= { tmnxMobPdnThresEntry 20 }  

tmnxMobPdnThresPthMgmtS5NoResp  OBJECT-TYPE
    SYNTAX      Gauge32
    MAX-ACCESS  read-only
    STATUS      current
    DESCRIPTION
        "The value of tmnxMobPdnThresPthMgmtS5NoResp indicates the number of 
         S5 peer not responding to requests."
    ::= { tmnxMobPdnThresEntry 21 }  

tmnxMobPdnThresPthMgmtS5Peer  OBJECT-TYPE
    SYNTAX      Gauge32
    MAX-ACCESS  read-only
    STATUS      current
    DESCRIPTION
        "The value of tmnxMobPdnThresPthMgmtS5Peer indicates the number of 
         S5 peers."
    ::= { tmnxMobPdnThresEntry 22 }  

tmnxMobPdnThresPthMgmtS8Peer  OBJECT-TYPE
    SYNTAX      Gauge32
    MAX-ACCESS  read-only
    STATUS      current
    DESCRIPTION
        "The value of tmnxMobPdnThresPthMgmtS8Peer indicates the number of 
         s8 peers."
    ::= { tmnxMobPdnThresEntry 23 }  

tmnxMobPdnThresPthMgmtGxFail  OBJECT-TYPE
    SYNTAX      Gauge32
    MAX-ACCESS  read-only
    STATUS      current
    DESCRIPTION
        "The value of tmnxMobPdnThresPthMgmtGxFail indicates the number of 
         Gx failures."
    ::= { tmnxMobPdnThresEntry 24 }  

tmnxMobPdnThresPthMgmtRfFail  OBJECT-TYPE
    SYNTAX      Gauge32
    MAX-ACCESS  read-only
    STATUS      current
    DESCRIPTION
        "The value of tmnxMobPdnThresPthMgmtRfFail indicates the number of 
         Rf failures."
    ::= { tmnxMobPdnThresEntry 25 }

--
--  Gp table
--

tmnxMobPdnGpTableLastChanged  OBJECT-TYPE
    SYNTAX      TimeStamp
    MAX-ACCESS  read-only
    STATUS      current
    DESCRIPTION
        "The value of tmnxMobPdnGpTableLastChanged indicates the sysUpTime at
         the time of the last modification to tmnxMobPdnGpTable by adding,
         deleting an entry or change to a writable object in the table.

         If no changes were made to the table since the last re-initialization
         of the local network management subsystem, then this object contains
         a zero value."
    ::= { tmnxMobPdnGlobalObjs 26 }

tmnxMobPdnGpTable  OBJECT-TYPE
    SYNTAX      SEQUENCE OF TmnxMobPdnGpEntry
    MAX-ACCESS  not-accessible
    STATUS      current
    DESCRIPTION
        "The tmnxMobPdnGpTable provides an extension of the tmnxMobPdnTable
         for Gp reference point configuration."
    ::= { tmnxMobPdnConfObjs 22 }

tmnxMobPdnGpEntry  OBJECT-TYPE
    SYNTAX      TmnxMobPdnGpEntry
    MAX-ACCESS  not-accessible
    STATUS      current
    DESCRIPTION
        "Each row entry represents additional columns for Gp reference point
         configuration for a Packet Data Network Gateway (PGW)."
    AUGMENTS { tmnxMobPdnEntry }
    ::= { tmnxMobPdnGpTable 1 }

TmnxMobPdnGpEntry ::= SEQUENCE {
        tmnxMobPdnGpLastChanged        TimeStamp,
        tmnxMobPdnGpGtpcIfVRtrId       TmnxVRtrID,
        tmnxMobPdnGpGtpcIfIndex        InterfaceIndexOrZero,
        tmnxMobPdnGpGtpuIfVRtrId       TmnxVRtrID,
        tmnxMobPdnGpGtpuIfIndex        InterfaceIndexOrZero,
        tmnxMobPdnGpGtpcProfile        TmnxMobProfNameOrEmpty,
        tmnxMobPdnGpGtpuProfile        TmnxMobProfNameOrEmpty,
        tmnxMobPdnGpPeerList           TmnxMobProfNameOrEmpty
    }

tmnxMobPdnGpLastChanged  OBJECT-TYPE
    SYNTAX      TimeStamp
    MAX-ACCESS  read-only
    STATUS      current
    DESCRIPTION
        "The value of tmnxMobPdnGpLastChanged indicates the timestamp of
         the last change to this row in tmnxMobPdnGpTable."
    ::= { tmnxMobPdnGpEntry 1 }

tmnxMobPdnGpGtpcIfVRtrId  OBJECT-TYPE
    SYNTAX      TmnxVRtrID
    MAX-ACCESS  read-write
    STATUS      current
    DESCRIPTION
        "The value of tmnxMobPdnGpGtpcIfVRtrId specifies the virtual
         router to which the interface specified by tmnxMobPdnGpGtpcIfIndex
         belongs."
    DEFVAL { 1 }
    ::= { tmnxMobPdnGpEntry 2 }

tmnxMobPdnGpGtpcIfIndex  OBJECT-TYPE
    SYNTAX      InterfaceIndexOrZero
    MAX-ACCESS  read-write
    STATUS      current
    DESCRIPTION
        "The value of tmnxMobPdnGpGtpcIfIndex specifies the interface
         index of the local interface used for the General Packet Radio
         Services Tunneling Protocol for Control Plane (GTP-C) signaling.
         When the value of this object is set to 0, no interface has
         been assigned."
    DEFVAL { 0 }
    ::= { tmnxMobPdnGpEntry 3 }

tmnxMobPdnGpGtpuIfVRtrId  OBJECT-TYPE
    SYNTAX      TmnxVRtrID
    MAX-ACCESS  read-write
    STATUS      current
    DESCRIPTION
        "The value of tmnxMobPdnGpGtpuIfVRtrId specifies the virtual
         router to which the interface specified by tmnxMobPdnGpGtpuIfIndex
         belongs."
    DEFVAL { 1 }
    ::= { tmnxMobPdnGpEntry 4 }

tmnxMobPdnGpGtpuIfIndex  OBJECT-TYPE
    SYNTAX      InterfaceIndexOrZero
    MAX-ACCESS  read-write
    STATUS      current
    DESCRIPTION
        "The value of tmnxMobPdnGpGtpuIfIndex specifies the interface
         index of the local interface used for the General Packet Radio
         Services Tunneling Protocol for User Plane (GTP-U) signaling.
         When the value of this object is set to 0, no interface has
         been assigned."
    DEFVAL { 0 }
    ::= { tmnxMobPdnGpEntry 5 }

tmnxMobPdnGpGtpcProfile  OBJECT-TYPE
    SYNTAX      TmnxMobProfNameOrEmpty
    MAX-ACCESS  read-write
    STATUS      current
    DESCRIPTION
        "The value of tmnxMobPdnGpGtpcProfile specifies the GPRS Tunneling
         Protocol-Control plane (GTP-C) profile name. The GTP-C profile provides
         GTP-C signaling related configuration.

         If a corresponding GTP profile does not exist in
         TIMETRA-MOBILE-PROFILE-MIB::tmnxMobProfGtpTable,
         an 'inconsistentValue' error will be returned."
    DEFVAL { ''H }
    ::= { tmnxMobPdnGpEntry 6 }

tmnxMobPdnGpGtpuProfile  OBJECT-TYPE
    SYNTAX      TmnxMobProfNameOrEmpty
    MAX-ACCESS  read-write
    STATUS      current
    DESCRIPTION
        "The value of tmnxMobPdnGpGtpuProfile specifies the GPRS Tunneling
         Protocol-User plane (GTP-U) profile name. The GTP-U profile provides
         GTP-U signaling related configuration.

         If a corresponding GTP profile does not exist in
         TIMETRA-MOBILE-PROFILE-MIB::tmnxMobProfGtpTable,
         an 'inconsistentValue' error will be returned."
    DEFVAL { ''H }
    ::= { tmnxMobPdnGpEntry 7 }

tmnxMobPdnGpPeerList  OBJECT-TYPE
    SYNTAX      TmnxMobProfNameOrEmpty
    MAX-ACCESS  read-write
    STATUS      current
    DESCRIPTION
        "The value of tmnxMobPdnGpPeerList specifies the GPRS Tunneling
         Protocol (GTP) peer list. 

         If a corresponding GTP peer list does not exist in
         TIMETRA-MOBILE-PROFILE-MIB::tmnxMobProfPeerListTable,
         an 'inconsistentValue' error will be returned."
    DEFVAL { ''H }
    ::= { tmnxMobPdnGpEntry 8 }

--
--  Gp peer list table
--

tmnxMobPdnGpPeerTableLastChanged     OBJECT-TYPE
    SYNTAX      TimeStamp
    MAX-ACCESS  read-only
    STATUS      current
    DESCRIPTION
        "The value of tmnxMobPdnGpPeerTableLastChanged indicates the sysUpTime at
         the time of the last modification to tmnxMobPdnGpPeerTable by adding,
         deleting an entry or change to a writable object in the table.

         If no changes were made to the table since the last re-initialization
         of the local network management subsystem, then this object contains
         a zero value."
    ::= { tmnxMobPdnGlobalObjs 27 }

tmnxMobPdnGpPeerTable  OBJECT-TYPE
    SYNTAX      SEQUENCE OF TmnxMobPdnGpPeerEntry
    MAX-ACCESS  not-accessible
    STATUS      current
    DESCRIPTION
        "The tmnxMobPdnGpPeerTable has an entry for each peer on the Gp
         reference point."
    ::= { tmnxMobPdnConfObjs 23 }

tmnxMobPdnGpPeerEntry  OBJECT-TYPE
    SYNTAX      TmnxMobPdnGpPeerEntry
    MAX-ACCESS  not-accessible
    STATUS      current
    DESCRIPTION
        "Each row entry represents a peer on the Gp reference point."
    INDEX { vRtrID,
            tmnxMobPdnGpPeerAddressType,
            tmnxMobPdnGpPeerAddress,
            tmnxMobPdnGpPeerPort
          }
    ::= { tmnxMobPdnGpPeerTable 1 }

TmnxMobPdnGpPeerEntry ::= SEQUENCE {
        tmnxMobPdnGpPeerAddressType        InetAddressType,
        tmnxMobPdnGpPeerAddress            InetAddress,
        tmnxMobPdnGpPeerPort               InetPortNumber,
        tmnxMobPdnGpPeerLastChanged        TimeStamp,
        tmnxMobPdnGpPeerCreateTime         TimeStamp,
        tmnxMobPdnGpPeerPathMgmtState      TmnxMobPathMgmtState,
        tmnxMobPdnGpPeerGatewayId          TmnxMobGwId,
        tmnxMobPdnGpPeerType               TmnxMobPeerType
    }

tmnxMobPdnGpPeerAddressType  OBJECT-TYPE
    SYNTAX      InetAddressType
    MAX-ACCESS  not-accessible
    STATUS      current
    DESCRIPTION
        "The value of tmnxMobPdnGpPeerAddressType indicates the type of
         address represented by tmnxMobPdnGpPeerAddress."
    ::= { tmnxMobPdnGpPeerEntry 1 }

tmnxMobPdnGpPeerAddress  OBJECT-TYPE
    SYNTAX      InetAddress (SIZE (4|16))
    MAX-ACCESS  not-accessible
    STATUS      current
    DESCRIPTION
        "The value of tmnxMobPdnGpPeerAddress indicates the IP address of the
         peer on Gp reference point."
    ::= { tmnxMobPdnGpPeerEntry 2 }

tmnxMobPdnGpPeerPort  OBJECT-TYPE
    SYNTAX      InetPortNumber
    MAX-ACCESS  not-accessible
    STATUS      current
    DESCRIPTION
        "The value of tmnxMobPdnGpPeerPort indicates the port number of this
         peer."
    ::= { tmnxMobPdnGpPeerEntry 3 }

tmnxMobPdnGpPeerLastChanged  OBJECT-TYPE
    SYNTAX      TimeStamp
    MAX-ACCESS  read-only
    STATUS      current
    DESCRIPTION
        "The value of tmnxMobPdnGpPeerLastChanged indicates the timestamp of
         the last change to this row in tmnxMobPdnGpPeerTable."
    ::= { tmnxMobPdnGpPeerEntry 4 }

tmnxMobPdnGpPeerCreateTime  OBJECT-TYPE
    SYNTAX      TimeStamp
    MAX-ACCESS  read-only
    STATUS      current
    DESCRIPTION
        "The value of tmnxMobPdnGpPeerCreateTime indicates the sysUpTime when
         this entry was created."
    ::= { tmnxMobPdnGpPeerEntry 5 }

tmnxMobPdnGpPeerPathMgmtState  OBJECT-TYPE
    SYNTAX      TmnxMobPathMgmtState
    MAX-ACCESS  read-only
    STATUS      current
    DESCRIPTION
        "The value of tmnxMobPdnGpPeerPathMgmtState indicates the state of
         path."
    ::= { tmnxMobPdnGpPeerEntry 6 }

tmnxMobPdnGpPeerGatewayId  OBJECT-TYPE
    SYNTAX      TmnxMobGwId
    MAX-ACCESS  read-only
    STATUS      current
    DESCRIPTION
        "The value of tmnxMobPdnGpPeerGatewayId indicates the gateway 
         to which this peer belongs."
    ::= { tmnxMobPdnGpPeerEntry 7 }

tmnxMobPdnGpPeerType  OBJECT-TYPE
    SYNTAX      TmnxMobPeerType
    MAX-ACCESS  read-only
    STATUS      current
    DESCRIPTION
        "The value of tmnxMobPdnGpPeerType indicates the type of this peer."
    ::= { tmnxMobPdnGpPeerEntry 8 }

--
--  Gp Stats Table
--

tmnxMobPdnGpStatTable  OBJECT-TYPE
    SYNTAX      SEQUENCE OF TmnxMobPdnGpStatEntry
    MAX-ACCESS  not-accessible
    STATUS      current
    DESCRIPTION
        "The tmnxMobPdnGpStatTable has an entry for each peer on the Gp
         reference point."
    ::= { tmnxMobPdnStatObjs 18 }

tmnxMobPdnGpStatEntry  OBJECT-TYPE
    SYNTAX      TmnxMobPdnGpStatEntry
    MAX-ACCESS  not-accessible
    STATUS      current
    DESCRIPTION
        "Each row entry represents a peer on the Gp reference point
         and contains statistics for this peer on a card."
    INDEX { vRtrID,
            tmnxMobPdnGpPeerAddressType,
            tmnxMobPdnGpPeerAddress,
            tmnxMobPdnGpPeerPort,
            tmnxChassisIndex,
            tmnxCardSlotNum
          }
    ::= { tmnxMobPdnGpStatTable 1 }

TmnxMobPdnGpStatEntry ::= SEQUENCE {
        tmnxMobPdnGpStatCreatePdpReq       Counter32,
        tmnxMobPdnGpStatCreatePdpRsp       Counter32,
        tmnxMobPdnGpStatDeletePdpReq       Counter32,
        tmnxMobPdnGpStatDeletePdpRsp       Counter32,
        tmnxMobPdnGpStatModifyPdpReq       Counter32,
        tmnxMobPdnGpStatModifyPdpRsp       Counter32,
        tmnxMobPdnGpStatRxEchoRequests     Counter32,
        tmnxMobPdnGpStatTxEchoResponses    Counter32,
        tmnxMobPdnGpStatTxEchoRequests     Counter32,
        tmnxMobPdnGpStatRxEchoResponses    Counter32,
        tmnxMobPdnGpStatRxErrorsIndCnt     Counter32,
        tmnxMobPdnGpStatTxErrorsIndCnt     Counter32,
        tmnxMobPdnGpStatRxMalformedPkts    Counter32,
        tmnxMobPdnGpStatRxUnknownPkts      Counter32,
        tmnxMobPdnGpStatRxMissingIePkts    Counter32,
        tmnxMobPdnGpStatPeerRestarts       Counter32,
        tmnxMobPdnGpStatPeerRestrtCount    Counter32,
        tmnxMobPdnGpStatPathMgmtFails      Counter32        
    }
tmnxMobPdnGpStatCreatePdpReq  OBJECT-TYPE
    SYNTAX      Counter32
    MAX-ACCESS  read-only
    STATUS      current
    DESCRIPTION
        "The value of tmnxMobPdnGpStatCreatePdpReq indicates the number of
         create Packet Data Protocol (PDP) request messages received from this
         peer or transmitted to this peer."
    ::= { tmnxMobPdnGpStatEntry 1 }

tmnxMobPdnGpStatCreatePdpRsp  OBJECT-TYPE
    SYNTAX      Counter32
    MAX-ACCESS  read-only
    STATUS      current
    DESCRIPTION
        "The value of tmnxMobPdnGpStatCreatePdpRsp indicates the number of
         create Packet Data Protocol (PDP) response messages received from this
         peer or transmitted to this peer."
    ::= { tmnxMobPdnGpStatEntry 2 }

tmnxMobPdnGpStatDeletePdpReq  OBJECT-TYPE
    SYNTAX      Counter32
    MAX-ACCESS  read-only
    STATUS      current
    DESCRIPTION
        "The value of tmnxMobPdnGpStatDeletePdpReq indicates the number of
         delete Packet Data Protocol (PDP) request messages received from this
         peer or transmitted to this peer."
    ::= { tmnxMobPdnGpStatEntry 3 }

tmnxMobPdnGpStatDeletePdpRsp  OBJECT-TYPE
    SYNTAX      Counter32
    MAX-ACCESS  read-only
    STATUS      current
    DESCRIPTION
        "The value of tmnxMobPdnGpStatDeletePdpRsp indicates the number of
         delete Packet Data Protocol (PDP) response messages received from this
         peer or transmitted to this peer."
    ::= { tmnxMobPdnGpStatEntry 4 }

tmnxMobPdnGpStatModifyPdpReq  OBJECT-TYPE
    SYNTAX      Counter32
    MAX-ACCESS  read-only
    STATUS      current
    DESCRIPTION
        "The value of tmnxMobPdnGpStatModifyPdpReq indicates the number of
         modify Packet Data Protocol (PDP) request messages received from this
         peer or transmitted to this peer."
    ::= { tmnxMobPdnGpStatEntry 5 }

tmnxMobPdnGpStatModifyPdpRsp  OBJECT-TYPE
    SYNTAX      Counter32
    MAX-ACCESS  read-only
    STATUS      current
    DESCRIPTION
        "The value of tmnxMobPdnGpStatModifyPdpRsp indicates the number of
         modify Packet Data Protocol (PDP) response messages received from this
         peer or transmitted to this peer."
    ::= { tmnxMobPdnGpStatEntry 6 }

tmnxMobPdnGpStatRxEchoRequests  OBJECT-TYPE
    SYNTAX      Counter32
    MAX-ACCESS  read-only
    STATUS      current
    DESCRIPTION
        "The value of tmnxMobPdnGpStatRxEchoRequests indicates the number of
         echo request messages received from this peer."
    ::= { tmnxMobPdnGpStatEntry 7 }

tmnxMobPdnGpStatTxEchoResponses  OBJECT-TYPE
    SYNTAX      Counter32
    MAX-ACCESS  read-only
    STATUS      current
    DESCRIPTION
        "The value of tmnxMobPdnGpStatTxEchoResponses indicates the number of
         echo response messages transmitted to this peer."
    ::= { tmnxMobPdnGpStatEntry 8 }

tmnxMobPdnGpStatTxEchoRequests  OBJECT-TYPE
    SYNTAX      Counter32
    MAX-ACCESS  read-only
    STATUS      current
    DESCRIPTION
        "The value of tmnxMobPdnGpStatTxEchoRequests indicates the number of
         echo request messages transmitted to this peer."
    ::= { tmnxMobPdnGpStatEntry 9 }

tmnxMobPdnGpStatRxEchoResponses  OBJECT-TYPE
    SYNTAX      Counter32
    MAX-ACCESS  read-only
    STATUS      current
    DESCRIPTION
        "The value of tmnxMobPdnGpStatRxEchoResponses indicates the number of
         echo response messages received from this peer."
    ::= { tmnxMobPdnGpStatEntry 10 }

tmnxMobPdnGpStatRxErrorsIndCnt  OBJECT-TYPE
    SYNTAX      Counter32
    MAX-ACCESS  read-only
    STATUS      current
    DESCRIPTION
        "The value of tmnxMobPdnGpStatRxErrorsIndCnt indicates the number of
         indication request errors transmitted to this peer."
    ::= { tmnxMobPdnGpStatEntry 11 }

tmnxMobPdnGpStatTxErrorsIndCnt  OBJECT-TYPE
    SYNTAX      Counter32
    MAX-ACCESS  read-only
    STATUS      current
    DESCRIPTION
        "The value of tmnxMobPdnGpStatTxErrorsIndCnt indicates the number of
         indication response errors received from this peer."
    ::= { tmnxMobPdnGpStatEntry 12 }

tmnxMobPdnGpStatRxMalformedPkts  OBJECT-TYPE
    SYNTAX      Counter32
    MAX-ACCESS  read-only
    STATUS      current
    DESCRIPTION
        "The value of tmnxMobPdnGpStatRxMalformedPkts indicates the number of
         malformed packets received from this peer."
    ::= { tmnxMobPdnGpStatEntry 13 }

tmnxMobPdnGpStatRxUnknownPkts  OBJECT-TYPE
    SYNTAX      Counter32
    MAX-ACCESS  read-only
    STATUS      current
    DESCRIPTION
        "The value of tmnxMobPdnGpStatRxUnknownPkts indicates the number of
         unknown message type packets received from this peer."
    ::= { tmnxMobPdnGpStatEntry 14 }

tmnxMobPdnGpStatRxMissingIePkts  OBJECT-TYPE
    SYNTAX      Counter32
    MAX-ACCESS  read-only
    STATUS      current
    DESCRIPTION
        "The value of tmnxMobPdnGpStatRxMissingIePkts indicates the number of
         missing mandatory Information Element (IE) packets received from this
         peer."
    ::= { tmnxMobPdnGpStatEntry 15 }

tmnxMobPdnGpStatPeerRestarts  OBJECT-TYPE
    SYNTAX      Counter32
    MAX-ACCESS  read-only
    STATUS      current
    DESCRIPTION
        "The value of tmnxMobPdnGpStatPeerRestarts indicates the number of
         times this peer restarted after registering with the system."
    ::= { tmnxMobPdnGpStatEntry 16 }

tmnxMobPdnGpStatPeerRestrtCount  OBJECT-TYPE
    SYNTAX      Counter32
    MAX-ACCESS  read-only
    STATUS      current
    DESCRIPTION
        "The value of tmnxMobPdnGpStatPeerRestrtCount indicates the counter
         value of the number of times this peer restarted."
    ::= { tmnxMobPdnGpStatEntry 17 }

tmnxMobPdnGpStatPathMgmtFails  OBJECT-TYPE
    SYNTAX      Counter32
    MAX-ACCESS  read-only
    STATUS      current
    DESCRIPTION
        "The value of tmnxMobPdnGpStatPathMgmtFails indicates the number of
         path management failures for this peer."
    ::= { tmnxMobPdnGpStatEntry 18 }


--
--  S2a peer stats table
--

tmnxMobPdnS2aPeerTblLastChanged     OBJECT-TYPE
    SYNTAX      TimeStamp
    MAX-ACCESS  read-only
    STATUS      current
    DESCRIPTION
        "The value of tmnxMobPdnS2aPeerTblLastChanged indicates the sysUpTime at
         the time of the last modification to tmnxMobPdnS2aPeerTable by adding,
         deleting an entry or change to a writable object in the table.

         If no changes were made to the table since the last re-initialization
         of the local network management subsystem, then this object contains
         a zero value."
    ::= { tmnxMobPdnGlobalObjs 28 }

tmnxMobPdnS2aPeerTable  OBJECT-TYPE
    SYNTAX      SEQUENCE OF TmnxMobPdnS2aPeerEntry
    MAX-ACCESS  not-accessible
    STATUS      current
    DESCRIPTION
        "The tmnxMobPdnS2aPeerTable has an entry for each peer on the S2a
         reference point."
    ::= { tmnxMobPdnStatObjs 19 }

tmnxMobPdnS2aPeerEntry  OBJECT-TYPE
    SYNTAX      TmnxMobPdnS2aPeerEntry
    MAX-ACCESS  not-accessible
    STATUS      current
    DESCRIPTION
        "Each row entry represents a peer on the S2a reference point."
    INDEX { vRtrID,
            tmnxMobPdnS2aPeerAddressType,
            tmnxMobPdnS2aPeerAddress,
            tmnxMobPdnS2aPeerPort
          }
    ::= { tmnxMobPdnS2aPeerTable 1 }

TmnxMobPdnS2aPeerEntry ::= SEQUENCE {
        tmnxMobPdnS2aPeerAddressType        InetAddressType,
        tmnxMobPdnS2aPeerAddress            InetAddress,
        tmnxMobPdnS2aPeerPort               InetPortNumber,
        tmnxMobPdnS2aPeerLastChanged        TimeStamp,
        tmnxMobPdnS2aPeerCreateTime         TimeStamp,
        tmnxMobPdnS2aPeerPathMgmtState      TmnxMobPathMgmtState,
        tmnxMobPdnS2aPeerGatewayId          TmnxMobGwId,
        tmnxMobPdnS2aPeerType               TmnxMobPeerType,
        tmnxMobPdnS2aPeerHBCompatible       TruthValue
    }

tmnxMobPdnS2aPeerAddressType  OBJECT-TYPE
    SYNTAX      InetAddressType
    MAX-ACCESS  not-accessible
    STATUS      current
    DESCRIPTION
        "The value of tmnxMobPdnS2aPeerAddressType indicates the type of
         address represented by tmnxMobPdnS2aPeerAddress."
    ::= { tmnxMobPdnS2aPeerEntry 1 }

tmnxMobPdnS2aPeerAddress  OBJECT-TYPE
    SYNTAX      InetAddress (SIZE (4|16))
    MAX-ACCESS  not-accessible
    STATUS      current
    DESCRIPTION
        "The value of tmnxMobPdnS2aPeerAddress indicates the IP address of the
         peer on S2a reference point."
    ::= { tmnxMobPdnS2aPeerEntry 2 }

tmnxMobPdnS2aPeerPort  OBJECT-TYPE
    SYNTAX      InetPortNumber
    MAX-ACCESS  not-accessible
    STATUS      current
    DESCRIPTION
        "The value of tmnxMobPdnS2aPeerPort indicates the port number of this
         peer."
    ::= { tmnxMobPdnS2aPeerEntry 3 }

tmnxMobPdnS2aPeerLastChanged  OBJECT-TYPE
    SYNTAX      TimeStamp
    MAX-ACCESS  read-only
    STATUS      current
    DESCRIPTION
        "The value of tmnxMobPdnS2aPeerLastChanged indicates the timestamp of
         the last change to this row in tmnxMobPdnS2aPeerTable."
    ::= { tmnxMobPdnS2aPeerEntry 4 }

tmnxMobPdnS2aPeerCreateTime  OBJECT-TYPE
    SYNTAX      TimeStamp
    MAX-ACCESS  read-only
    STATUS      current
    DESCRIPTION
        "The value of tmnxMobPdnS2aPeerCreateTime indicates the sysUpTime when
         this entry was created."
    ::= { tmnxMobPdnS2aPeerEntry 5 }

tmnxMobPdnS2aPeerPathMgmtState  OBJECT-TYPE
    SYNTAX      TmnxMobPathMgmtState
    MAX-ACCESS  read-only
    STATUS      current
    DESCRIPTION
        "The value of tmnxMobPdnS2aPeerPathMgmtState indicates the state of
         path."
    ::= { tmnxMobPdnS2aPeerEntry 6 }

tmnxMobPdnS2aPeerGatewayId  OBJECT-TYPE
    SYNTAX      TmnxMobGwId
    MAX-ACCESS  read-only
    STATUS      current
    DESCRIPTION
        "The value of tmnxMobPdnS2aPeerGatewayId indicates the gateway 
         to which this peer belongs."
    ::= { tmnxMobPdnS2aPeerEntry 7 }

tmnxMobPdnS2aPeerType  OBJECT-TYPE
    SYNTAX      TmnxMobPeerType
    MAX-ACCESS  read-only
    STATUS      current
    DESCRIPTION
        "The value of tmnxMobPdnS2aPeerType indicates the type of this peer."
    ::= { tmnxMobPdnS2aPeerEntry 8 }

tmnxMobPdnS2aPeerHBCompatible OBJECT-TYPE
    SYNTAX        TruthValue
    MAX-ACCESS    read-only
    STATUS        current
    DESCRIPTION
        "The value of tmnxMobPdnS2aPeerHBCompatible indicates if the Packet Data 
        Network Gateway (PGW) detects the peer to be compatible with Proxy Mobile IPv6
        (PMIPv6) heartbeat mechanism."
    REFERENCE     "RFC 5847"
     ::={ tmnxMobPdnS2aPeerEntry 9 }
    


--
--  S2a stats table
--

tmnxMobPdnS2aStatTable  OBJECT-TYPE
    SYNTAX      SEQUENCE OF TmnxMobPdnS2aStatEntry
    MAX-ACCESS  not-accessible
    STATUS      current
    DESCRIPTION
        "The tmnxMobPdnS2aStatTable has an entry for each peer on the S2a
         reference point."
    ::= {  tmnxMobPdnStatObjs 20 }

tmnxMobPdnS2aStatEntry  OBJECT-TYPE
    SYNTAX      TmnxMobPdnS2aStatEntry
    MAX-ACCESS  not-accessible
    STATUS      current
    DESCRIPTION
        "Each row entry represents a peer on the S2a reference point 
         and contain statistics for this peer on a card."
    INDEX { vRtrID,
            tmnxMobPdnS2aPeerAddressType,
            tmnxMobPdnS2aPeerAddress,
            tmnxMobPdnS2aPeerPort,
            tmnxChassisIndex,
            tmnxCardSlotNum
          }
    ::= { tmnxMobPdnS2aStatTable 1 }

TmnxMobPdnS2aStatEntry ::= SEQUENCE {
        tmnxMobPdnS2aStatPeerRestart        Counter32,
        tmnxMobPdnS2aStatPathMgmtFail       Counter32,
        tmnxMobPdnS2aStatPeerRestartCnt     Counter32,
        tmnxMobPdnS2aStatHeartBeatReqTx     Counter32,
        tmnxMobPdnS2aStatHeartBeatReqRx     Counter32,
        tmnxMobPdnS2aStatHeartBeatRespTx    Counter32,
        tmnxMobPdnS2aStatHeartBeatRespRx    Counter32,
        tmnxMobPdnS2aStatPbu                Counter32,
        tmnxMobPdnS2aStatBri                Counter32,
        tmnxMobPdnS2aStatRxMalformedPkts    Counter32,
        tmnxMobPdnS2aStatRxMissingIePkts    Counter32,
        tmnxMobPdnS2aStatRxUnknownPkts      Counter32,        
        tmnxMobPdnS2aStatPbaFailure         Counter32,
        tmnxMobPdnS2aStatBraFailure         Counter32,
        tmnxMobPdnS2aStatPbaSuccess         Counter32,
        tmnxMobPdnS2aStatBraSuccess         Counter32,
        tmnxMobPdnS2aStatHBCompatible       TruthValue
    }

tmnxMobPdnS2aStatPeerRestart   OBJECT-TYPE
    SYNTAX      Counter32
    MAX-ACCESS  read-only
    STATUS      current
    DESCRIPTION
        "The value of tmnxMobPdnS2aStatPeerRestart indicates if the peer has  
         restarted after registering with the Packet Data Network Gateway (PGW)."
    ::= { tmnxMobPdnS2aStatEntry 1 }

tmnxMobPdnS2aStatPathMgmtFail   OBJECT-TYPE
    SYNTAX      Counter32
    MAX-ACCESS  read-only
    STATUS      current
    DESCRIPTION
        "The value of tmnxMobPdnS2aStatPathMgmtFail indicates the number of 
         path management failures for this peer."
    ::= { tmnxMobPdnS2aStatEntry 2 }  

tmnxMobPdnS2aStatPeerRestartCnt   OBJECT-TYPE
    SYNTAX      Counter32
    MAX-ACCESS  read-only
    STATUS      current
    DESCRIPTION
        "The value of tmnxMobPdnS2aStatPeerRestartCnt indicates the counter value
         of the number of times this peer restarted."        
    ::= { tmnxMobPdnS2aStatEntry 3 }  

tmnxMobPdnS2aStatHeartBeatReqTx   OBJECT-TYPE
    SYNTAX      Counter32
    MAX-ACCESS  read-only
    STATUS      current
    DESCRIPTION
        "The value of tmnxMobPdnS2aStatHeartBeatReqTx indicates the number of 
         heartbeat request messages transmitted to this peer."
    ::= { tmnxMobPdnS2aStatEntry 4 }  

tmnxMobPdnS2aStatHeartBeatReqRx   OBJECT-TYPE
    SYNTAX      Counter32
    MAX-ACCESS  read-only
    STATUS      current
    DESCRIPTION
        "The value of tmnxMobPdnS2aStatHeartBeatReqRx indicates the number of 
         hearbeat request messages received from this peer."
    ::= { tmnxMobPdnS2aStatEntry 5 }  

tmnxMobPdnS2aStatHeartBeatRespTx   OBJECT-TYPE
    SYNTAX      Counter32
    MAX-ACCESS  read-only
    STATUS      current
    DESCRIPTION
        "The value of tmnxMobPdnS2aStatHeartBeatRespTx indicates the number of 
         heartbeat response messages transmitted to this peer."
    ::= { tmnxMobPdnS2aStatEntry 6 }  

tmnxMobPdnS2aStatHeartBeatRespRx   OBJECT-TYPE
    SYNTAX      Counter32
    MAX-ACCESS  read-only
    STATUS      current
    DESCRIPTION
        "The value of tmnxMobPdnS2aStatHeartBeatRespRx indicates the number of 
         heartbeat response messages received from this peer."
    ::= { tmnxMobPdnS2aStatEntry 7 }  

tmnxMobPdnS2aStatPbu   OBJECT-TYPE
    SYNTAX      Counter32
    MAX-ACCESS  read-only
    STATUS      current
    DESCRIPTION
        "The value of tmnxMobPdnS2aStatPbu indicates the number of Proxy Binding 
         Updates received from this peer."
    ::= { tmnxMobPdnS2aStatEntry 8 }  

tmnxMobPdnS2aStatBri   OBJECT-TYPE
    SYNTAX      Counter32
    MAX-ACCESS  read-only
    STATUS      current
    DESCRIPTION
        "The value of tmnxMobPdnS2aStatBri indicates the number of Binding
         Revocation Indication messages transmitted to this peer."
    ::= { tmnxMobPdnS2aStatEntry 9 }

tmnxMobPdnS2aStatRxMalformedPkts   OBJECT-TYPE
    SYNTAX      Counter32
    MAX-ACCESS  read-only
    STATUS      current
    DESCRIPTION
        "The value of tmnxMobPdnS2aStatRxMalformedPkts indicates the number of
         malformed packets received from this peer."
    ::= { tmnxMobPdnS2aStatEntry 10 }

tmnxMobPdnS2aStatRxMissingIePkts   OBJECT-TYPE
    SYNTAX      Counter32
    MAX-ACCESS  read-only
    STATUS      current
    DESCRIPTION
        "The value of tmnxMobPdnS2aStatRxMissingIePkts indicates the number of
         missing mandatory Information Element (IE) packets received  from this
         peer."
    ::= { tmnxMobPdnS2aStatEntry 11 }

tmnxMobPdnS2aStatRxUnknownPkts   OBJECT-TYPE
    SYNTAX      Counter32
    MAX-ACCESS  read-only
    STATUS      current
    DESCRIPTION
        "The value of tmnxMobPdnS2aStatRxUnknownPkts indicates the number of
         unknown message type packets received from this peer."
    ::= { tmnxMobPdnS2aStatEntry 12 }

tmnxMobPdnS2aStatPbaFailure   OBJECT-TYPE
    SYNTAX      Counter32
    MAX-ACCESS  read-only
    STATUS      current
    DESCRIPTION
        "The value of tmnxMobPdnS2aStatPbaFailure indicates the number of failed
         Proxy Binding Acknowledgements transmitted to this peer."
    ::= { tmnxMobPdnS2aStatEntry 13 }

tmnxMobPdnS2aStatBraFailure   OBJECT-TYPE
    SYNTAX      Counter32
    MAX-ACCESS  read-only
    STATUS      current
    DESCRIPTION
        "The value of tmnxMobPdnS2aStatBraFailure indicates the number of failed
         Binding Revocation Acknowledgements received from this peer."
    ::= { tmnxMobPdnS2aStatEntry 14 }

tmnxMobPdnS2aStatPbaSuccess   OBJECT-TYPE
    SYNTAX      Counter32
    MAX-ACCESS  read-only
    STATUS      current
    DESCRIPTION
        "The value of tmnxMobPdnS2aStatPbaSuccess indicates the number of
         successful Proxy Binding transmitted to this peer."
    ::= { tmnxMobPdnS2aStatEntry 15 }

tmnxMobPdnS2aStatBraSuccess   OBJECT-TYPE
    SYNTAX      Counter32
    MAX-ACCESS  read-only
    STATUS      current
    DESCRIPTION
        "The value of tmnxMobPdnS2aStatBraSuccess indicates the number of
         successful Binding Revocation Acknowledgements received from this
         peer."
    ::= { tmnxMobPdnS2aStatEntry 16 }

tmnxMobPdnS2aStatHBCompatible OBJECT-TYPE
    SYNTAX      TruthValue
    MAX-ACCESS  read-only
    STATUS      current
    DESCRIPTION
        "The value of tmnxMobPdnS2aStatHBCompatible indicates if the Packet Data 
         Network Gateway (PGW) detects the peer to be compatible with Proxy
         Mobile IPv6 (PMIPv6) heartbeat mechanism."
    REFERENCE   "RFC 5847" 
    ::= { tmnxMobPdnS2aStatEntry 17 }

--
--  APN Extension-3 table
--

tmnxMobPdnApnExt3TableLastChangd  OBJECT-TYPE
    SYNTAX      TimeStamp
    MAX-ACCESS  read-only
    STATUS      current
    DESCRIPTION
        "The value of tmnxMobPdnApnExt3TableLastChangd indicates the sysUpTime 
         at the time of the last modification to tmnxMobPdnApnExt3Table by
         adding, deleting an entry or change to a writable object in the table.

         If no changes were made to the table since the last re-initialization
         of the local network management subsystem, then this object contains
         a zero value."
    ::= { tmnxMobPdnGlobalObjs 29 }

tmnxMobPdnApnExt3Table  OBJECT-TYPE
    SYNTAX      SEQUENCE OF TmnxMobPdnApnExt3Entry
    MAX-ACCESS  not-accessible
    STATUS      current
    DESCRIPTION
        "The tmnxMobPdnApnExt3Table has an entry for each Access Point Name 
         (APN). An APN identifies an external network that is accessible from a
         terminal.

         The tmnxMobPdnApnExt3Table provides an extension of the 
         tmnxMobPdnApnTable."
    ::= { tmnxMobPdnConfObjs 24 }

tmnxMobPdnApnExt3Entry  OBJECT-TYPE
    SYNTAX      TmnxMobPdnApnExt3Entry
    MAX-ACCESS  not-accessible
    STATUS      current
    DESCRIPTION
        "Each row entry represents additional columns for attributes specific 
         to Access Point Name (APN) configuration."
    AUGMENTS { tmnxMobPdnApnEntry }
    ::= { tmnxMobPdnApnExt3Table 1 }

TmnxMobPdnApnExt3Entry ::= SEQUENCE {
        tmnxMobPdnApnExt3LastChanged        TimeStamp,
        tmnxMobPdnApnAuthPriDiamPeer        TmnxMobProfNameOrEmpty,
        tmnxMobPdnApnAuthSecDiamPeer        TmnxMobProfNameOrEmpty,
        tmnxMobPdnApnDefAppProfile          TNamedItemOrEmpty,
        tmnxMobPdnApnAuthSupImsi            TmnxEnabledDisabled,
        tmnxMobPdnApnAcctSupImsi            TmnxEnabledDisabled,
        tmnxMobPdnApnPreAuthSupImsi         TmnxEnabledDisabled,
        tmnxMobPdnApnAaGroupIndex           TmnxBsxIsaAaGroupIndexOrZero,
        tmnxMobPdnApnAaGrpPartIndex         TmnxBsxAaGrpPartIndex,
        tmnxMobPdnApnHttpRedirect           TmnxMobProfNameOrEmpty,
        tmnxMobPdnApnRedirTrafficPol        INTEGER,
        tmnxMobPdnApnRedirPolRouterInst     TmnxVRtrID,
        tmnxMobPdnApnRedirPolNHopAddrTyp    InetAddressType,
        tmnxMobPdnApnRedirPolNHopAddr       InetAddress,
        tmnxMobPdnApnAllowEmergency         TmnxEnabledDisabled
}

tmnxMobPdnApnExt3LastChanged  OBJECT-TYPE
    SYNTAX      TimeStamp
    MAX-ACCESS  read-only
    STATUS      current
    DESCRIPTION
        "The value of tmnxMobPdnApnExt3LastChanged indicates the timestamp of
         the last change to this row in tmnxMobPdnApnExt3Table."
    ::= { tmnxMobPdnApnExt3Entry 1 }

tmnxMobPdnApnAuthPriDiamPeer OBJECT-TYPE
    SYNTAX        TmnxMobProfNameOrEmpty
    MAX-ACCESS    read-write
    STATUS        current
    DESCRIPTION 
         "The value of tmnxMobPdnApnAuthPriDiamPeer specifies the default primary 
          diameter peer profile name. 

          If a corresponding diameter peer profile does not exist in 
          TIMETRA-MOBILE-PROFILE-MIB::tmnxMobProfDiaPeerTable, an 'inconsistent' error 
          will be returned. "
    DEFVAL { ''H }
    ::= { tmnxMobPdnApnExt3Entry 2 }

tmnxMobPdnApnAuthSecDiamPeer OBJECT-TYPE
    SYNTAX        TmnxMobProfNameOrEmpty
    MAX-ACCESS    read-write
    STATUS        current
    DESCRIPTION 
         "The value of tmnxMobPdnApnAuthSecDiamPeer specifies the default secondary
          diameter peer profile name.
 
          If a corresponding diameter peer profile does not exist in 
          TIMETRA-MOBILE-PROFILE-MIB::tmnxMobProfDiaPeerTable, an 'inconsistent' error 
          will be returned."
    DEFVAL { ''H }
    ::= { tmnxMobPdnApnExt3Entry 3 }

tmnxMobPdnApnDefAppProfile OBJECT-TYPE
    SYNTAX        TNamedItemOrEmpty
    MAX-ACCESS    read-write
    STATUS        current
    DESCRIPTION 
        "The value of tmnxMobPdnApnDefAppProfile specifies the value of default
         application profile being applied at the Access Point Name (APN)."
    DEFVAL { ''H }
    ::= { tmnxMobPdnApnExt3Entry 4 }

tmnxMobPdnApnAuthSupImsi  OBJECT-TYPE
    SYNTAX      TmnxEnabledDisabled
    MAX-ACCESS  read-write
    STATUS      current
    DESCRIPTION
        "The value of tmnxMobPdnApnAuthSupImsi specifies to remove the 
         3GPP-IMSI attribute when sending an authentication message.

         When the value of tmnxMobPdnApnAuthSupImsi is not specifed, 
         the 3GPP-IMSI attribute shall be sent."
    DEFVAL { disabled }
    ::= { tmnxMobPdnApnExt3Entry 5 }

tmnxMobPdnApnAcctSupImsi  OBJECT-TYPE
    SYNTAX      TmnxEnabledDisabled
    MAX-ACCESS  read-write
    STATUS      current
    DESCRIPTION
        "The value of tmnxMobPdnApnAcctSupImsi specifies to remove the 
         3GPP-IMSI attribute when sending an accounting message.

         When the value of tmnxMobPdnApnAcctSupImsi is not specifed, 
         the 3GPP-IMSI attribute shall be sent."
    DEFVAL { disabled }
    ::= { tmnxMobPdnApnExt3Entry 6 }

tmnxMobPdnApnPreAuthSupImsi  OBJECT-TYPE
    SYNTAX      TmnxEnabledDisabled
    MAX-ACCESS  read-write
    STATUS      current
    DESCRIPTION
        "The value of tmnxMobPdnApnPreAuthSupImsi specifies to remove the 
         3GPP-IMSI attribute when sending an pre authentication message.

         When the value of tmnxMobPdnApnPreAuthSupImsi is not specifed, 
         the 3GPP-IMSI attribute shall be sent."
    DEFVAL { disabled }
    ::= { tmnxMobPdnApnExt3Entry 7 }

tmnxMobPdnApnAaGroupIndex    OBJECT-TYPE
    SYNTAX      TmnxBsxIsaAaGroupIndexOrZero
    MAX-ACCESS  read-write
    STATUS      current
    DESCRIPTION
        "The value of tmnxMobPdnApnAaGroupIndex specifies the
         group number of this group of BSX MDAs at the Access Point Name (APN)
         level.

         The corresponding row for the AA group must have already been created
         in the TIMETRA-BSX-NG-MIB::tmnxBsxIsaAaGrpTable.

         The value of zero indicates that no BSX MDA group is specified."
    DEFVAL { 0 }
    ::= { tmnxMobPdnApnExt3Entry  8 }

tmnxMobPdnApnAaGrpPartIndex    OBJECT-TYPE
    SYNTAX      TmnxBsxAaGrpPartIndex
    MAX-ACCESS  read-write
    STATUS      current
    DESCRIPTION
        "The value of tmnxMobPdnApnAaGrpPartIndex specifies the
         partition index within an AA group at the Access Point Name (APN) 
         level.

         The corresponding row for the partition index must have already been
         created in the 
         TIMETRA-BSX-NG-MIB::tmnxBsxAaGrpPartTable.

         The value of zero indicates that no Application Assurance partition is
         specified."
    DEFVAL { 0 }
    ::= { tmnxMobPdnApnExt3Entry 9 }

tmnxMobPdnApnHttpRedirect  OBJECT-TYPE
    SYNTAX      TmnxMobProfNameOrEmpty 
    MAX-ACCESS  read-write
    STATUS      current
    DESCRIPTION
        "The value of tmnxMobPdnApnHttpRedirect specifies the http redirect
         rule on this Access Point Name (APN)."
    DEFVAL { ''H }
    ::= { tmnxMobPdnApnExt3Entry 10 }

tmnxMobPdnApnRedirTrafficPol  OBJECT-TYPE
    SYNTAX      INTEGER {
                  mobileToMobile (1),
                  mobileToAll    (2)
                 }
    MAX-ACCESS  read-write
    STATUS      current
    DESCRIPTION
        "The value of tmnxMobPdnApnRedirTrafficPol specifies the redirect traffic
         policy for nexthop in the Gi uplink direction on this Access Point
         Name (APN)."
    DEFVAL { mobileToAll }
    ::= { tmnxMobPdnApnExt3Entry 11 }

tmnxMobPdnApnRedirPolRouterInst  OBJECT-TYPE
    SYNTAX      TmnxVRtrID 
    MAX-ACCESS  read-write
    STATUS      current
    DESCRIPTION
        "The value of tmnxMobPdnApnRedirPolRouterInst specifies the Gi router instance
         used by the redirect traffic policy configured on this Access Point Name (APN)."
    DEFVAL { 1 }
    ::= { tmnxMobPdnApnExt3Entry 12 }

tmnxMobPdnApnRedirPolNHopAddrTyp  OBJECT-TYPE
    SYNTAX      InetAddressType 
    MAX-ACCESS  read-write
    STATUS      current
    DESCRIPTION
        "The value of tmnxMobPdnApnRedirPolNHopAddrTyp indicates the type of
         address represented by tmnxMobPdnApnRedirPolNHopAddr."
    DEFVAL { unknown }
    ::= { tmnxMobPdnApnExt3Entry 13 }

tmnxMobPdnApnRedirPolNHopAddr  OBJECT-TYPE
    SYNTAX      InetAddress (SIZE(0|4|16))
    MAX-ACCESS  read-write
    STATUS      current
    DESCRIPTION
        "The value of tmnxMobPdnApnRedirPolNHopAddr specifies the next hop IP
         address on Gi side for the redirection traffic policy configured on this 
         Access Point Name (APN)"
    DEFVAL { ''H }
    ::= { tmnxMobPdnApnExt3Entry 14 }

tmnxMobPdnApnAllowEmergency  OBJECT-TYPE
    SYNTAX      TmnxEnabledDisabled
    MAX-ACCESS  read-write
    STATUS      current
    DESCRIPTION
        "The value of tmnxMobPdnApnAllowEmergency specifies whether the PDN
         sessions for Emergency PDNs with unauthenticated International
         Mobile Subscriber Identity (IMSI) and only with International Mobile
         Equipment Identity (IMEI) is allowed on this Access Point Name (APN)."
    DEFVAL { disabled }
    ::= { tmnxMobPdnApnExt3Entry 15 }

--
--  Gy OCS Selection Entry
--

tmnxMobPdnGyOcsTableLastChanged  OBJECT-TYPE
    SYNTAX      TimeStamp
    MAX-ACCESS  read-only
    STATUS      current
    DESCRIPTION
        "The value of tmnxMobPdnGyOcsTableLastChanged indicates the sysUpTime at
         the time of the last modification to tmnxMobPdnGyOcsTable by
         adding, deleting an entry or change to a writable object in the table.

         If no changes were made to the table since the last re-initialization
         of the local network management subsystem, then this object contains
         a zero value."
    ::= { tmnxMobPdnGlobalObjs 31 }

tmnxMobPdnGyOcsTable  OBJECT-TYPE
    SYNTAX      SEQUENCE OF TmnxMobPdnGyOcsEntry
    MAX-ACCESS  not-accessible
    STATUS      current
    DESCRIPTION
        "The tmnxMobPdnGyOcsTable provides an entry for each User Range 
         configuration for the International Mobile Subscriber Identity (IMSI)
         or the Mobile Subscriber Integrated Services Digital Network (MSISDN)
         mapping to the associated primary and secondary Online Charging 
         System (OCS) peers."
    ::= { tmnxMobPdnConfObjs 25 }

tmnxMobPdnGyOcsEntry  OBJECT-TYPE
    SYNTAX      TmnxMobPdnGyOcsEntry
    MAX-ACCESS  not-accessible
    STATUS      current
    DESCRIPTION
        "Each row entry represents a unique User Range for the Packet Data
         Network Gateway (PGW). Entries can be created and deleted by the user."
    INDEX { tmnxMobGwId,
            tmnxMobPdnGyOcsUserRangeName
          }
    ::= { tmnxMobPdnGyOcsTable 1 }

TmnxMobPdnGyOcsEntry ::= SEQUENCE {
        tmnxMobPdnGyOcsUserRangeName        TNamedItem,
        tmnxMobPdnGyOcsRowStatus            RowStatus,
        tmnxMobPdnGyOcsLastChanged          TimeStamp,
        tmnxMobPdnGyOcsUeStartId            TmnxMobUeStrPrefix,
        tmnxMobPdnGyOcsUeEndId              TmnxMobUeStrPrefix,
        tmnxMobPdnGyOcsPriDiaPeer           TmnxMobProfNameOrEmpty,
        tmnxMobPdnGyOcsSecDiaPeer           TmnxMobProfNameOrEmpty,
        tmnxMobPdnGyOcsDccaProf             TmnxMobProfName
    }

tmnxMobPdnGyOcsUserRangeName  OBJECT-TYPE
    SYNTAX      TNamedItem
    MAX-ACCESS  not-accessible
    STATUS      current
    DESCRIPTION
        "The value of tmnxMobPdnGyOcsUserRangeName specifies the name of the 
         user range for the International Mobile Subscriber Identity (IMSI) or
         the Mobile Subscriber Integrated Services Digital Network (MSISDN)
         mapping to the associated primary and secondary Online Charging System
         (OCS) peers."
    ::= { tmnxMobPdnGyOcsEntry 1 }

tmnxMobPdnGyOcsRowStatus  OBJECT-TYPE
    SYNTAX      RowStatus
    MAX-ACCESS  read-create
    STATUS      current
    DESCRIPTION
        "The value of tmnxMobPdnGyOcsRowStatus specifies the row status of
         this entry. It is used for creation and deletion of this User Range."
    ::= { tmnxMobPdnGyOcsEntry 2 }

tmnxMobPdnGyOcsLastChanged  OBJECT-TYPE
    SYNTAX      TimeStamp
    MAX-ACCESS  read-only
    STATUS      current
    DESCRIPTION
        "The value of tmnxMobPdnGyLastChanged indicates the timestamp of
         the last change to this row in tmnxMobPdnGyOcsTable."
    ::= { tmnxMobPdnGyOcsEntry 3 }

tmnxMobPdnGyOcsUeStartId  OBJECT-TYPE
    SYNTAX      TmnxMobUeStrPrefix
    MAX-ACCESS  read-create
    STATUS      current
    DESCRIPTION
        "The value of tmnxMobPdnGyOcsUeStartId specifies the start value of
         the International Mobile Subscriber Identity (IMSI) or the Mobile
         Subscriber Integrated Services Digital Network (MSISDN) for the User
         Range. 

         The value must be specified at the time of row creation. An 
         'inconsistentValue' error is returned if an attempt is made to set
         this object individually."
    ::= { tmnxMobPdnGyOcsEntry 4 }

tmnxMobPdnGyOcsUeEndId  OBJECT-TYPE
    SYNTAX      TmnxMobUeStrPrefix
    MAX-ACCESS  read-create
    STATUS      current
    DESCRIPTION
        "The value of tmnxMobPdnGyOcsUeEndId specifies the end value of
         the International Mobile Subscriber Identity (IMSI) or the Mobile
         Subscriber Integrated Services Digital Network (MSISDN) for the User
         Range."
    DEFVAL { ''H }
    ::= { tmnxMobPdnGyOcsEntry 5 }

tmnxMobPdnGyOcsPriDiaPeer  OBJECT-TYPE
    SYNTAX      TmnxMobProfNameOrEmpty
    MAX-ACCESS  read-create
    STATUS      current
    DESCRIPTION
        "The value of tmnxMobPdnGyOcsPriDiaPeer specifies the primary 
         Online Charging System (OCS) diameter peer profile for the User
         Range.

         The value must be specified at the time of row creation. If a 
         corresponding diameter profile does not exist in
         TIMETRA-MOBILE-PROFILE-MIB::tmnxMobProfDiaTable, an 'inconsistentValue'
         error will be returned. An 'inconsistentValue' error is returned if
         an attempt is made to set this object individually."
    ::= { tmnxMobPdnGyOcsEntry 6 }

tmnxMobPdnGyOcsSecDiaPeer  OBJECT-TYPE
    SYNTAX      TmnxMobProfNameOrEmpty
    MAX-ACCESS  read-create
    STATUS      current
    DESCRIPTION
        "The value of tmnxMobPdnGyOcsSecDiaPeer specifies the secondary 
         Online Charging System (OCS) diameter peer profile for the User
         Range."
    DEFVAL { ''H }
    ::= { tmnxMobPdnGyOcsEntry 7 }

tmnxMobPdnGyOcsDccaProf  OBJECT-TYPE
    SYNTAX      TmnxMobProfName
    MAX-ACCESS  read-create
    STATUS      current
    DESCRIPTION
        "The value of tmnxMobPdnGyOcsDccaProf specifies the unique name of this
         Diameter Credit Control Application (DCCA) profile for this User
         Range.

         The value must be specified at the time of row creation. If a 
         corresponding DCCA profile does not exist in
         TIMETRA-MOBILE-PROFILE-MIB::tmnxMobProfDccaTable,
         an 'inconsistentValue' error will be returned. An 'inconsistentValue'
         error is returned if an attempt is made to set this object
         individually."
    ::= { tmnxMobPdnGyOcsEntry 8 }

--
--  Bearer Context Accounting Ga Table
--

tmnxMobPdnBcAcctGaTable  OBJECT-TYPE
    SYNTAX      SEQUENCE OF TmnxMobPdnBcAcctGaEntry
    MAX-ACCESS  not-accessible
    STATUS      current
    DESCRIPTION
        "The tmnxMobPdnBcAcctGaTable has an entry for each bearer context
         of an User Equipment (UE).

         The tmnxMobPdnBcAcctGaTable provides an extension of the 
         tmnxMobPdnBearerContextTable."
    ::= { tmnxMobPdnStatObjs 21 }

tmnxMobPdnBcAcctGaEntry  OBJECT-TYPE
    SYNTAX      TmnxMobPdnBcAcctGaEntry
    MAX-ACCESS  not-accessible
    STATUS      current
    DESCRIPTION
        "Each row entry represents a bearer context of an User Equipment (UE)
         and contains reference point Ga Accounting statistics information."
    AUGMENTS { tmnxMobPdnBearerContextEntry }
    ::= { tmnxMobPdnBcAcctGaTable 1 }

TmnxMobPdnBcAcctGaEntry ::= SEQUENCE {
        tmnxMobPdnBcAcctGaChargingId       TmnxMobChargingProfile,
        tmnxMobPdnBcAcctGaUlSustRate       Counter32,
        tmnxMobPdnBcAcctGaDlSustRate       Counter32,
        tmnxMobPdnBcAcctGaAggrUlPkts       Counter64,
        tmnxMobPdnBcAcctGaAggrUlPktsLow    Counter32,
        tmnxMobPdnBcAcctGaAggrUlPktsHigh   Counter32,
        tmnxMobPdnBcAcctGaAggrDlPkts       Counter64,
        tmnxMobPdnBcAcctGaAggrDlPktsLow    Counter32,
        tmnxMobPdnBcAcctGaAggrDlPktsHigh   Counter32,
        tmnxMobPdnBcAcctGaAggrUlByts       Counter64,
        tmnxMobPdnBcAcctGaAggrUlBytsLow    Counter32,
        tmnxMobPdnBcAcctGaAggrUlBytsHigh   Counter32,
        tmnxMobPdnBcAcctGaAggrDlByts       Counter64,
        tmnxMobPdnBcAcctGaAggrDlBytsLow    Counter32,
        tmnxMobPdnBcAcctGaAggrDlBytsHigh   Counter32,
        tmnxMobPdnBcAcctGaNumPartCdrs      Counter32,
        tmnxMobPdnBcAcctGaNumContainers    Counter32,
        tmnxMobPdnBcAcctGaNumMaxChanges    Counter32,
        tmnxMobPdnBcAcctGaNumRgs           Counter32,            
        tmnxMobPdnBcAcctGaNumOfRgSvcId     Counter32
    }

tmnxMobPdnBcAcctGaChargingId  OBJECT-TYPE
    SYNTAX      TmnxMobChargingProfile
    MAX-ACCESS  read-only
    STATUS      current
    DESCRIPTION
        "The value of tmnxMobPdnBcAcctGaChargingId indicates the charging
         profile assigned by the Packet Data Network Gateway (PGW) for
         this bearer."
    ::= { tmnxMobPdnBcAcctGaEntry 1 }

tmnxMobPdnBcAcctGaUlSustRate  OBJECT-TYPE
    SYNTAX      Counter32
    MAX-ACCESS  read-only
    STATUS      current
    DESCRIPTION
        "The value of tmnxMobPdnBcAcctGaUlSustRate indicates the uplink
         sustained rate for this bearer since last 5 minutes."
    ::= { tmnxMobPdnBcAcctGaEntry 2 }

tmnxMobPdnBcAcctGaDlSustRate  OBJECT-TYPE
    SYNTAX      Counter32
    MAX-ACCESS  read-only
    STATUS      current
    DESCRIPTION
        "The value of tmnxMobPdnBcAcctGaDlSustRate indicates the downlink
         sustained rate for this bearer since last 5 minutes."
    ::= { tmnxMobPdnBcAcctGaEntry 3 }

tmnxMobPdnBcAcctGaAggrUlPkts  OBJECT-TYPE
    SYNTAX      Counter64
    MAX-ACCESS  read-only
    STATUS      current
    DESCRIPTION
        "The value of tmnxMobPdnBcAcctGaAggrUlPkts indicates the aggregate
         uplink packets for this bearer."
    ::= { tmnxMobPdnBcAcctGaEntry 4 }

tmnxMobPdnBcAcctGaAggrUlPktsLow  OBJECT-TYPE
    SYNTAX      Counter32
    MAX-ACCESS  read-only
    STATUS      current
    DESCRIPTION
        "The value of tmnxMobPdnBcAcctGaAggrUlPktsLow indicates the lower 32
         bits of the value of tmnxMobPdnBcAcctGaAggrUlPkts."
    ::= { tmnxMobPdnBcAcctGaEntry 5 }

tmnxMobPdnBcAcctGaAggrUlPktsHigh  OBJECT-TYPE
    SYNTAX      Counter32
    MAX-ACCESS  read-only
    STATUS      current
    DESCRIPTION
        "The value of tmnxMobPdnBcAcctGaAggrUlPktsHigh indicates the higer 32
         bits of the value of tmnxMobPdnBcAcctGaAggrUlPkts."
    ::= { tmnxMobPdnBcAcctGaEntry 6 }

tmnxMobPdnBcAcctGaAggrDlPkts  OBJECT-TYPE
    SYNTAX      Counter64
    MAX-ACCESS  read-only
    STATUS      current
    DESCRIPTION
        "The value of tmnxMobPdnBcAcctGaAggrDlPkts indicates the aggregate
         downlink packets for this bearer."
    ::= { tmnxMobPdnBcAcctGaEntry 7 }

tmnxMobPdnBcAcctGaAggrDlPktsLow  OBJECT-TYPE
    SYNTAX      Counter32
    MAX-ACCESS  read-only
    STATUS      current
    DESCRIPTION
        "The value of tmnxMobPdnBcAcctGaAggrDlPktsLow indicates the lower 32
         bits of the value of tmnxMobPdnBcAcctGaAggrDlPkts."
    ::= { tmnxMobPdnBcAcctGaEntry 8 }

tmnxMobPdnBcAcctGaAggrDlPktsHigh  OBJECT-TYPE
    SYNTAX      Counter32
    MAX-ACCESS  read-only
    STATUS      current
    DESCRIPTION
        "The value of tmnxMobPdnBcAcctGaAggrDlPktsLow indicates the higer 32
         bits of the value of tmnxMobPdnBcAcctGaAggrDlPkts."
    ::= { tmnxMobPdnBcAcctGaEntry 9 }

tmnxMobPdnBcAcctGaAggrUlByts  OBJECT-TYPE
    SYNTAX      Counter64
    MAX-ACCESS  read-only
    STATUS      current
    DESCRIPTION
        "The value of tmnxMobPdnBcAcctGaAggrUlByts indicates the aggregate
         uplink bytes for this bearer."
    ::= { tmnxMobPdnBcAcctGaEntry 10 }

tmnxMobPdnBcAcctGaAggrUlBytsLow  OBJECT-TYPE
    SYNTAX      Counter32
    MAX-ACCESS  read-only
    STATUS      current
    DESCRIPTION
        "The value of tmnxMobPdnBcAcctGaAggrUlBytsLow indicates the lower 32
         bits of the value of tmnxMobPdnBcAcctGaAggrUlByts."
    ::= { tmnxMobPdnBcAcctGaEntry 11 }

tmnxMobPdnBcAcctGaAggrUlBytsHigh  OBJECT-TYPE
    SYNTAX      Counter32
    MAX-ACCESS  read-only
    STATUS      current
    DESCRIPTION
        "The value of tmnxMobPdnBcAcctGaAggrUlBytsHigh indicates the higer 32
         bits of the value of tmnxMobPdnBcAcctGaAggrUlByts."
    ::= { tmnxMobPdnBcAcctGaEntry 12 }

tmnxMobPdnBcAcctGaAggrDlByts  OBJECT-TYPE
    SYNTAX      Counter64
    MAX-ACCESS  read-only
    STATUS      current
    DESCRIPTION
        "The value of tmnxMobPdnBcAcctGaAggrDlByts indicates the aggregate
         downlink bytes for this bearer."
    ::= { tmnxMobPdnBcAcctGaEntry 13 }

tmnxMobPdnBcAcctGaAggrDlBytsLow  OBJECT-TYPE
    SYNTAX      Counter32
    MAX-ACCESS  read-only
    STATUS      current
    DESCRIPTION
        "The value of tmnxMobPdnBcAcctGaAggrDlBytsLow indicates the lower 32
         bits of the value of tmnxMobPdnBcAcctGaAggrDlByts."
    ::= { tmnxMobPdnBcAcctGaEntry 14 }

tmnxMobPdnBcAcctGaAggrDlBytsHigh  OBJECT-TYPE
    SYNTAX      Counter32
    MAX-ACCESS  read-only
    STATUS      current
    DESCRIPTION
        "The value of tmnxMobPdnBcAcctGaAggrDlBytsLow indicates the higer 32
         bits of the value of tmnxMobPdnBcAcctGaAggrDlByts."
    ::= { tmnxMobPdnBcAcctGaEntry 15 }

tmnxMobPdnBcAcctGaNumPartCdrs  OBJECT-TYPE
    SYNTAX      Counter32
    MAX-ACCESS  read-only
    STATUS      current
    DESCRIPTION
        "The value of tmnxMobPdnBcAcctGaNumPartCdrs indicates the number of 
         partial Charging Data Requests(CDR) messages for this bearer."
    ::= { tmnxMobPdnBcAcctGaEntry 16 }

tmnxMobPdnBcAcctGaNumContainers  OBJECT-TYPE
    SYNTAX      Counter32
    MAX-ACCESS  read-only
    STATUS      current
    DESCRIPTION
        "The value of tmnxMobPdnBcAcctGaNumContainers indicates the number of 
         Service Data containers for this bearer."
    ::= { tmnxMobPdnBcAcctGaEntry 17 }

tmnxMobPdnBcAcctGaNumMaxChanges  OBJECT-TYPE
    SYNTAX      Counter32
    MAX-ACCESS  read-only
    STATUS      current
    DESCRIPTION
        "The value of tmnxMobPdnBcAcctGaNumMaxChanges indicates the number of 
         maximum change events generated for this bearer."
    ::= { tmnxMobPdnBcAcctGaEntry 18 }

tmnxMobPdnBcAcctGaNumRgs  OBJECT-TYPE
    SYNTAX      Counter32
    MAX-ACCESS  read-only
    STATUS      current
    DESCRIPTION
        "The value of tmnxMobPdnBcAcctGaNumRgs indicates the number of 
         Rating Groups associated with this bearer."
    ::= { tmnxMobPdnBcAcctGaEntry 19 }

tmnxMobPdnBcAcctGaNumOfRgSvcId  OBJECT-TYPE
    SYNTAX      Counter32
    MAX-ACCESS  read-only
    STATUS      current
    DESCRIPTION
        "The value of tmnxMobPdnBcAcctGaNumOfRgSvcId indicates the number of 
         unique Rating Group and Service Identifier pairs associated with this
         bearer."
    ::= { tmnxMobPdnBcAcctGaEntry 20 }

--
--  Acct Ga Charging Rule Unit Stats Table
--

tmnxMobPdnBcGaChrgTable  OBJECT-TYPE
    SYNTAX      SEQUENCE OF TmnxMobPdnBcGaChrgEntry
    MAX-ACCESS  not-accessible
    STATUS      current
    DESCRIPTION
        "The tmnxMobPdnBcGaChrgTable has an entry for each
         Rating Group and Service ID pair of an User Equipment (UE)."
    ::= { tmnxMobPdnStatObjs 22 }

tmnxMobPdnBcGaChrgEntry  OBJECT-TYPE
    SYNTAX      TmnxMobPdnBcGaChrgEntry
    MAX-ACCESS  not-accessible
    STATUS      current
    DESCRIPTION
        "Each row entry represents a Ga Charging Rule Unit statistics
         information for each Rating Group and Service Identifier pair of an
         User Equipment (UE)."
    INDEX { tmnxMobGwId,
            tmnxMobPdnUeImsi,
            tmnxMobPdnPcApn,
            tmnxMobPdnPcPdnType,
            tmnxMobPdnBcBearerId,
            tmnxMobProfChgUnitRatingGroup,
            tmnxMobProfChgUnitServIdentifier
          }
    ::= { tmnxMobPdnBcGaChrgTable 1 }

TmnxMobPdnBcGaChrgEntry ::= SEQUENCE {
        tmnxMobPdnBcGaChrgOnlnCharging          TruthValue,
        tmnxMobPdnBcGaChrgOfflnCharging         TruthValue,
        tmnxMobPdnBcGaChrgUlPkts                Counter64,
        tmnxMobPdnBcGaChrgUlPktsLow             Counter32,
        tmnxMobPdnBcGaChrgUlPktsHigh            Counter32,
        tmnxMobPdnBcGaChrgDlPkts                Counter64,
        tmnxMobPdnBcGaChrgDlPktsLow             Counter32,
        tmnxMobPdnBcGaChrgDlPktsHigh            Counter32,
        tmnxMobPdnBcGaChrgUlByts                Counter64,
        tmnxMobPdnBcGaChrgUlBytsLow             Counter32,
        tmnxMobPdnBcGaChrgUlBytsHigh            Counter32,
        tmnxMobPdnBcGaChrgDlByts                Counter64,
        tmnxMobPdnBcGaChrgDlBytsLow             Counter32,
        tmnxMobPdnBcGaChrgDlBytsHigh            Counter32
    }

tmnxMobPdnBcGaChrgOnlnCharging  OBJECT-TYPE
    SYNTAX      TruthValue
    MAX-ACCESS  read-only
    STATUS      current
    DESCRIPTION
        "The value of tmnxMobPdnBcGaChrgOnlnCharging indicates whether online
         charging is enabled."        
    ::= { tmnxMobPdnBcGaChrgEntry 1 }

tmnxMobPdnBcGaChrgOfflnCharging  OBJECT-TYPE
    SYNTAX      TruthValue
    MAX-ACCESS  read-only
    STATUS      current
    DESCRIPTION
        "The value of tmnxMobPdnBcGaChrgOfflnCharging indicates whether offline
         charging is enabled."        
    ::= { tmnxMobPdnBcGaChrgEntry 2 }

tmnxMobPdnBcGaChrgUlPkts  OBJECT-TYPE
    SYNTAX      Counter64
    MAX-ACCESS  read-only
    STATUS      current
    DESCRIPTION
        "The value of tmnxMobPdnBcGaChrgUlPkts indicates the total
         uplink packets."
    ::= { tmnxMobPdnBcGaChrgEntry 3 }

tmnxMobPdnBcGaChrgUlPktsLow  OBJECT-TYPE
    SYNTAX      Counter32
    MAX-ACCESS  read-only
    STATUS      current
    DESCRIPTION
        "The value of tmnxMobPdnBcGaChrgUlPktsLow indicates the lower 32
         bits of the value of tmnxMobPdnBcGaChrgUlPkts."
    ::= { tmnxMobPdnBcGaChrgEntry 4 }

tmnxMobPdnBcGaChrgUlPktsHigh  OBJECT-TYPE
    SYNTAX      Counter32
    MAX-ACCESS  read-only
    STATUS      current
    DESCRIPTION
        "The value of tmnxMobPdnBcGaChrgUlPktsHigh indicates the higer 32
         bits of the value of tmnxMobPdnBcGaChrgUlPkts."
    ::= { tmnxMobPdnBcGaChrgEntry 5 }

tmnxMobPdnBcGaChrgDlPkts  OBJECT-TYPE
    SYNTAX      Counter64
    MAX-ACCESS  read-only
    STATUS      current
    DESCRIPTION
        "The value of tmnxMobPdnBcGaChrgDlPkts indicates the total
         downlink packets."
    ::= { tmnxMobPdnBcGaChrgEntry 6 }

tmnxMobPdnBcGaChrgDlPktsLow  OBJECT-TYPE
    SYNTAX      Counter32
    MAX-ACCESS  read-only
    STATUS      current
    DESCRIPTION
        "The value of tmnxMobPdnBcGaChrgDlPktsLow indicates the lower 32
         bits of the value of tmnxMobPdnBcGaChrgDlPkts."
    ::= { tmnxMobPdnBcGaChrgEntry 7 }

tmnxMobPdnBcGaChrgDlPktsHigh  OBJECT-TYPE
    SYNTAX      Counter32
    MAX-ACCESS  read-only
    STATUS      current
    DESCRIPTION
        "The value of tmnxMobPdnBcGaChrgDlPktsLow indicates the higer 32
         bits of the value of tmnxMobPdnBcGaChrgDlPkts."
    ::= { tmnxMobPdnBcGaChrgEntry 8 }

tmnxMobPdnBcGaChrgUlByts  OBJECT-TYPE
    SYNTAX      Counter64
    MAX-ACCESS  read-only
    STATUS      current
    DESCRIPTION
        "The value of tmnxMobPdnBcGaChrgUlByts indicates the total
         uplink bytes."
    ::= { tmnxMobPdnBcGaChrgEntry 9 }

tmnxMobPdnBcGaChrgUlBytsLow  OBJECT-TYPE
    SYNTAX      Counter32
    MAX-ACCESS  read-only
    STATUS      current
    DESCRIPTION
        "The value of tmnxMobPdnBcGaChrgUlBytsLow indicates the lower 32
         bits of the value of tmnxMobPdnBcGaChrgUlByts."
    ::= { tmnxMobPdnBcGaChrgEntry 10 }

tmnxMobPdnBcGaChrgUlBytsHigh  OBJECT-TYPE
    SYNTAX      Counter32
    MAX-ACCESS  read-only
    STATUS      current
    DESCRIPTION
        "The value of tmnxMobPdnBcGaChrgUlBytsHigh indicates the higer 32
         bits of the value of tmnxMobPdnBcGaChrgUlByts."
    ::= { tmnxMobPdnBcGaChrgEntry 11 }

tmnxMobPdnBcGaChrgDlByts  OBJECT-TYPE
    SYNTAX      Counter64
    MAX-ACCESS  read-only
    STATUS      current
    DESCRIPTION
        "The value of tmnxMobPdnBcGaChrgDlByts indicates the total
         downlink bytes."
    ::= { tmnxMobPdnBcGaChrgEntry 12 }

tmnxMobPdnBcGaChrgDlBytsLow  OBJECT-TYPE
    SYNTAX      Counter32
    MAX-ACCESS  read-only
    STATUS      current
    DESCRIPTION
        "The value of tmnxMobPdnBcGaChrgDlBytsLow indicates the lower 32
         bits of the value of tmnxMobPdnBcGaChrgDlByts."
    ::= { tmnxMobPdnBcGaChrgEntry 13 }

tmnxMobPdnBcGaChrgDlBytsHigh  OBJECT-TYPE
    SYNTAX      Counter32
    MAX-ACCESS  read-only
    STATUS      current
    DESCRIPTION
        "The value of tmnxMobPdnBcGaChrgDlBytsLow indicates the higer 32
         bits of the value of tmnxMobPdnBcGaChrgDlByts."
    ::= { tmnxMobPdnBcGaChrgEntry 14 }

--
--  Bearer Context Accounting Gy Table
--

tmnxMobPdnBcAcctGyTable  OBJECT-TYPE
    SYNTAX      SEQUENCE OF TmnxMobPdnBcAcctGyEntry
    MAX-ACCESS  not-accessible
    STATUS      current
    DESCRIPTION
        "The tmnxMobPdnBcAcctGyTable has an entry for each bearer context
         of an User Equipment (UE).

         The tmnxMobPdnBcAcctGyTable provides an extension of the 
         tmnxMobPdnBearerContextTable."
    ::= { tmnxMobPdnStatObjs 23 }

tmnxMobPdnBcAcctGyEntry  OBJECT-TYPE
    SYNTAX      TmnxMobPdnBcAcctGyEntry
    MAX-ACCESS  not-accessible
    STATUS      current
    DESCRIPTION
        "Each row entry represents a bearer context of an User Equipment (UE)
         and contains reference point Gy Accounting statistics information."
    AUGMENTS { tmnxMobPdnBearerContextEntry }
    ::= { tmnxMobPdnBcAcctGyTable 1 }

TmnxMobPdnBcAcctGyEntry ::= SEQUENCE {
        tmnxMobPdnBcAcctGyChargingId       TmnxMobChargingProfile,
        tmnxMobPdnBcAcctGyUlSustRate       Counter32,
        tmnxMobPdnBcAcctGyDlSustRate       Counter32,
        tmnxMobPdnBcAcctGyAggrUlPkts       Counter64,
        tmnxMobPdnBcAcctGyAggrUlPktsLow    Counter32,
        tmnxMobPdnBcAcctGyAggrUlPktsHigh   Counter32,
        tmnxMobPdnBcAcctGyAggrDlPkts       Counter64,
        tmnxMobPdnBcAcctGyAggrDlPktsLow    Counter32,
        tmnxMobPdnBcAcctGyAggrDlPktsHigh   Counter32,
        tmnxMobPdnBcAcctGyAggrUlByts       Counter64,
        tmnxMobPdnBcAcctGyAggrUlBytsLow    Counter32,
        tmnxMobPdnBcAcctGyAggrUlBytsHigh   Counter32,
        tmnxMobPdnBcAcctGyAggrDlByts       Counter64,
        tmnxMobPdnBcAcctGyAggrDlBytsLow    Counter32,
        tmnxMobPdnBcAcctGyAggrDlBytsHigh   Counter32,
        tmnxMobPdnBcAcctGyNumRedirection   Counter32,
        tmnxMobPdnBcAcctGyLastRedctTime    TimeStamp,
        tmnxMobPdnBcAcctGyNumCreditsRepl   Counter32,
        tmnxMobPdnBcAcctGyLstCrdReplTime   TimeStamp,
        tmnxMobPdnBcAcctGyNumRgs           Counter32,            
        tmnxMobPdnBcAcctGyNumOfRgSvcId     Counter32
    }

tmnxMobPdnBcAcctGyChargingId  OBJECT-TYPE
    SYNTAX      TmnxMobChargingProfile
    MAX-ACCESS  read-only
    STATUS      current
    DESCRIPTION
        "The value of tmnxMobPdnBcAcctGyChargingId indicates the charging
         profile assigned by the Packet Data Network Gateway (PGW) for
         this bearer."
    ::= { tmnxMobPdnBcAcctGyEntry 1 }

tmnxMobPdnBcAcctGyUlSustRate  OBJECT-TYPE
    SYNTAX      Counter32
    MAX-ACCESS  read-only
    STATUS      current
    DESCRIPTION
        "The value of tmnxMobPdnBcAcctGyUlSustRate indicates the uplink
         sustained rate for this bearer since last 5 minutes."
    ::= { tmnxMobPdnBcAcctGyEntry 2 }

tmnxMobPdnBcAcctGyDlSustRate  OBJECT-TYPE
    SYNTAX      Counter32
    MAX-ACCESS  read-only
    STATUS      current
    DESCRIPTION
        "The value of tmnxMobPdnBcAcctGyDlSustRate indicates the downlink
         sustained rate for this bearer since last 5 minutes."
    ::= { tmnxMobPdnBcAcctGyEntry 3 }

tmnxMobPdnBcAcctGyAggrUlPkts  OBJECT-TYPE
    SYNTAX      Counter64
    MAX-ACCESS  read-only
    STATUS      current
    DESCRIPTION
        "The value of tmnxMobPdnBcAcctGyAggrUlPkts indicates the aggregate
         uplink packets for this bearer."
    ::= { tmnxMobPdnBcAcctGyEntry 4 }

tmnxMobPdnBcAcctGyAggrUlPktsLow  OBJECT-TYPE
    SYNTAX      Counter32
    MAX-ACCESS  read-only
    STATUS      current
    DESCRIPTION
        "The value of tmnxMobPdnBcAcctGyAggrUlPktsLow indicates the lower 32
         bits of the value of tmnxMobPdnBcAcctGyAggrUlPkts."
    ::= { tmnxMobPdnBcAcctGyEntry 5 }

tmnxMobPdnBcAcctGyAggrUlPktsHigh  OBJECT-TYPE
    SYNTAX      Counter32
    MAX-ACCESS  read-only
    STATUS      current
    DESCRIPTION
        "The value of tmnxMobPdnBcAcctGyAggrUlPktsHigh indicates the higer 32
         bits of the value of tmnxMobPdnBcAcctGyAggrUlPkts."
    ::= { tmnxMobPdnBcAcctGyEntry 6 }

tmnxMobPdnBcAcctGyAggrDlPkts  OBJECT-TYPE
    SYNTAX      Counter64
    MAX-ACCESS  read-only
    STATUS      current
    DESCRIPTION
        "The value of tmnxMobPdnBcAcctGyAggrDlPkts indicates the aggregate
         downlink packets for this bearer."
    ::= { tmnxMobPdnBcAcctGyEntry 7 }

tmnxMobPdnBcAcctGyAggrDlPktsLow  OBJECT-TYPE
    SYNTAX      Counter32
    MAX-ACCESS  read-only
    STATUS      current
    DESCRIPTION
        "The value of tmnxMobPdnBcAcctGyAggrDlPktsLow indicates the lower 32
         bits of the value of tmnxMobPdnBcAcctGyAggrDlPkts."
    ::= { tmnxMobPdnBcAcctGyEntry 8 }

tmnxMobPdnBcAcctGyAggrDlPktsHigh  OBJECT-TYPE
    SYNTAX      Counter32
    MAX-ACCESS  read-only
    STATUS      current
    DESCRIPTION
        "The value of tmnxMobPdnBcAcctGyAggrDlPktsLow indicates the higer 32
         bits of the value of tmnxMobPdnBcAcctGyAggrDlPkts."
    ::= { tmnxMobPdnBcAcctGyEntry 9 }

tmnxMobPdnBcAcctGyAggrUlByts  OBJECT-TYPE
    SYNTAX      Counter64
    MAX-ACCESS  read-only
    STATUS      current
    DESCRIPTION
        "The value of tmnxMobPdnBcAcctGyAggrUlByts indicates the aggregate
         uplink bytes for this bearer."
    ::= { tmnxMobPdnBcAcctGyEntry 10 }

tmnxMobPdnBcAcctGyAggrUlBytsLow  OBJECT-TYPE
    SYNTAX      Counter32
    MAX-ACCESS  read-only
    STATUS      current
    DESCRIPTION
        "The value of tmnxMobPdnBcAcctGyAggrUlBytsLow indicates the lower 32
         bits of the value of tmnxMobPdnBcAcctGyAggrUlByts."
    ::= { tmnxMobPdnBcAcctGyEntry 11 }

tmnxMobPdnBcAcctGyAggrUlBytsHigh  OBJECT-TYPE
    SYNTAX      Counter32
    MAX-ACCESS  read-only
    STATUS      current
    DESCRIPTION
        "The value of tmnxMobPdnBcAcctGyAggrUlBytsHigh indicates the higer 32
         bits of the value of tmnxMobPdnBcAcctGyAggrUlByts."
    ::= { tmnxMobPdnBcAcctGyEntry 12 }

tmnxMobPdnBcAcctGyAggrDlByts  OBJECT-TYPE
    SYNTAX      Counter64
    MAX-ACCESS  read-only
    STATUS      current
    DESCRIPTION
        "The value of tmnxMobPdnBcAcctGyAggrDlByts indicates the aggregate
         downlink bytes for this bearer."
    ::= { tmnxMobPdnBcAcctGyEntry 13 }

tmnxMobPdnBcAcctGyAggrDlBytsLow  OBJECT-TYPE
    SYNTAX      Counter32
    MAX-ACCESS  read-only
    STATUS      current
    DESCRIPTION
        "The value of tmnxMobPdnBcAcctGyAggrDlBytsLow indicates the lower 32
         bits of the value of tmnxMobPdnBcAcctGyAggrDlByts."
    ::= { tmnxMobPdnBcAcctGyEntry 14 }

tmnxMobPdnBcAcctGyAggrDlBytsHigh  OBJECT-TYPE
    SYNTAX      Counter32
    MAX-ACCESS  read-only
    STATUS      current
    DESCRIPTION
        "The value of tmnxMobPdnBcAcctGyAggrDlBytsLow indicates the higer 32
         bits of the value of tmnxMobPdnBcAcctGyAggrDlByts."
    ::= { tmnxMobPdnBcAcctGyEntry 15 }

tmnxMobPdnBcAcctGyNumRedirection  OBJECT-TYPE
    SYNTAX      Counter32
    MAX-ACCESS  read-only
    STATUS      current
    DESCRIPTION
        "The value of tmnxMobPdnBcAcctGyNumRedirection indicates the number of 
         times subscriber redirected to Accounting Portal due to quota
         exhaustion on this bearer."
    ::= { tmnxMobPdnBcAcctGyEntry 16 }

tmnxMobPdnBcAcctGyLastRedctTime  OBJECT-TYPE
    SYNTAX      TimeStamp
    MAX-ACCESS  read-only
    STATUS      current
    DESCRIPTION
        "The value of tmnxMobPdnBcAcctGyLastRedctTime indicates the time of the
         last redirection due to quota exhaustion for this bearer."
    ::= { tmnxMobPdnBcAcctGyEntry 17 }

tmnxMobPdnBcAcctGyNumCreditsRepl  OBJECT-TYPE
    SYNTAX      Counter32
    MAX-ACCESS  read-only
    STATUS      current
    DESCRIPTION
        "The value of tmnxMobPdnBcAcctGyNumCreditsRepl indicates the number of
         times redirection to accounting portal due to credit replenish for 
         this bearer."
    ::= { tmnxMobPdnBcAcctGyEntry 18 }

tmnxMobPdnBcAcctGyLstCrdReplTime  OBJECT-TYPE
    SYNTAX      TimeStamp
    MAX-ACCESS  read-only
    STATUS      current
    DESCRIPTION
        "The value of tmnxMobPdnBcAcctGyLstCrdReplTime indicates the time of the
         last credit replenish message sent for this bearer."

    ::= { tmnxMobPdnBcAcctGyEntry 19 }

tmnxMobPdnBcAcctGyNumRgs  OBJECT-TYPE
    SYNTAX      Counter32
    MAX-ACCESS  read-only
    STATUS      current
    DESCRIPTION
        "The value of tmnxMobPdnBcAcctGyNumRgs indicates the number of 
         Rating Groups associated with this bearer."
    ::= { tmnxMobPdnBcAcctGyEntry 20 }

tmnxMobPdnBcAcctGyNumOfRgSvcId  OBJECT-TYPE
    SYNTAX      Counter32
    MAX-ACCESS  read-only
    STATUS      current
    DESCRIPTION
        "The value of tmnxMobPdnBcAcctGyNumOfRgSvcId indicates the number of 
         unique Rating Group and Service Identifier pairs associated with this
         bearer."
    ::= { tmnxMobPdnBcAcctGyEntry 21 }

--
--  Acct Gy Charging Rule Unit Stats Table
--

tmnxMobPdnBcGyChrgTable  OBJECT-TYPE
    SYNTAX      SEQUENCE OF TmnxMobPdnBcGyChrgEntry
    MAX-ACCESS  not-accessible
    STATUS      current
    DESCRIPTION
        "The tmnxMobPdnBcGyChrgTable has an entry for each
         Rating Group and Service ID pair of an User Equipment (UE)."
    ::= { tmnxMobPdnStatObjs 24 }

tmnxMobPdnBcGyChrgEntry  OBJECT-TYPE
    SYNTAX      TmnxMobPdnBcGyChrgEntry
    MAX-ACCESS  not-accessible
    STATUS      current
    DESCRIPTION
        "Each row entry represents a Gy Charging Rule Unit statistics
         information for each Rating Group and Service ID pair of an User
         Equipment (UE)."
    INDEX { tmnxMobGwId,
            tmnxMobPdnUeImsi,
            tmnxMobPdnPcApn,
            tmnxMobPdnPcPdnType,
            tmnxMobPdnBcBearerId,
            tmnxMobProfChgUnitRatingGroup,
            tmnxMobProfChgUnitServIdentifier
          }
    ::= { tmnxMobPdnBcGyChrgTable 1 }

TmnxMobPdnBcGyChrgEntry ::= SEQUENCE {
        tmnxMobPdnBcGyChrgTimeGranted           TimeStamp,
        tmnxMobPdnBcGyChrgTimeUsed              TimeStamp,
        tmnxMobPdnBcGyChrgGrntTtlOct            Counter64,
        tmnxMobPdnBcGyChrgGrntTtlOctLow         Counter32,
        tmnxMobPdnBcGyChrgGrntTtlOctHigh        Counter32,
        tmnxMobPdnBcGyChrgGrntInOct             Counter64,
        tmnxMobPdnBcGyChrgGrntInOctLow          Counter32,
        tmnxMobPdnBcGyChrgGrntInOctHigh         Counter32,
        tmnxMobPdnBcGyChrgGrntOutOct            Counter64,
        tmnxMobPdnBcGyChrgGrntOutOctLow         Counter32,
        tmnxMobPdnBcGyChrgGrntOutOctHigh        Counter32,
        tmnxMobPdnBcGyChrgUsedTtlOct            Counter64,
        tmnxMobPdnBcGyChrgUsedTtlOctLow         Counter32,
        tmnxMobPdnBcGyChrgUsedTtlOctHigh        Counter32,
        tmnxMobPdnBcGyChrgUsedInOct             Counter64,
        tmnxMobPdnBcGyChrgUsedInOctLow          Counter32,
        tmnxMobPdnBcGyChrgUsedInOctHigh         Counter32,
        tmnxMobPdnBcGyChrgUsedOutOct            Counter64,
        tmnxMobPdnBcGyChrgUsedOutOctLow         Counter32,
        tmnxMobPdnBcGyChrgUsedOutOctHigh        Counter32,            
        tmnxMobPdnBcGyChrgRatingGrpState        TmnxMobRatingGrpState,
        tmnxMobPdnBcGyChrgTimeBasedRep          TmnxEnabledDisabled,
        tmnxMobPdnBcGyChrgVolumeBasedRep        TmnxEnabledDisabled,        
        tmnxMobPdnBcGyChrgQctPresent            TmnxMobPresenceState,
        tmnxMobPdnBcGyChrgQctGranted            Unsigned32,
        tmnxMobPdnBcGyChrgQhtPresent            TmnxMobPresenceState,
        tmnxMobPdnBcGyChrgQhtGranted            Unsigned32,
        tmnxMobPdnBcGyChrgQhtRemaining          Unsigned32,
        tmnxMobPdnBcGyChrgQvtPresent            TmnxMobPresenceState,
        tmnxMobPdnBcGyChrgQvtRemaining          Unsigned32,
        tmnxMobPdnBcGyChrgTtcPresent            TmnxMobPresenceState,
        tmnxMobPdnBcGyChrgTarrifTimeChng        Unsigned32,
        tmnxMobPdnBcGyChrgFuiPresent            TmnxMobPresenceState,
        tmnxMobPdnBcGyChrgOnlineEnabled         TmnxEnabledDisabled,
        tmnxMobPdnBcGyChrgTimeThreshold         Unsigned32,
        tmnxMobPdnBcGyChrgVolThreshold          Unsigned32,
        tmnxMobPdnBcGyChrgTrigger               TmnxMobPdnGyChrgTriggerType,
        tmnxMobPdnBcGyChrgActvThreshold         Unsigned32,
        tmnxMobPdnBcGyChrgRedServerType         InetAddressType,
        tmnxMobPdnBcGyChrgRedServer             InetAddress,
        tmnxMobPdnBcGyChrgBillingMethod         INTEGER,
        tmnxMobPdnBcGyChrgReportingLevel        INTEGER,
        tmnxMobPdnBcGyChrgResultCode            Unsigned32
    }

tmnxMobPdnBcGyChrgTimeGranted  OBJECT-TYPE
    SYNTAX      TimeStamp
    MAX-ACCESS  read-only
    STATUS      current
    DESCRIPTION
        "The value of tmnxMobPdnBcGyChrgTimeGranted indicates the total
         time granted for this Rating Group and Service ID pair."        
    ::= { tmnxMobPdnBcGyChrgEntry 1 }

tmnxMobPdnBcGyChrgTimeUsed  OBJECT-TYPE
    SYNTAX      TimeStamp
    MAX-ACCESS  read-only
    STATUS      current
    DESCRIPTION
        "The value of tmnxMobPdnBcGyChrgTimeUsed indicates the total
         time used for this Rating Group and Service ID pair."        
    ::= { tmnxMobPdnBcGyChrgEntry 2 }

tmnxMobPdnBcGyChrgGrntTtlOct  OBJECT-TYPE
    SYNTAX      Counter64
    MAX-ACCESS  read-only
    STATUS      current
    DESCRIPTION
        "The value of tmnxMobPdnBcGyChrgGrntTtlOct indicates the total
         octets granted for this Rating Group and Service ID pair."
    ::= { tmnxMobPdnBcGyChrgEntry 3 }

tmnxMobPdnBcGyChrgGrntTtlOctLow  OBJECT-TYPE
    SYNTAX      Counter32
    MAX-ACCESS  read-only
    STATUS      current
    DESCRIPTION
        "The value of tmnxMobPdnBcGyChrgGrntTtlOctLow indicates the lower 32
         bits of the value of tmnxMobPdnBcGyChrgGrntTtlOct."
    ::= { tmnxMobPdnBcGyChrgEntry 4 }

tmnxMobPdnBcGyChrgGrntTtlOctHigh  OBJECT-TYPE
    SYNTAX      Counter32
    MAX-ACCESS  read-only
    STATUS      current
    DESCRIPTION
        "The value of tmnxMobPdnBcGyChrgGrntTtlOctHigh indicates the higer 32
         bits of the value of tmnxMobPdnBcGyChrgGrntTtlOct."
    ::= { tmnxMobPdnBcGyChrgEntry 5 }

tmnxMobPdnBcGyChrgGrntInOct  OBJECT-TYPE
    SYNTAX      Counter64
    MAX-ACCESS  read-only
    STATUS      current
    DESCRIPTION
        "The value of tmnxMobPdnBcGyChrgGrntInOct indicates the total
         octets granted for this Rating Group and Service ID pair."
    ::= { tmnxMobPdnBcGyChrgEntry 6 }

tmnxMobPdnBcGyChrgGrntInOctLow  OBJECT-TYPE
    SYNTAX      Counter32
    MAX-ACCESS  read-only
    STATUS      current
    DESCRIPTION
        "The value of tmnxMobPdnBcGyChrgGrntInOctLow indicates the lower 32
         bits of the value of tmnxMobPdnBcGyChrgGrntInOct."
    ::= { tmnxMobPdnBcGyChrgEntry 7 }

tmnxMobPdnBcGyChrgGrntInOctHigh  OBJECT-TYPE
    SYNTAX      Counter32
    MAX-ACCESS  read-only
    STATUS      current
    DESCRIPTION
        "The value of tmnxMobPdnBcGyChrgGrntInOctHigh indicates the higer 32
         bits of the value of tmnxMobPdnBcGyChrgGrntInOct."
    ::= { tmnxMobPdnBcGyChrgEntry 8 }

tmnxMobPdnBcGyChrgGrntOutOct  OBJECT-TYPE
    SYNTAX      Counter64
    MAX-ACCESS  read-only
    STATUS      current
    DESCRIPTION
        "The value of tmnxMobPdnBcGyChrgGrntOutOct indicates the total
         octets granted for this Rating Group and Service ID pair."
    ::= { tmnxMobPdnBcGyChrgEntry 9 }

tmnxMobPdnBcGyChrgGrntOutOctLow  OBJECT-TYPE
    SYNTAX      Counter32
    MAX-ACCESS  read-only
    STATUS      current
    DESCRIPTION
        "The value of tmnxMobPdnBcGyChrgGrntOutOctLow indicates the lower 32
         bits of the value of tmnxMobPdnBcGyChrgGrntOutOct."
    ::= { tmnxMobPdnBcGyChrgEntry 10 }

tmnxMobPdnBcGyChrgGrntOutOctHigh  OBJECT-TYPE
    SYNTAX      Counter32
    MAX-ACCESS  read-only
    STATUS      current
    DESCRIPTION
        "The value of tmnxMobPdnBcGyChrgGrntOutOctHigh indicates the higer 32
         bits of the value of tmnxMobPdnBcGyChrgGrntOutOct."
    ::= { tmnxMobPdnBcGyChrgEntry 11 }

tmnxMobPdnBcGyChrgUsedTtlOct  OBJECT-TYPE
    SYNTAX      Counter64
    MAX-ACCESS  read-only
    STATUS      current
    DESCRIPTION
        "The value of tmnxMobPdnBcGyChrgUsedTtlOct indicates the total
         octets granted for this Rating Group and Service ID pair."
    ::= { tmnxMobPdnBcGyChrgEntry 12 }

tmnxMobPdnBcGyChrgUsedTtlOctLow  OBJECT-TYPE
    SYNTAX      Counter32
    MAX-ACCESS  read-only
    STATUS      current
    DESCRIPTION
        "The value of tmnxMobPdnBcGyChrgUsedTtlOctLow indicates the lower 32
         bits of the value of tmnxMobPdnBcGyChrgUsedTtlOct."
    ::= { tmnxMobPdnBcGyChrgEntry 13 }

tmnxMobPdnBcGyChrgUsedTtlOctHigh  OBJECT-TYPE
    SYNTAX      Counter32
    MAX-ACCESS  read-only
    STATUS      current
    DESCRIPTION
        "The value of tmnxMobPdnBcGyChrgUsedTtlOctHigh indicates the higer 32
         bits of the value of tmnxMobPdnBcGyChrgUsedTtlOct."
    ::= { tmnxMobPdnBcGyChrgEntry 14 }

tmnxMobPdnBcGyChrgUsedInOct  OBJECT-TYPE
    SYNTAX      Counter64
    MAX-ACCESS  read-only
    STATUS      current
    DESCRIPTION
        "The value of tmnxMobPdnBcGyChrgUsedInOct indicates the total
         octets granted for this Rating Group and Service ID pair."
    ::= { tmnxMobPdnBcGyChrgEntry 15 }

tmnxMobPdnBcGyChrgUsedInOctLow  OBJECT-TYPE
    SYNTAX      Counter32
    MAX-ACCESS  read-only
    STATUS      current
    DESCRIPTION
        "The value of tmnxMobPdnBcGyChrgUsedInOctLow indicates the lower 32
         bits of the value of tmnxMobPdnBcGyChrgUsedInOct."
    ::= { tmnxMobPdnBcGyChrgEntry 16 }

tmnxMobPdnBcGyChrgUsedInOctHigh  OBJECT-TYPE
    SYNTAX      Counter32
    MAX-ACCESS  read-only
    STATUS      current
    DESCRIPTION
        "The value of tmnxMobPdnBcGyChrgUsedInOctHigh indicates the higer 32
         bits of the value of tmnxMobPdnBcGyChrgUsedInOct."
    ::= { tmnxMobPdnBcGyChrgEntry 17 }

tmnxMobPdnBcGyChrgUsedOutOct  OBJECT-TYPE
    SYNTAX      Counter64
    MAX-ACCESS  read-only
    STATUS      current
    DESCRIPTION
        "The value of tmnxMobPdnBcGyChrgUsedOutOct indicates the total
         octets granted for this Rating Group and Service ID pair."
    ::= { tmnxMobPdnBcGyChrgEntry 18 }

tmnxMobPdnBcGyChrgUsedOutOctLow  OBJECT-TYPE
    SYNTAX      Counter32
    MAX-ACCESS  read-only
    STATUS      current
    DESCRIPTION
        "The value of tmnxMobPdnBcGyChrgUsedOutOctLow indicates the lower 32
         bits of the value of tmnxMobPdnBcGyChrgUsedOutOct."
    ::= { tmnxMobPdnBcGyChrgEntry 19 }

tmnxMobPdnBcGyChrgUsedOutOctHigh  OBJECT-TYPE
    SYNTAX      Counter32
    MAX-ACCESS  read-only
    STATUS      current
    DESCRIPTION
        "The value of tmnxMobPdnBcGyChrgUsedOutOctHigh indicates the higer 32
         bits of the value of tmnxMobPdnBcGyChrgUsedOutOct."
    ::= { tmnxMobPdnBcGyChrgEntry 20 }

tmnxMobPdnBcGyChrgRatingGrpState  OBJECT-TYPE
    SYNTAX      TmnxMobRatingGrpState
    MAX-ACCESS  read-only
    STATUS      current
    DESCRIPTION
        "The value of tmnxMobPdnBcGyChrgRatingGrpState indicates the state of
         the Rating Group."
    ::= { tmnxMobPdnBcGyChrgEntry 21 }

tmnxMobPdnBcGyChrgTimeBasedRep  OBJECT-TYPE
    SYNTAX      TmnxEnabledDisabled
    MAX-ACCESS  read-only
    STATUS      current
    DESCRIPTION
        "The value of tmnxMobPdnBcGyChrgTimeBasedRep indicates whether the time
         based reporting is enabled."
    ::= { tmnxMobPdnBcGyChrgEntry 22 }

tmnxMobPdnBcGyChrgVolumeBasedRep  OBJECT-TYPE
    SYNTAX      TmnxEnabledDisabled
    MAX-ACCESS  read-only
    STATUS      current
    DESCRIPTION
        "The value of tmnxMobPdnBcGyChrgVolumeBasedRep indicates whether the
         volume based reporting is enabled."
    ::= { tmnxMobPdnBcGyChrgEntry 23 }

tmnxMobPdnBcGyChrgQctPresent  OBJECT-TYPE
    SYNTAX      TmnxMobPresenceState
    MAX-ACCESS  read-only
    STATUS      current
    DESCRIPTION
        "The value of tmnxMobPdnBcGyChrgQctPresent indicates whether the
         Quota Consumption Time (QCT) field is received from the Online Charging
         System (OCS)."
    ::= { tmnxMobPdnBcGyChrgEntry 24 }

tmnxMobPdnBcGyChrgQctGranted  OBJECT-TYPE
    SYNTAX      Unsigned32
    UNITS       "seconds"
    MAX-ACCESS  read-only
    STATUS      current
    DESCRIPTION
        "The value of tmnxMobPdnBcGyChrgQctPresent indicates the Quota
         Consumption Time (QCT) received from the Online Charging System (OCS)."
    ::= { tmnxMobPdnBcGyChrgEntry 25 }

tmnxMobPdnBcGyChrgQhtPresent  OBJECT-TYPE
    SYNTAX      TmnxMobPresenceState
    MAX-ACCESS  read-only
    STATUS      current
    DESCRIPTION
        "The value of tmnxMobPdnBcGyChrgQhtPresent indicates whether the
         Quota Hold Time (QHT) field is received from the Online Charging
         System (OCS)."
    ::= { tmnxMobPdnBcGyChrgEntry 26 }

tmnxMobPdnBcGyChrgQhtGranted  OBJECT-TYPE
    SYNTAX      Unsigned32
    UNITS       "seconds"
    MAX-ACCESS  read-only
    STATUS      current
    DESCRIPTION
        "The value of tmnxMobPdnBcGyChrgQhtPresent indicates the granted Quota
         Hold Time (QHT) received from the Online Charging System (OCS)."
    ::= { tmnxMobPdnBcGyChrgEntry 27 }

tmnxMobPdnBcGyChrgQhtRemaining  OBJECT-TYPE
    SYNTAX      Unsigned32
    UNITS       "seconds"
    MAX-ACCESS  read-only
    STATUS      current
    DESCRIPTION
        "The value of tmnxMobPdnBcGyChrgQhtRemaining indicates the remaining
         Quota Hold Time (QHT)."
    ::= { tmnxMobPdnBcGyChrgEntry 28 }

tmnxMobPdnBcGyChrgQvtPresent  OBJECT-TYPE
    SYNTAX      TmnxMobPresenceState
    MAX-ACCESS  read-only
    STATUS      current
    DESCRIPTION
        "The value of tmnxMobPdnBcGyChrgQvtPresent indicates whether the
         Quota Validity Time (QVT) field is received from the Online Charging
         System (OCS)."
    ::= { tmnxMobPdnBcGyChrgEntry 29 }

tmnxMobPdnBcGyChrgQvtRemaining  OBJECT-TYPE
    SYNTAX      Unsigned32
    UNITS       "seconds"
    MAX-ACCESS  read-only
    STATUS      current
    DESCRIPTION
        "The value of tmnxMobPdnBcGyChrgQvtRemaining indicates the remaining
         Quota Validity Time (QVT)."
    ::= { tmnxMobPdnBcGyChrgEntry 30 }

tmnxMobPdnBcGyChrgTtcPresent  OBJECT-TYPE
    SYNTAX      TmnxMobPresenceState
    MAX-ACCESS  read-only
    STATUS      current
    DESCRIPTION
        "The value of tmnxMobPdnBcGyChrgTtcPresent indicates whether the
         Tariff Time Change (TTC) field is received from the Online Charging
         System (OCS)."
    ::= { tmnxMobPdnBcGyChrgEntry 31 }

tmnxMobPdnBcGyChrgTarrifTimeChng  OBJECT-TYPE
    SYNTAX      Unsigned32
    UNITS       "seconds"
    MAX-ACCESS  read-only
    STATUS      current
    DESCRIPTION
        "The value of tmnxMobPdnBcGyChrgTarrifTimeChng indicates the 
         Tariff Time Change (TTC)."
    ::= { tmnxMobPdnBcGyChrgEntry 32 }

tmnxMobPdnBcGyChrgFuiPresent  OBJECT-TYPE
    SYNTAX      TmnxMobPresenceState
    MAX-ACCESS  read-only
    STATUS      current
    DESCRIPTION
        "The value of tmnxMobPdnBcGyChrgFuiPresent indicates whether the
         Final Unit Indication (FUI) field is received from the Online Charging
         System (OCS)."
    ::= { tmnxMobPdnBcGyChrgEntry 33 }

tmnxMobPdnBcGyChrgOnlineEnabled  OBJECT-TYPE
    SYNTAX      TmnxEnabledDisabled
    MAX-ACCESS  read-only
    STATUS      current
    DESCRIPTION
        "The value of tmnxMobPdnBcGyChrgOnlineEnabled indicates whether the 
         online charging is enabled."
    ::= { tmnxMobPdnBcGyChrgEntry 34 }

tmnxMobPdnBcGyChrgTimeThreshold  OBJECT-TYPE
    SYNTAX      Unsigned32
    UNITS       "seconds"
    MAX-ACCESS  read-only
    STATUS      current
    DESCRIPTION
        "The value of tmnxMobPdnBcGyChrgTimeThreshold indicates the Time 
         Threshold received from the Online Charging System (OCS)."
    ::= { tmnxMobPdnBcGyChrgEntry 35 }

tmnxMobPdnBcGyChrgVolThreshold  OBJECT-TYPE
    SYNTAX      Unsigned32
    UNITS       "bytes"
    MAX-ACCESS  read-only
    STATUS      current
    DESCRIPTION
        "The value of tmnxMobPdnBcGyChrgVolThreshold indicates the Volume 
         Threshold received from the Online Charging System (OCS)."
    ::= { tmnxMobPdnBcGyChrgEntry 36 }

tmnxMobPdnBcGyChrgTrigger  OBJECT-TYPE
    SYNTAX      TmnxMobPdnGyChrgTriggerType
    MAX-ACCESS  read-only
    STATUS      current
    DESCRIPTION
        "The value of tmnxMobPdnBcGyChrgTrigger indicates the trigger activated  
         by the Online Charging System (OCS)."
    ::= { tmnxMobPdnBcGyChrgEntry 37 }

tmnxMobPdnBcGyChrgActvThreshold  OBJECT-TYPE
    SYNTAX      Unsigned32
    UNITS       "bytes"
    MAX-ACCESS  read-only
    STATUS      current
    DESCRIPTION
        "The value of tmnxMobPdnBcGyChrgActvThreshold indicates the Activity 
         Threshold time."
    ::= { tmnxMobPdnBcGyChrgEntry 38 }

tmnxMobPdnBcGyChrgRedServerType  OBJECT-TYPE
    SYNTAX      InetAddressType
    MAX-ACCESS  read-only
    STATUS      current
    DESCRIPTION 
        "The value of tmnxMobPdnBcGyChrgRedServerType indicates the type of
         address represented by tmnxMobPdnBcGyChrgRedServer."
    ::= { tmnxMobPdnBcGyChrgEntry 39 }

tmnxMobPdnBcGyChrgRedServer  OBJECT-TYPE 
    SYNTAX      InetAddress
    MAX-ACCESS  read-only
    STATUS      current
    DESCRIPTION
        "The value of tmnxMobPdnBcGyChrgRedServer indicates the value of
         server to which traffic is redirected when Final Unit Indication (FUI)
         Redirect is applied."
    ::= { tmnxMobPdnBcGyChrgEntry 40 }

tmnxMobPdnBcGyChrgBillingMethod  OBJECT-TYPE
    SYNTAX     INTEGER
                {
                        online          (1),
                        offline         (2),
                        onlineOffline   (3)
                }
    MAX-ACCESS  read-only
    STATUS      current
    DESCRIPTION
        "The value of tmnxMobPdnBcGyChrgBillingMethod indicates the billing
         method used."
    ::= { tmnxMobPdnBcGyChrgEntry 41 }

tmnxMobPdnBcGyChrgReportingLevel  OBJECT-TYPE
    SYNTAX     INTEGER
                {
                        svcIdLevel       (1),
                        rgLevel          (2)
                }
    MAX-ACCESS  read-only
    STATUS      current
    DESCRIPTION
        "The value of tmnxMobPdnBcGyChrgReportingLevel indicates the reporting 
         level used."
    ::= { tmnxMobPdnBcGyChrgEntry 42 }

tmnxMobPdnBcGyChrgResultCode  OBJECT-TYPE
    SYNTAX      Unsigned32
    MAX-ACCESS  read-only
    STATUS      current
    DESCRIPTION
        "The value of tmnxMobPdnBcGyChrgResultCode indicates the last
         diameter result code received for this Rating Group(RG)."
    ::= { tmnxMobPdnBcGyChrgEntry 43 }

--
--  Bearer Context Accounting Rf Table
--

tmnxMobPdnBcAcctRfTable  OBJECT-TYPE
    SYNTAX      SEQUENCE OF TmnxMobPdnBcAcctRfEntry
    MAX-ACCESS  not-accessible
    STATUS      current
    DESCRIPTION
        "The tmnxMobPdnBcAcctRfTable has an entry for each bearer context
         of an User Equipment (UE).

         The tmnxMobPdnBcAcctRfTable provides an extension of the 
         tmnxMobPdnBearerContextTable."
    ::= { tmnxMobPdnStatObjs 25 }

tmnxMobPdnBcAcctRfEntry  OBJECT-TYPE
    SYNTAX      TmnxMobPdnBcAcctRfEntry
    MAX-ACCESS  not-accessible
    STATUS      current
    DESCRIPTION
        "Each row entry represents a bearer context of an User Equipment (UE)
         and contains reference point Rf Accounting statistics information."
    AUGMENTS { tmnxMobPdnBearerContextEntry }
    ::= { tmnxMobPdnBcAcctRfTable 1 }

TmnxMobPdnBcAcctRfEntry ::= SEQUENCE {
        tmnxMobPdnBcAcctRfChargingId       TmnxMobChargingProfile,
        tmnxMobPdnBcAcctRfUlSustRate       Counter32,
        tmnxMobPdnBcAcctRfDlSustRate       Counter32,
        tmnxMobPdnBcAcctRfAggrUlPkts       Counter64,
        tmnxMobPdnBcAcctRfAggrUlPktsLow    Counter32,
        tmnxMobPdnBcAcctRfAggrUlPktsHigh   Counter32,
        tmnxMobPdnBcAcctRfAggrDlPkts       Counter64,
        tmnxMobPdnBcAcctRfAggrDlPktsLow    Counter32,
        tmnxMobPdnBcAcctRfAggrDlPktsHigh   Counter32,
        tmnxMobPdnBcAcctRfAggrUlByts       Counter64,
        tmnxMobPdnBcAcctRfAggrUlBytsLow    Counter32,
        tmnxMobPdnBcAcctRfAggrUlBytsHigh   Counter32,
        tmnxMobPdnBcAcctRfAggrDlByts       Counter64,
        tmnxMobPdnBcAcctRfAggrDlBytsLow    Counter32,
        tmnxMobPdnBcAcctRfAggrDlBytsHigh   Counter32,
        tmnxMobPdnBcAcctRfNumInterimSent   Counter32,
        tmnxMobPdnBcAcctRfNumRgs           Counter32,            
        tmnxMobPdnBcAcctRfNumOfRgSvcId     Counter32
    }

tmnxMobPdnBcAcctRfChargingId  OBJECT-TYPE
    SYNTAX      TmnxMobChargingProfile
    MAX-ACCESS  read-only
    STATUS      current
    DESCRIPTION
        "The value of tmnxMobPdnBcAcctRfChargingId indicates the charging
         profile assigned by the Packet Data Network Gateway (PGW) for
         this bearer."
    ::= { tmnxMobPdnBcAcctRfEntry 1 }

tmnxMobPdnBcAcctRfUlSustRate  OBJECT-TYPE
    SYNTAX      Counter32
    MAX-ACCESS  read-only
    STATUS      current
    DESCRIPTION
        "The value of tmnxMobPdnBcAcctRfUlSustRate indicates the uplink
         sustained rate for this bearer since last 5 minutes."
    ::= { tmnxMobPdnBcAcctRfEntry 2 }

tmnxMobPdnBcAcctRfDlSustRate  OBJECT-TYPE
    SYNTAX      Counter32
    MAX-ACCESS  read-only
    STATUS      current
    DESCRIPTION
        "The value of tmnxMobPdnBcAcctRfDlSustRate indicates the downlink
         sustained rate for this bearer since last 5 minutes."
    ::= { tmnxMobPdnBcAcctRfEntry 3 }

tmnxMobPdnBcAcctRfAggrUlPkts  OBJECT-TYPE
    SYNTAX      Counter64
    MAX-ACCESS  read-only
    STATUS      current
    DESCRIPTION
        "The value of tmnxMobPdnBcAcctRfAggrUlPkts indicates the aggregate
         uplink packets for this bearer."
    ::= { tmnxMobPdnBcAcctRfEntry 4 }

tmnxMobPdnBcAcctRfAggrUlPktsLow  OBJECT-TYPE
    SYNTAX      Counter32
    MAX-ACCESS  read-only
    STATUS      current
    DESCRIPTION
        "The value of tmnxMobPdnBcAcctRfAggrUlPktsLow indicates the lower 32
         bits of the value of tmnxMobPdnBcAcctRfAggrUlPkts."
    ::= { tmnxMobPdnBcAcctRfEntry 5 }

tmnxMobPdnBcAcctRfAggrUlPktsHigh  OBJECT-TYPE
    SYNTAX      Counter32
    MAX-ACCESS  read-only
    STATUS      current
    DESCRIPTION
        "The value of tmnxMobPdnBcAcctRfAggrUlPktsHigh indicates the higer 32
         bits of the value of tmnxMobPdnBcAcctRfAggrUlPkts."
    ::= { tmnxMobPdnBcAcctRfEntry 6 }

tmnxMobPdnBcAcctRfAggrDlPkts  OBJECT-TYPE
    SYNTAX      Counter64
    MAX-ACCESS  read-only
    STATUS      current
    DESCRIPTION
        "The value of tmnxMobPdnBcAcctRfAggrDlPkts indicates the aggregate
         downlink packets for this bearer."
    ::= { tmnxMobPdnBcAcctRfEntry 7 }

tmnxMobPdnBcAcctRfAggrDlPktsLow  OBJECT-TYPE
    SYNTAX      Counter32
    MAX-ACCESS  read-only
    STATUS      current
    DESCRIPTION
        "The value of tmnxMobPdnBcAcctRfAggrDlPktsLow indicates the lower 32
         bits of the value of tmnxMobPdnBcAcctRfAggrDlPkts."
    ::= { tmnxMobPdnBcAcctRfEntry 8 }

tmnxMobPdnBcAcctRfAggrDlPktsHigh  OBJECT-TYPE
    SYNTAX      Counter32
    MAX-ACCESS  read-only
    STATUS      current
    DESCRIPTION
        "The value of tmnxMobPdnBcAcctRfAggrDlPktsLow indicates the higer 32
         bits of the value of tmnxMobPdnBcAcctRfAggrDlPkts."
    ::= { tmnxMobPdnBcAcctRfEntry 9 }

tmnxMobPdnBcAcctRfAggrUlByts  OBJECT-TYPE
    SYNTAX      Counter64
    MAX-ACCESS  read-only
    STATUS      current
    DESCRIPTION
        "The value of tmnxMobPdnBcAcctRfAggrUlByts indicates the aggregate
         uplink bytes for this bearer."
    ::= { tmnxMobPdnBcAcctRfEntry 10 }

tmnxMobPdnBcAcctRfAggrUlBytsLow  OBJECT-TYPE
    SYNTAX      Counter32
    MAX-ACCESS  read-only
    STATUS      current
    DESCRIPTION
        "The value of tmnxMobPdnBcAcctRfAggrUlBytsLow indicates the lower 32
         bits of the value of tmnxMobPdnBcAcctRfAggrUlByts."
    ::= { tmnxMobPdnBcAcctRfEntry 11 }

tmnxMobPdnBcAcctRfAggrUlBytsHigh  OBJECT-TYPE
    SYNTAX      Counter32
    MAX-ACCESS  read-only
    STATUS      current
    DESCRIPTION
        "The value of tmnxMobPdnBcAcctRfAggrUlBytsHigh indicates the higer 32
         bits of the value of tmnxMobPdnBcAcctRfAggrUlByts."
    ::= { tmnxMobPdnBcAcctRfEntry 12 }

tmnxMobPdnBcAcctRfAggrDlByts  OBJECT-TYPE
    SYNTAX      Counter64
    MAX-ACCESS  read-only
    STATUS      current
    DESCRIPTION
        "The value of tmnxMobPdnBcAcctRfAggrDlByts indicates the aggregate
         downlink bytes for this bearer."
    ::= { tmnxMobPdnBcAcctRfEntry 13 }

tmnxMobPdnBcAcctRfAggrDlBytsLow  OBJECT-TYPE
    SYNTAX      Counter32
    MAX-ACCESS  read-only
    STATUS      current
    DESCRIPTION
        "The value of tmnxMobPdnBcAcctRfAggrDlBytsLow indicates the lower 32
         bits of the value of tmnxMobPdnBcAcctRfAggrDlByts."
    ::= { tmnxMobPdnBcAcctRfEntry 14 }

tmnxMobPdnBcAcctRfAggrDlBytsHigh  OBJECT-TYPE
    SYNTAX      Counter32
    MAX-ACCESS  read-only
    STATUS      current
    DESCRIPTION
        "The value of tmnxMobPdnBcAcctRfAggrDlBytsLow indicates the higer 32
         bits of the value of tmnxMobPdnBcAcctRfAggrDlByts."
    ::= { tmnxMobPdnBcAcctRfEntry 15 }

tmnxMobPdnBcAcctRfNumInterimSent  OBJECT-TYPE
    SYNTAX      Counter32
    MAX-ACCESS  read-only
    STATUS      current
    DESCRIPTION
        "The value of tmnxMobPdnBcAcctRfNumInterimSent indicates the number of 
         interim accounting messages sent for this bearer."
    ::= { tmnxMobPdnBcAcctRfEntry 16 }

tmnxMobPdnBcAcctRfNumRgs  OBJECT-TYPE
    SYNTAX      Counter32
    MAX-ACCESS  read-only
    STATUS      current
    DESCRIPTION
        "The value of tmnxMobPdnBcAcctRfNumRgs indicates the number of 
         Rating Groups for this bearer."
    ::= { tmnxMobPdnBcAcctRfEntry 17 }

tmnxMobPdnBcAcctRfNumOfRgSvcId  OBJECT-TYPE
    SYNTAX      Counter32
    MAX-ACCESS  read-only
    STATUS      current
    DESCRIPTION
        "The value of tmnxMobPdnBcAcctRfNumOfRgSvcId indicates the number of 
         unique Rating Group and Service Identifier pairs for this bearer."
    ::= { tmnxMobPdnBcAcctRfEntry 18 }

--
--  PDN Context Rf Acct Table
--

tmnxMobPdnPcAcctRfTable  OBJECT-TYPE
    SYNTAX      SEQUENCE OF TmmnxMobPdnPcAcctRfEntry
    MAX-ACCESS  not-accessible
    STATUS      current
    DESCRIPTION
        "The tmnxMobPdnPcAcctRfTable has an entry for each Pakcet Data
         Network (PDN) context of an User Equipment (UE).

         The tmnxMobPdnPcAcctRfTable provides an extension of the
         tmnxMobPdnPdnContextTable for Accounting Rf related information."
    ::= { tmnxMobPdnStatObjs 26 }

tmnxMobPdnPcAcctRfEntry  OBJECT-TYPE
    SYNTAX      TmmnxMobPdnPcAcctRfEntry
    MAX-ACCESS  not-accessible
    STATUS      current
    DESCRIPTION
        "Each row entry represents a Pakcet Data Network (PDN) context of an
         User Equipment (UE) and contains Accounting Rf interface related
         information."
    AUGMENTS { tmnxMobPdnPdnContextEntry }
    ::= { tmnxMobPdnPcAcctRfTable 1 }

TmmnxMobPdnPcAcctRfEntry ::= SEQUENCE {
        tmnxMobPdnPcAcctRfAggrUlPkts       Counter64,
        tmnxMobPdnPcAcctRfAggrUlPktsLow    Counter32,
        tmnxMobPdnPcAcctRfAggrUlPktsHigh   Counter32,
        tmnxMobPdnPcAcctRfAggrDlPkts       Counter64,
        tmnxMobPdnPcAcctRfAggrDlPktsLow    Counter32,
        tmnxMobPdnPcAcctRfAggrDlPktsHigh   Counter32,
        tmnxMobPdnPcAcctRfAggrUlByts       Counter64,
        tmnxMobPdnPcAcctRfAggrUlBytsLow    Counter32,
        tmnxMobPdnPcAcctRfAggrUlBytsHigh   Counter32,
        tmnxMobPdnPcAcctRfAggrDlByts       Counter64,
        tmnxMobPdnPcAcctRfAggrDlBytsLow    Counter32,
        tmnxMobPdnPcAcctRfAggrDlBytsHigh   Counter32,
        tmnxMobPdnPcAcctRfUlAvgRate        Counter32,
        tmnxMobPdnPcAcctRfDlAvgRate        Counter32,
        tmnxMobPdnPcAcctRfNumInterimSent   Counter32,
        tmnxMobPdnPcAcctRfNumRgs           Counter32,            
        tmnxMobPdnPcAcctRfNumOfRgSvcId     Counter32
    }

tmnxMobPdnPcAcctRfAggrUlPkts  OBJECT-TYPE
    SYNTAX      Counter64
    MAX-ACCESS  read-only
    STATUS      current
    DESCRIPTION
        "The value of tmnxMobPdnPcAcctRfAggrUlPkts indicates the aggregate
         uplink packets for this Pakcet Data Network (PDN) context."
    ::= { tmnxMobPdnPcAcctRfEntry 1 }

tmnxMobPdnPcAcctRfAggrUlPktsLow  OBJECT-TYPE
    SYNTAX      Counter32
    MAX-ACCESS  read-only
    STATUS      current
    DESCRIPTION
        "The value of tmnxMobPdnPcAcctRfAggrUlPktsLow indicates the lower 32
         bits of the value of tmnxMobPdnPcAcctRfAggrUlPkts."
    ::= { tmnxMobPdnPcAcctRfEntry 2 }

tmnxMobPdnPcAcctRfAggrUlPktsHigh  OBJECT-TYPE
    SYNTAX      Counter32
    MAX-ACCESS  read-only
    STATUS      current
    DESCRIPTION
        "The value of tmnxMobPdnPcAcctRfAggrUlPktsHigh indicates the higer 32
         bits of the value of tmnxMobPdnPcAcctRfAggrUlPkts."
    ::= { tmnxMobPdnPcAcctRfEntry 3 }

tmnxMobPdnPcAcctRfAggrDlPkts  OBJECT-TYPE
    SYNTAX      Counter64
    MAX-ACCESS  read-only
    STATUS      current
    DESCRIPTION
        "The value of tmnxMobPdnPcAcctRfAggrDlPkts indicates the aggregate
         downlink packets for this Pakcet Data Network (PDN) context."
    ::= { tmnxMobPdnPcAcctRfEntry 4 }

tmnxMobPdnPcAcctRfAggrDlPktsLow  OBJECT-TYPE
    SYNTAX      Counter32
    MAX-ACCESS  read-only
    STATUS      current
    DESCRIPTION
        "The value of tmnxMobPdnPcAcctRfAggrDlPktsLow indicates the lower 32
         bits of the value of tmnxMobPdnPcAcctRfAggrDlPkts."
    ::= { tmnxMobPdnPcAcctRfEntry 5 }

tmnxMobPdnPcAcctRfAggrDlPktsHigh  OBJECT-TYPE
    SYNTAX      Counter32
    MAX-ACCESS  read-only
    STATUS      current
    DESCRIPTION
        "The value of tmnxMobPdnPcAcctRfAggrDlPktsLow indicates the higer 32
         bits of the value of tmnxMobPdnPcAcctRfAggrDlPkts."
    ::= { tmnxMobPdnPcAcctRfEntry 6 }

tmnxMobPdnPcAcctRfAggrUlByts  OBJECT-TYPE
    SYNTAX      Counter64
    MAX-ACCESS  read-only
    STATUS      current
    DESCRIPTION
        "The value of tmnxMobPdnPcAcctRfAggrUlByts indicates the aggregate
         uplink bytes for this Pakcet Data Network (PDN) context."
    ::= { tmnxMobPdnPcAcctRfEntry 7 }

tmnxMobPdnPcAcctRfAggrUlBytsLow  OBJECT-TYPE
    SYNTAX      Counter32
    MAX-ACCESS  read-only
    STATUS      current
    DESCRIPTION
        "The value of tmnxMobPdnPcAcctRfAggrUlBytsLow indicates the lower 32
         bits of the value of tmnxMobPdnPcAcctRfAggrUlByts."
    ::= { tmnxMobPdnPcAcctRfEntry 8 }

tmnxMobPdnPcAcctRfAggrUlBytsHigh  OBJECT-TYPE
    SYNTAX      Counter32
    MAX-ACCESS  read-only
    STATUS      current
    DESCRIPTION
        "The value of tmnxMobPdnPcAcctRfAggrUlBytsHigh indicates the higer 32
         bits of the value of tmnxMobPdnPcAcctRfAggrUlByts."
    ::= { tmnxMobPdnPcAcctRfEntry 9 }

tmnxMobPdnPcAcctRfAggrDlByts  OBJECT-TYPE
    SYNTAX      Counter64
    MAX-ACCESS  read-only
    STATUS      current
    DESCRIPTION
        "The value of tmnxMobPdnPcAcctRfAggrDlByts indicates the aggregate
         downlink bytes for this Pakcet Data Network (PDN) context."
    ::= { tmnxMobPdnPcAcctRfEntry 10 }

tmnxMobPdnPcAcctRfAggrDlBytsLow  OBJECT-TYPE
    SYNTAX      Counter32
    MAX-ACCESS  read-only
    STATUS      current
    DESCRIPTION
        "The value of tmnxMobPdnPcAcctRfAggrDlBytsLow indicates the lower 32
         bits of the value of tmnxMobPdnPcAcctRfAggrDlByts."
    ::= { tmnxMobPdnPcAcctRfEntry 11 }

tmnxMobPdnPcAcctRfAggrDlBytsHigh  OBJECT-TYPE
    SYNTAX      Counter32
    MAX-ACCESS  read-only
    STATUS      current
    DESCRIPTION
        "The value of tmnxMobPdnPcAcctRfAggrDlBytsLow indicates the higer 32
         bits of the value of tmnxMobPdnPcAcctRfAggrDlByts."
    ::= { tmnxMobPdnPcAcctRfEntry 12 }

tmnxMobPdnPcAcctRfUlAvgRate  OBJECT-TYPE
    SYNTAX      Counter32
    UNITS       "kbps"
    MAX-ACCESS  read-only
    STATUS      current
    DESCRIPTION
        "The value of tmnxMobPdnPcAcctRfUlAvgRate indicates the average uplink  
         traffic on this Pakcet Data Network (PDN) context."
    ::= { tmnxMobPdnPcAcctRfEntry 13 }

tmnxMobPdnPcAcctRfDlAvgRate  OBJECT-TYPE
    SYNTAX      Counter32
    UNITS       "kbps"
    MAX-ACCESS  read-only
    STATUS      current
    DESCRIPTION
        "The value of tmnxMobPdnPcAcctRfDlAvgRate indicates the average downlink  
         traffic on this Pakcet Data Network (PDN) context."
    ::= { tmnxMobPdnPcAcctRfEntry 14 }

tmnxMobPdnPcAcctRfNumInterimSent  OBJECT-TYPE
    SYNTAX      Counter32
    MAX-ACCESS  read-only
    STATUS      current
    DESCRIPTION
        "The value of tmnxMobPdnPcAcctRfNumInterimSent indicates the number of 
         interim accounting messages sent for this Pakcet Data Network (PDN)
         context."
    ::= { tmnxMobPdnPcAcctRfEntry 15 }

tmnxMobPdnPcAcctRfNumRgs  OBJECT-TYPE
    SYNTAX      Counter32
    MAX-ACCESS  read-only
    STATUS      current
    DESCRIPTION
        "The value of tmnxMobPdnPcAcctRfNumRgs indicates the number of 
         Rating Groups for this Pakcet Data Network (PDN) context."
    ::= { tmnxMobPdnPcAcctRfEntry 16 }

tmnxMobPdnPcAcctRfNumOfRgSvcId  OBJECT-TYPE
    SYNTAX      Counter32
    MAX-ACCESS  read-only
    STATUS      current
    DESCRIPTION
        "The value of tmnxMobPdnPcAcctRfNumOfRgSvcId indicates the number of 
         unique Rating Group and Service Identifier pairs for this Pakcet Data
         Network (PDN) context."
    ::= { tmnxMobPdnPcAcctRfEntry 17 }

--
--  PDN Context Acct Rf Charging Rule Unit Stats Table
--

tmnxMobPdnPcRfChrgTable  OBJECT-TYPE
    SYNTAX      SEQUENCE OF TmnxMobPdnPcRfChrgEntry
    MAX-ACCESS  not-accessible
    STATUS      current
    DESCRIPTION
        "The tmnxMobPdnPcRfChrgTable has an entry for each
         Rating Group and Service ID pair of an User Equipment (UE) for
         this Pakcet Data Network (PDN) context."
    ::= { tmnxMobPdnStatObjs 27 }

tmnxMobPdnPcRfChrgEntry  OBJECT-TYPE
    SYNTAX      TmnxMobPdnPcRfChrgEntry
    MAX-ACCESS  not-accessible
    STATUS      current
    DESCRIPTION
        "Each row entry represents a Rf Charging Rule Unit statistics
         information for each Rating Group and Service ID pair of an User
         Equipment (UE) for this Pakcet Data Network (PDN) context."
    INDEX { tmnxMobGwId,
            tmnxMobPdnUeImsi,
            tmnxMobPdnPcApn,
            tmnxMobPdnPcPdnType,
            tmnxMobPdnBcBearerId,
            tmnxMobProfChgUnitRatingGroup,
            tmnxMobProfChgUnitServIdentifier            
          }
    ::= { tmnxMobPdnPcRfChrgTable 1 }

TmnxMobPdnPcRfChrgEntry ::= SEQUENCE {
        tmnxMobPdnPcRfChrgOnlnCharging          TruthValue,
        tmnxMobPdnPcRfChrgOfflnCharging         TruthValue,
        tmnxMobPdnPcRfChrgUlPkts                Counter64,
        tmnxMobPdnPcRfChrgUlPktsLow             Counter32,
        tmnxMobPdnPcRfChrgUlPktsHigh            Counter32,
        tmnxMobPdnPcRfChrgDlPkts                Counter64,
        tmnxMobPdnPcRfChrgDlPktsLow             Counter32,
        tmnxMobPdnPcRfChrgDlPktsHigh            Counter32,
        tmnxMobPdnPcRfChrgUlByts                Counter64,
        tmnxMobPdnPcRfChrgUlBytsLow             Counter32,
        tmnxMobPdnPcRfChrgUlBytsHigh            Counter32,
        tmnxMobPdnPcRfChrgDlByts                Counter64,
        tmnxMobPdnPcRfChrgDlBytsLow             Counter32,
        tmnxMobPdnPcRfChrgDlBytsHigh            Counter32
    }

tmnxMobPdnPcRfChrgOnlnCharging  OBJECT-TYPE
    SYNTAX      TruthValue
    MAX-ACCESS  read-only
    STATUS      current
    DESCRIPTION
        "The value of tmnxMobPdnPcRfChrgOnlnCharging indicates whether online
         charging is enabled."        
    ::= { tmnxMobPdnPcRfChrgEntry 1 }

tmnxMobPdnPcRfChrgOfflnCharging  OBJECT-TYPE
    SYNTAX      TruthValue
    MAX-ACCESS  read-only
    STATUS      current
    DESCRIPTION
        "The value of tmnxMobPdnPcRfChrgOfflnCharging indicates whether offline
         charging is enabled."        
    ::= { tmnxMobPdnPcRfChrgEntry 2 }

tmnxMobPdnPcRfChrgUlPkts  OBJECT-TYPE
    SYNTAX      Counter64
    MAX-ACCESS  read-only
    STATUS      current
    DESCRIPTION
        "The value of tmnxMobPdnPcRfChrgUlPkts indicates the total
         uplink packets for this Rating Group and Service ID pair."
    ::= { tmnxMobPdnPcRfChrgEntry 3 }

tmnxMobPdnPcRfChrgUlPktsLow  OBJECT-TYPE
    SYNTAX      Counter32
    MAX-ACCESS  read-only
    STATUS      current
    DESCRIPTION
        "The value of tmnxMobPdnPcRfChrgUlPktsLow indicates the lower 32
         bits of the value of tmnxMobPdnPcRfChrgUlPkts."
    ::= { tmnxMobPdnPcRfChrgEntry 4 }

tmnxMobPdnPcRfChrgUlPktsHigh  OBJECT-TYPE
    SYNTAX      Counter32
    MAX-ACCESS  read-only
    STATUS      current
    DESCRIPTION
        "The value of tmnxMobPdnPcRfChrgUlPktsHigh indicates the higer 32
         bits of the value of tmnxMobPdnPcRfChrgUlPkts."
    ::= { tmnxMobPdnPcRfChrgEntry 5 }

tmnxMobPdnPcRfChrgDlPkts  OBJECT-TYPE
    SYNTAX      Counter64
    MAX-ACCESS  read-only
    STATUS      current
    DESCRIPTION
        "The value of tmnxMobPdnPcRfChrgDlPkts indicates the total
         downlink packets for this Rating Group and Service ID pair."
    ::= { tmnxMobPdnPcRfChrgEntry 6 }

tmnxMobPdnPcRfChrgDlPktsLow  OBJECT-TYPE
    SYNTAX      Counter32
    MAX-ACCESS  read-only
    STATUS      current
    DESCRIPTION
        "The value of tmnxMobPdnPcRfChrgDlPktsLow indicates the lower 32
         bits of the value of tmnxMobPdnPcRfChrgDlPkts."
    ::= { tmnxMobPdnPcRfChrgEntry 7 }

tmnxMobPdnPcRfChrgDlPktsHigh  OBJECT-TYPE
    SYNTAX      Counter32
    MAX-ACCESS  read-only
    STATUS      current
    DESCRIPTION
        "The value of tmnxMobPdnPcRfChrgDlPktsLow indicates the higer 32
         bits of the value of tmnxMobPdnPcRfChrgDlPkts."
    ::= { tmnxMobPdnPcRfChrgEntry 8 }

tmnxMobPdnPcRfChrgUlByts  OBJECT-TYPE
    SYNTAX      Counter64
    MAX-ACCESS  read-only
    STATUS      current
    DESCRIPTION
        "The value of tmnxMobPdnPcRfChrgUlByts indicates the total
         uplink bytes for this Rating Group and Service ID pair."
    ::= { tmnxMobPdnPcRfChrgEntry 9 }

tmnxMobPdnPcRfChrgUlBytsLow  OBJECT-TYPE
    SYNTAX      Counter32
    MAX-ACCESS  read-only
    STATUS      current
    DESCRIPTION
        "The value of tmnxMobPdnPcRfChrgUlBytsLow indicates the lower 32
         bits of the value of tmnxMobPdnPcRfChrgUlByts."
    ::= { tmnxMobPdnPcRfChrgEntry 10 }

tmnxMobPdnPcRfChrgUlBytsHigh  OBJECT-TYPE
    SYNTAX      Counter32
    MAX-ACCESS  read-only
    STATUS      current
    DESCRIPTION
        "The value of tmnxMobPdnPcRfChrgUlBytsHigh indicates the higer 32
         bits of the value of tmnxMobPdnPcRfChrgUlByts."
    ::= { tmnxMobPdnPcRfChrgEntry 11 }

tmnxMobPdnPcRfChrgDlByts  OBJECT-TYPE
    SYNTAX      Counter64
    MAX-ACCESS  read-only
    STATUS      current
    DESCRIPTION
        "The value of tmnxMobPdnPcRfChrgDlByts indicates the total
         downlink bytes for this Rating Group and Service ID pair."
    ::= { tmnxMobPdnPcRfChrgEntry 12 }

tmnxMobPdnPcRfChrgDlBytsLow  OBJECT-TYPE
    SYNTAX      Counter32
    MAX-ACCESS  read-only
    STATUS      current
    DESCRIPTION
        "The value of tmnxMobPdnPcRfChrgDlBytsLow indicates the lower 32
         bits of the value of tmnxMobPdnPcRfChrgDlByts."
    ::= { tmnxMobPdnPcRfChrgEntry 13 }

tmnxMobPdnPcRfChrgDlBytsHigh  OBJECT-TYPE
    SYNTAX      Counter32
    MAX-ACCESS  read-only
    STATUS      current
    DESCRIPTION
        "The value of tmnxMobPdnPcRfChrgDlBytsLow indicates the higer 32
         bits of the value of tmnxMobPdnPcRfChrgDlByts."
    ::= { tmnxMobPdnPcRfChrgEntry 14 }

--
-- S6b peer table
--

tmnxMobPdnS6bPeerTableLastChngd     OBJECT-TYPE
    SYNTAX      TimeStamp
    MAX-ACCESS  read-only
    STATUS      current
    DESCRIPTION
        "The value of tmnxMobPdnS6bPeerTableLastChngd indicates the sysUpTime
         at the time of the last modification to tmnxMobPdnS6bPeerTable by
         adding, deleting an entry or change to a writable object in the table.

         If no changes were made to the table since the last re-initialization
         of the local network management subsystem, then this object contains
         a zero value."
    ::= { tmnxMobPdnGlobalObjs 30 }

tmnxMobPdnS6bPeerTable  OBJECT-TYPE
    SYNTAX      SEQUENCE OF TmnxMobPdnS6bPeerEntry
    MAX-ACCESS  not-accessible
    STATUS      current
    DESCRIPTION
        "The tmnxMobPdnS6bPeerTable has an entry for each peer on the S6b
         reference point served by a Packet Data Network Gateway (PGW)."
    ::= { tmnxMobPdnStatObjs 28 }

tmnxMobPdnS6bPeerEntry  OBJECT-TYPE
    SYNTAX      TmnxMobPdnS6bPeerEntry
    MAX-ACCESS  not-accessible
    STATUS      current
    DESCRIPTION
        "Each row entry represents a peer on the S6b reference point."
    INDEX { tmnxMobGwId,
            vRtrID,
            tmnxMobProfDiaPeerName,
            tmnxMobProfDiaPeerListIndex,
            tmnxMobPdnS6bPeerAddressType,
            tmnxMobPdnS6bPeerAddress,
            tmnxMobPdnS6bPeerPort
          }
    ::= { tmnxMobPdnS6bPeerTable 1 }

TmnxMobPdnS6bPeerEntry ::= SEQUENCE {
        tmnxMobPdnS6bPeerAddressType       InetAddressType,
        tmnxMobPdnS6bPeerAddress           InetAddress,
        tmnxMobPdnS6bPeerPort              InetPortNumber,
        tmnxMobPdnS6bPeerLastChanged       TimeStamp,
        tmnxMobPdnS6bPeerCreateTime        TimeStamp,
        tmnxMobPdnS6bPeerPathMgmtState     TmnxMobDiaPathMgmtState,
        tmnxMobPdnS6bPeerDetailState       TmnxMobDiaDetailPathMgmtState
    }

tmnxMobPdnS6bPeerAddressType  OBJECT-TYPE
    SYNTAX      InetAddressType
    MAX-ACCESS  not-accessible
    STATUS      current
    DESCRIPTION
        "The value of tmnxMobPdnS6bPeerAddressType indicates the type of
         address represented by tmnxMobPdnS6bPeerAddress."
    ::= { tmnxMobPdnS6bPeerEntry 1 }

tmnxMobPdnS6bPeerAddress  OBJECT-TYPE
    SYNTAX      InetAddress (SIZE (0|4|16))
    MAX-ACCESS  not-accessible
    STATUS      current
    DESCRIPTION
        "The value of tmnxMobPdnS6bPeerAddress indicates the IP address of the
         peer on S6b reference point."
    ::= { tmnxMobPdnS6bPeerEntry 2 }

tmnxMobPdnS6bPeerPort  OBJECT-TYPE
    SYNTAX      InetPortNumber
    MAX-ACCESS  not-accessible
    STATUS      current
    DESCRIPTION
        "The value of tmnxMobPdnS6bPeerPort indicates the port number of this
         peer."
    ::= { tmnxMobPdnS6bPeerEntry 3 }

tmnxMobPdnS6bPeerLastChanged  OBJECT-TYPE
    SYNTAX      TimeStamp
    MAX-ACCESS  read-only
    STATUS      current
    DESCRIPTION
        "The value of tmnxMobPdnS6bPeerLastChanged indicates the timestamp of
         the last change to this row in tmnxMobPdnS6bPeerTable."
    ::= { tmnxMobPdnS6bPeerEntry 4 }

tmnxMobPdnS6bPeerCreateTime  OBJECT-TYPE
    SYNTAX      TimeStamp
    MAX-ACCESS  read-only
    STATUS      current
    DESCRIPTION
        "The value of tmnxMobPdnS6bPeerCreateTime indicates the sysUpTime when
         this entry was created."
    ::= { tmnxMobPdnS6bPeerEntry 5 }

tmnxMobPdnS6bPeerPathMgmtState  OBJECT-TYPE
    SYNTAX      TmnxMobDiaPathMgmtState
    MAX-ACCESS  read-only
    STATUS      current
    DESCRIPTION
        "The value of tmnxMobPdnS6bPeerPathMgmtState indicates the state of
         the path."
    ::= { tmnxMobPdnS6bPeerEntry 6 }

tmnxMobPdnS6bPeerDetailState  OBJECT-TYPE
    SYNTAX      TmnxMobDiaDetailPathMgmtState
    MAX-ACCESS  read-only
    STATUS      current
    DESCRIPTION
        "The value of tmnxMobPdnS6bPeerDetailState indicates the detail state
         of the path."
    ::= { tmnxMobPdnS6bPeerEntry 7 }

--
--  S6b Stats Table
--

tmnxMobPdnS6bStatTable  OBJECT-TYPE
    SYNTAX      SEQUENCE OF TmnxMobPdnS6bStatEntry
    MAX-ACCESS  not-accessible
    STATUS      current
    DESCRIPTION
        "The tmnxMobPdnS6bStatTable has an entry for each peer on the S6b
         reference point served by a Packet Data Network Gateway (PGW)."
    ::= { tmnxMobPdnStatObjs 29 }

tmnxMobPdnS6bStatEntry  OBJECT-TYPE
    SYNTAX      TmnxMobPdnS6bStatEntry
    MAX-ACCESS  not-accessible
    STATUS      current
    DESCRIPTION
        "Each row entry represents a peer on the S6b reference point and
         contain statistics for this peer on a card."
    INDEX { tmnxMobGwId,
            vRtrID,
            tmnxMobProfDiaPeerName,
            tmnxMobProfDiaPeerListIndex,
            tmnxMobPdnS6bPeerAddressType,
            tmnxMobPdnS6bPeerAddress,
            tmnxMobPdnS6bPeerPort,
            tmnxChassisIndex,
            tmnxCardSlotNum
          }
    ::= { tmnxMobPdnS6bStatTable 1 }

TmnxMobPdnS6bStatEntry ::= SEQUENCE {
        tmnxMobPdnS6bStatAARInitTx               Counter32,
        tmnxMobPdnS6bStatAARExtnTx               Counter32,
        tmnxMobPdnS6bStatAARDetachTx             Counter32,
        tmnxMobPdnS6bStatAARReauthTx             Counter32,
        tmnxMobPdnS6bStatAAAInitAtchRx           Counter32,
        tmnxMobPdnS6bStatAAAExtnRx               Counter32,
        tmnxMobPdnS6bStatAAADetachRx             Counter32,
        tmnxMobPdnS6bStatAAAReauthRx             Counter32,
        tmnxMobPdnS6bStatAAASuccessRx            Counter32,
        tmnxMobPdnS6bStatAAARejectRx             Counter32,
        tmnxMobPdnS6bStatRARequestRx             Counter32,
        tmnxMobPdnS6bStatRAAnswerTx              Counter32,
        tmnxMobPdnS6bStatSTRequestTx             Counter32,
        tmnxMobPdnS6bStatSTAnswerRx              Counter32,
        tmnxMobPdnS6bStatASRequestRx             Counter32,
        tmnxMobPdnS6bStatASAnswerTx              Counter32,
        tmnxMobPdnS6bStatAAAMissAVPPktRx         Counter32,
        tmnxMobPdnS6bStatRARMissAVPPktRx         Counter32,
        tmnxMobPdnS6bStatSTAMissAVPPktRx         Counter32,
        tmnxMobPdnS6bStatASRMissAVPPktRx         Counter32,
        tmnxMobPdnS6bStatAAAUnknSesPktRx         Counter32,
        tmnxMobPdnS6bStatAARRetries              Counter32,
        tmnxMobPdnS6bStatSTRRetries              Counter32,
        tmnxMobPdnS6bStatMessagesTx              Counter32,
        tmnxMobPdnS6bStatMessagesRx              Counter32,
        tmnxMobPdnS6bStatCERMsgsTx               Counter32,
        tmnxMobPdnS6bStatCEAMsgsRx               Counter32,
        tmnxMobPdnS6bStatDPRMsgsTx               Counter32,
        tmnxMobPdnS6bStatDPRMsgsRx               Counter32,
        tmnxMobPdnS6bStatDPAMsgsTx               Counter32,
        tmnxMobPdnS6bStatDPAMsgsRx               Counter32,
        tmnxMobPdnS6bStatDWRMsgsTx               Counter32,
        tmnxMobPdnS6bStatDWRMsgsRx               Counter32,
        tmnxMobPdnS6bStatDWAMsgsTx               Counter32,
        tmnxMobPdnS6bStatDWAMsgsRx               Counter32,
        tmnxMobPdnS6bStatConnAttempts            Counter32,
        tmnxMobPdnS6bStatConnFailures            Counter32,
        tmnxMobPdnS6bStatRxMsgUnexpctVer         Counter32,
        tmnxMobPdnS6bStatRxMsgTooBig             Counter32,
        tmnxMobPdnS6bStatRxMsgTooSmall           Counter32,
        tmnxMobPdnS6bStatRxInvalidCea            Counter32,
        tmnxMobPdnS6bStatTxRetrnsmitMsgs         Counter32,
        tmnxMobPdnS6bStatRxTransportDisc         Counter32,
        tmnxMobPdnS6bAARFinalTOTx                Counter32,
        tmnxMobPdnS6bSTRUnknownSessTx            Counter32,
        tmnxMobPdnS6bSTRFinalTOTx                Counter32,
        tmnxMobPdnS6bASAUnknownSessTx            Counter32,
        tmnxMobPdnS6bRAAUnknownSessTx            Counter32,
        tmnxMobPdnS6bAAAMalformedPktsRx          Counter32,
        tmnxMobPdnS6bAAABadAVPValue              Counter32,
        tmnxMobPdnS6bSTAMalformedPktsRx          Counter32,
        tmnxMobPdnS6bSTABadAVPValueRx            Counter32,
        tmnxMobPdnS6bRARBadAVPValueRx            Counter32,
        tmnxMobPdnS6bRARDuplicateRx              Counter32,
        tmnxMobPdnS6bASRBadAVPValueRx            Counter32,
        tmnxMobPdnS6bASRDuplicateRx              Counter32
    }

tmnxMobPdnS6bStatAARInitTx               OBJECT-TYPE
    SYNTAX      Counter32
    MAX-ACCESS  read-only
    STATUS      current
    DESCRIPTION
        "The value of tmnxMobPdnS6bStatAARInitTx indicates the number of AA 
         Request messages transmitted to this peer on behalf of an initial
         attach."
    ::= { tmnxMobPdnS6bStatEntry 1 }

tmnxMobPdnS6bStatAARExtnTx               OBJECT-TYPE
    SYNTAX      Counter32
    MAX-ACCESS  read-only
    STATUS      current
    DESCRIPTION
        "The value of tmnxMobPdnS6bStatAARExtnTx indicates the number of AA
         Request messages transmitted to this peer on behalf of a lifetime
         extension."
    ::= { tmnxMobPdnS6bStatEntry 2 }

tmnxMobPdnS6bStatAARDetachTx             OBJECT-TYPE
    SYNTAX      Counter32
    MAX-ACCESS  read-only
    STATUS      current
    DESCRIPTION
        "The value of tmnxMobPdnS6bStatAARDetachTx indicates the number of AA
         Request messages transmitted to this peer when detaching a session."
    ::= { tmnxMobPdnS6bStatEntry 3 }

tmnxMobPdnS6bStatAARReauthTx             OBJECT-TYPE
    SYNTAX      Counter32
    MAX-ACCESS  read-only
    STATUS      current
    DESCRIPTION
        "The value of tmnxMobPdnS6bStatAARReauthTx indicates the number of AA 
         Request messages transmitted to this peer during a reauthorization."
    ::= { tmnxMobPdnS6bStatEntry 4 }

tmnxMobPdnS6bStatAAAInitAtchRx           OBJECT-TYPE
    SYNTAX      Counter32
    MAX-ACCESS  read-only
    STATUS      current
    DESCRIPTION
        "The value of tmnxMobPdnS6bStatAAAInitAtchRx indicates the number of AA
         Answer messages received from this peer for an initial attach."
    ::= { tmnxMobPdnS6bStatEntry 5 }

tmnxMobPdnS6bStatAAAExtnRx               OBJECT-TYPE
    SYNTAX      Counter32
    MAX-ACCESS  read-only
    STATUS      current
    DESCRIPTION
        "The value of tmnxMobPdnS6bStatAAAExtnRx indicates the number of AA 
         Answer messages received from this peer for a lifetime extension."
    ::= { tmnxMobPdnS6bStatEntry 6 }

tmnxMobPdnS6bStatAAADetachRx             OBJECT-TYPE
    SYNTAX      Counter32
    MAX-ACCESS  read-only
    STATUS      current
    DESCRIPTION
        "The value of tmnxMobPdnS6bStatAAADetachRx indicates the number of AA
         Answer messages received from this peer for a detach."
    ::= { tmnxMobPdnS6bStatEntry 7 }

tmnxMobPdnS6bStatAAAReauthRx             OBJECT-TYPE
    SYNTAX      Counter32
    MAX-ACCESS  read-only
    STATUS      current
    DESCRIPTION
        "The value of tmnxMobPdnS6bStatAAAReauthRx indicates the number of AA 
         Answer messages received from this peer for a reauthorization."
    ::= { tmnxMobPdnS6bStatEntry 8 }

tmnxMobPdnS6bStatAAASuccessRx            OBJECT-TYPE
    SYNTAX      Counter32
    MAX-ACCESS  read-only
    STATUS      current
    DESCRIPTION
        "The value of tmnxMobPdnS6bStatAAASuccessRx indicates the number of AA
         Answer messages received from this peer with Result-Code set to 
         diameter success."
    ::= { tmnxMobPdnS6bStatEntry 9 }

tmnxMobPdnS6bStatAAARejectRx             OBJECT-TYPE
    SYNTAX      Counter32
    MAX-ACCESS  read-only
    STATUS      current
    DESCRIPTION
        "The value of tmnxMobPdnS6bStatAAARejectRx indicates the number of AA
         Answer messages received from this peer with Result-Code not set to
         diameter success."
    ::= { tmnxMobPdnS6bStatEntry 10 }

tmnxMobPdnS6bStatRARequestRx             OBJECT-TYPE
    SYNTAX      Counter32
    MAX-ACCESS  read-only
    STATUS      current
    DESCRIPTION
        "The value of tmnxMobPdnS6bStatRARequestRx indicates the number of 
         reauthorization request messages received by the Packet Data 
         Network Gateway (PGW)."
    ::= { tmnxMobPdnS6bStatEntry 11 }

tmnxMobPdnS6bStatRAAnswerTx              OBJECT-TYPE
    SYNTAX      Counter32
    MAX-ACCESS  read-only
    STATUS      current
    DESCRIPTION
        "The value of tmnxMobPdnS6bStatRAAnswerTx indicates the number of 
         reauthorization answer  messages transmitted by the Packet Data
         Network Gateway (PGW)."
    ::= { tmnxMobPdnS6bStatEntry 12 }

tmnxMobPdnS6bStatSTRequestTx             OBJECT-TYPE
    SYNTAX      Counter32
    MAX-ACCESS  read-only
    STATUS      current
    DESCRIPTION
        "The value of tmnxMobPdnS6bStatSTRequestTx indicates the number of 
         session termination request messages transmitted by the Packet Data 
         Network Gateway (PGW)."
    ::= { tmnxMobPdnS6bStatEntry 13 }

tmnxMobPdnS6bStatSTAnswerRx              OBJECT-TYPE
    SYNTAX      Counter32
    MAX-ACCESS  read-only
    STATUS      current
    DESCRIPTION
        "The value of tmnxMobPdnS6bStatSTAnswerRx indicates the number of 
         session termination answer messages received by the Packet Data Network
         Gateway (PGW)."
    ::= { tmnxMobPdnS6bStatEntry 14 }

tmnxMobPdnS6bStatASRequestRx             OBJECT-TYPE
    SYNTAX      Counter32
    MAX-ACCESS  read-only
    STATUS      current
    DESCRIPTION
        "The value of tmnxMobPdnS6bStatASRequestRx indicates the number of abort
         session request messages received by the Packet Data Network Gateway 
         (PGW)."
    ::= { tmnxMobPdnS6bStatEntry 15 }

tmnxMobPdnS6bStatASAnswerTx              OBJECT-TYPE
    SYNTAX      Counter32
    MAX-ACCESS  read-only
    STATUS      current
    DESCRIPTION
        "The value of tmnxMobPdnS6bStatASAnswerTx indicates the number of Abort
         session answer messages transmitted by the Packet Data Network Gateway
         (PGW)."
    ::= { tmnxMobPdnS6bStatEntry 16 }

tmnxMobPdnS6bStatAAAMissAVPPktRx         OBJECT-TYPE
    SYNTAX      Counter32
    MAX-ACCESS  read-only
    STATUS      current
    DESCRIPTION
        "The value of tmnxMobPdnS6bStatAAAMissAVPPktRx indicates the number of 
         AA Answer messages missing a mandatory attribute received by Packet
         Data Network Gateway (PGW)."
    ::= { tmnxMobPdnS6bStatEntry 17 }

tmnxMobPdnS6bStatRARMissAVPPktRx         OBJECT-TYPE
    SYNTAX      Counter32
    MAX-ACCESS  read-only
    STATUS      current
    DESCRIPTION
        "The value of tmnxMobPdnS6bStatRARMissAVPPktRx indicates the number of
         reauthorization request messages missing a mandatory attribute received
         by the Packet Data Network Gateway (PGW)."
    ::= { tmnxMobPdnS6bStatEntry 18 }

tmnxMobPdnS6bStatSTAMissAVPPktRx         OBJECT-TYPE
    SYNTAX      Counter32
    MAX-ACCESS  read-only
    STATUS      current
    DESCRIPTION
        "The value of tmnxMobPdnS6bStatSTAMissAVPPktRx indicates the number of
         session termination answer messages missing a mandatory attribute
         received by the Packet Data Network Gateway (PGW)."
    ::= { tmnxMobPdnS6bStatEntry 19 }

tmnxMobPdnS6bStatASRMissAVPPktRx         OBJECT-TYPE
    SYNTAX      Counter32
    MAX-ACCESS  read-only
    STATUS      current
    DESCRIPTION
        "The value of tmnxMobPdnS6bStatASRMissAVPPktRx indicates the number of
         abort session request messages missing a mandatory parameter received
         by the Packet Data Network Gateway (PGW)."
    ::= { tmnxMobPdnS6bStatEntry 20 }

tmnxMobPdnS6bStatAAAUnknSesPktRx         OBJECT-TYPE
    SYNTAX      Counter32
    MAX-ACCESS  read-only
    STATUS      current
    DESCRIPTION
        "The value of tmnxMobPdnS6bStatAAAUnknSesPktRx indicates the number of
         AA answer messages received by the Packet Data Network Gateway (PGW) 
         for which a session does not exist."
    ::= { tmnxMobPdnS6bStatEntry 21 }

tmnxMobPdnS6bStatAARRetries              OBJECT-TYPE
    SYNTAX      Counter32
    MAX-ACCESS  read-only
    STATUS      current
    DESCRIPTION
        "The value of tmnxMobPdnS6bStatAARRetries indicates the number of times
         the Packet Data Network Gateway (PGW) retried to send an AA Request."
    ::= { tmnxMobPdnS6bStatEntry 22 }

tmnxMobPdnS6bStatSTRRetries              OBJECT-TYPE
    SYNTAX      Counter32
    MAX-ACCESS  read-only
    STATUS      current
    DESCRIPTION
        "The value of tmnxMobPdnS6bStatSTRRetries indicates the number of
         times the Packet Data Network Gateway (PGW) retried to send an
         session termination request."
    ::= { tmnxMobPdnS6bStatEntry 23 }

tmnxMobPdnS6bStatMessagesTx              OBJECT-TYPE
    SYNTAX      Counter32
    MAX-ACCESS  read-only
    STATUS      current
    DESCRIPTION
        "The value of tmnxMobPdnS6bStatMessagesTx indicates the total number of 
         s6b application messages transmitted to this peer."
    ::= { tmnxMobPdnS6bStatEntry 24 }

tmnxMobPdnS6bStatMessagesRx              OBJECT-TYPE
    SYNTAX      Counter32
    MAX-ACCESS  read-only
    STATUS      current
    DESCRIPTION
        "The value of tmnxMobPdnS6bStatMessagesRx indicates the total number of 
         s6b application messages received from this peer."
    ::= { tmnxMobPdnS6bStatEntry 25 }

tmnxMobPdnS6bStatCERMsgsTx               OBJECT-TYPE
    SYNTAX      Counter32
    MAX-ACCESS  read-only
    STATUS      current
    DESCRIPTION
        "The value of tmnxMobPdnS6bStatCERMsgsTx indicates the number of 
         Capability Exchange Request (CER) messages transmitted to this peer."
    ::= { tmnxMobPdnS6bStatEntry 26 }

tmnxMobPdnS6bStatCEAMsgsRx               OBJECT-TYPE
    SYNTAX      Counter32
    MAX-ACCESS  read-only
    STATUS      current
    DESCRIPTION
        "The value of tmnxMobPdnS6bStatCEAMsgsRx indicates the number of 
         Capability Exchange Answer (CEA) messages received from this peer."
    ::= { tmnxMobPdnS6bStatEntry 27 }

tmnxMobPdnS6bStatDPRMsgsTx               OBJECT-TYPE
    SYNTAX      Counter32
    MAX-ACCESS  read-only
    STATUS      current
    DESCRIPTION
        "The value of tmnxMobPdnS6bStatDPRMsgsTx indicates the number of 
         Disconnect Peer Request (DPR) messages transmitted to this peer."
    ::= { tmnxMobPdnS6bStatEntry 28 }

tmnxMobPdnS6bStatDPRMsgsRx               OBJECT-TYPE
    SYNTAX      Counter32
    MAX-ACCESS  read-only
    STATUS      current
    DESCRIPTION
        "The value of tmnxMobPdnS6bStatDPRMsgsRx indicates the number of 
         Disconnect Peer Request (DPR) messages received from this peer."
    ::= { tmnxMobPdnS6bStatEntry 29 }

tmnxMobPdnS6bStatDPAMsgsTx               OBJECT-TYPE
    SYNTAX      Counter32
    MAX-ACCESS  read-only
    STATUS      current
    DESCRIPTION
        "The value of tmnxMobPdnS6bStatDPAMsgsTx indicates the number of 
         Disconnect Peer Answer (DPA) messages transmitted to this peer."
    ::= { tmnxMobPdnS6bStatEntry 30 }

tmnxMobPdnS6bStatDPAMsgsRx               OBJECT-TYPE
    SYNTAX      Counter32
    MAX-ACCESS  read-only
    STATUS      current
    DESCRIPTION
        "The value of tmnxMobPdnS6bStatDPAMsgsRx indicates the number of 
         Disconnect Peer Answer (DPA) messages received from this peer."
    ::= { tmnxMobPdnS6bStatEntry 31 }

tmnxMobPdnS6bStatDWRMsgsTx               OBJECT-TYPE
    SYNTAX      Counter32
    MAX-ACCESS  read-only
    STATUS      current
    DESCRIPTION
        "The value of tmnxMobPdnS6bStatDWRMsgsTx indicates the number of 
         Device Watchdog Request (DWR) messages transmitted to this peer."
    ::= { tmnxMobPdnS6bStatEntry 32 }

tmnxMobPdnS6bStatDWRMsgsRx               OBJECT-TYPE
    SYNTAX      Counter32
    MAX-ACCESS  read-only
    STATUS      current
    DESCRIPTION
        "The value of tmnxMobPdnS6bStatDWRMsgsRx indicates the number of 
         Device Watchdog Request (DWR) messages received from this peer."
    ::= { tmnxMobPdnS6bStatEntry 33 }

tmnxMobPdnS6bStatDWAMsgsTx               OBJECT-TYPE
    SYNTAX      Counter32
    MAX-ACCESS  read-only
    STATUS      current
    DESCRIPTION
        "The value of tmnxMobPdnS6bStatDWAMsgsTx indicates the number of 
         Device Watch Answer (DWA) messages transmitted to this peer."
    ::= { tmnxMobPdnS6bStatEntry 34 }

tmnxMobPdnS6bStatDWAMsgsRx               OBJECT-TYPE
    SYNTAX      Counter32
    MAX-ACCESS  read-only
    STATUS      current
    DESCRIPTION
        "The value of tmnxMobPdnS6bStatDWAMsgsRx indicates the number of 
         Device Watch Answer (DWA) messages received from this peer."
    ::= { tmnxMobPdnS6bStatEntry 35 }

tmnxMobPdnS6bStatConnAttempts            OBJECT-TYPE
    SYNTAX      Counter32
    MAX-ACCESS  read-only
    STATUS      current
    DESCRIPTION
        "The value of tmnxMobPdnS6bStatConnAttempts indicates the number of 
         connections attempted to this peer."
    ::= { tmnxMobPdnS6bStatEntry 36 }

tmnxMobPdnS6bStatConnFailures            OBJECT-TYPE
    SYNTAX      Counter32
    MAX-ACCESS  read-only
    STATUS      current
    DESCRIPTION
        "The value of tmnxMobPdnS6bStatConnFailures indicates the number of 
         failed connections with this peer."
    ::= { tmnxMobPdnS6bStatEntry 37 }

tmnxMobPdnS6bStatRxMsgUnexpctVer        OBJECT-TYPE
    SYNTAX      Counter32
    MAX-ACCESS  read-only
    STATUS      current
    DESCRIPTION
        "The value of tmnxMobPdnS6bStatRxMsgUnexpctVer indicates the number of 
         unexpected version messages received from this peer."
    ::= { tmnxMobPdnS6bStatEntry 38 }

tmnxMobPdnS6bStatRxMsgTooBig             OBJECT-TYPE
    SYNTAX      Counter32
    MAX-ACCESS  read-only
    STATUS      current
    DESCRIPTION
        "The value of tmnxMobPdnS6bStatRxMsgTooBig indicates the number of 
         oversize messages received from this peer."
    ::= { tmnxMobPdnS6bStatEntry 39 }

tmnxMobPdnS6bStatRxMsgTooSmall           OBJECT-TYPE
    SYNTAX      Counter32
    MAX-ACCESS  read-only
    STATUS      current
    DESCRIPTION
        "The value of tmnxMobPdnS6bStatRxMsgTooSmall indicates the number of 
         small messages received from this peer."
    ::= { tmnxMobPdnS6bStatEntry 40 }

tmnxMobPdnS6bStatRxInvalidCea            OBJECT-TYPE
    SYNTAX      Counter32
    MAX-ACCESS  read-only
    STATUS      current
    DESCRIPTION
        "The value of tmnxMobPdnS6bStatRxInvalidCea indicates the number of 
         invalid Capabilities Exchange Answer (CEA) messages received from 
         this peer."
    ::= { tmnxMobPdnS6bStatEntry 41 }

tmnxMobPdnS6bStatTxRetrnsmitMsgs        OBJECT-TYPE
    SYNTAX      Counter32
    MAX-ACCESS  read-only
    STATUS      current
    DESCRIPTION
        "The value of tmnxMobPdnS6bStatTxRetrnsmitMsgs indicates the number of 
         retransmit messages transmitted to this peer."
    ::= { tmnxMobPdnS6bStatEntry 42 }

tmnxMobPdnS6bStatRxTransportDisc         OBJECT-TYPE
    SYNTAX      Counter32
    MAX-ACCESS  read-only
    STATUS      current
    DESCRIPTION
        "The value of tmnxMobPdnS6bStatRxTransportDisc indicates the number of 
         remote transport disconnect messages received from this peer."
    ::= { tmnxMobPdnS6bStatEntry 43 }

tmnxMobPdnS6bAARFinalTOTx OBJECT-TYPE
    SYNTAX Counter32
    MAX-ACCESS  read-only
    STATUS      current
    DESCRIPTION
        "The value of tmnxMobPdnS6bAARFinalTOTx indicates the number of 
         AA Request (AAR) retries aborted due to exhaustion
         of maximum allowable retries due to the lack of response from the 
         Authentication, Authorization and Accounting (AAA) server."
    ::= { tmnxMobPdnS6bStatEntry 44 }
    
tmnxMobPdnS6bSTRUnknownSessTx OBJECT-TYPE
    SYNTAX Counter32
    MAX-ACCESS  read-only
    STATUS      current
    DESCRIPTION
        "The value of tmnxMobPdnS6bSTRUnknownSessTx indicates the number of 
         Session Termination Requests (STR) the Packet Data Network Gateway 
         (PGW) sends upon receiving AA Answer (AAA) message for an unknown
         session."
    ::= { tmnxMobPdnS6bStatEntry 45 }
    
tmnxMobPdnS6bSTRFinalTOTx OBJECT-TYPE
    SYNTAX Counter32
    MAX-ACCESS  read-only
    STATUS      current
    DESCRIPTION
        "The value of tmnxMobPdnS6bSTRFinalTOTx indicates the number of 
         Session Termination Request (STR) retries aborted due to exhaustion
         of maximum allowable retries due to the lack of response from the 
         Authentication, Authorization and Accounting(AAA) server."
    ::= { tmnxMobPdnS6bStatEntry 46 }
    
tmnxMobPdnS6bASAUnknownSessTx OBJECT-TYPE
    SYNTAX Counter32
    MAX-ACCESS  read-only
    STATUS      current
    DESCRIPTION
        "The value of tmnxMobPdnS6bASAUnknownSessTx indicates the number of 
         Abort Session Answer (ASA) messages sent when the session identified
         in the Abort Session Request (ASR) message could not be found."
    ::= { tmnxMobPdnS6bStatEntry 47 }
                
tmnxMobPdnS6bRAAUnknownSessTx   OBJECT-TYPE
    SYNTAX Counter32
    MAX-ACCESS  read-only
    STATUS      current
    DESCRIPTION
        "The value of tmnxMobPdnS6bRAAUnknownSessTx indicates the number of 
         Reauthorization Answer (RAA) messages sent when the session identified
         in the Reauthorization Request (RAR) could not be found."
    ::= { tmnxMobPdnS6bStatEntry 48 }
    
tmnxMobPdnS6bAAAMalformedPktsRx OBJECT-TYPE
    SYNTAX Counter32
    MAX-ACCESS  read-only
    STATUS      current
    DESCRIPTION
        "The value of tmnxMobPdnS6bAAAMalformedPktsRx indicates the number of 
         malformed AA Answer (AAA) messages received at the Packet Data Network 
         Gateway (PGW)."
    ::= { tmnxMobPdnS6bStatEntry 49 }
                
tmnxMobPdnS6bAAABadAVPValue OBJECT-TYPE
    SYNTAX Counter32
    MAX-ACCESS  read-only
    STATUS      current
    DESCRIPTION
        "The value of tmnxMobPdnS6bAAABadAVPValue indicates the number of 
         AA Answer (AAA) messages received with a bad Attribute Value Pair
         (AVP) parameter."
    ::= { tmnxMobPdnS6bStatEntry 50 }
                  
tmnxMobPdnS6bSTAMalformedPktsRx OBJECT-TYPE
    SYNTAX Counter32
    MAX-ACCESS  read-only
    STATUS      current
    DESCRIPTION
        "The value of tmnxMobPdnS6bSTAMalformedPktsRx indicates the number of 
         malformed Session Termination Answer (STA) messages received at the 
         Packet Data Network Gateway (PGW)."
    ::= { tmnxMobPdnS6bStatEntry 51 }
                
tmnxMobPdnS6bSTABadAVPValueRx OBJECT-TYPE
    SYNTAX Counter32
    MAX-ACCESS  read-only
    STATUS      current
    DESCRIPTION
        "The value of tmnxMobPdnS6bSTABadAVPValueRx indicates the number of 
         Session Termination Answer (STA) messages received with a bad 
         Attribute Value Pair (AVP) parameter."
    ::= { tmnxMobPdnS6bStatEntry 52 }
                
tmnxMobPdnS6bRARBadAVPValueRx OBJECT-TYPE
    SYNTAX Counter32
    MAX-ACCESS  read-only
    STATUS      current
    DESCRIPTION
        "The value of tmnxMobPdnS6bRARBadAVPValueRx indicates the number of 
         Reauthorization Request (RAR) messages received with a bad 
         Attribute Value Pair (AVP) parameter."
    ::= { tmnxMobPdnS6bStatEntry 53 }
                
tmnxMobPdnS6bRARDuplicateRx OBJECT-TYPE
    SYNTAX Counter32
    MAX-ACCESS  read-only
    STATUS      current
    DESCRIPTION
        "The value of tmnxMobPdnS6bRARDuplicateRx indicates the number of 
         Reauthorization Request (RAR) messages received for a session that is
         currently processing a previously received RAR message."
    ::= { tmnxMobPdnS6bStatEntry 54 }
                  
tmnxMobPdnS6bASRBadAVPValueRx OBJECT-TYPE
    SYNTAX Counter32
    MAX-ACCESS  read-only
    STATUS      current
    DESCRIPTION
        "The value of tmnxMobPdnS6bASRBadAVPValueRx indicates the number of 
         Abort Session Request (ASR) messages received with a bad Attribute
         Value Pair (AVP) parameter."
    ::= { tmnxMobPdnS6bStatEntry 55 }
                
tmnxMobPdnS6bASRDuplicateRx OBJECT-TYPE
    SYNTAX Counter32
    MAX-ACCESS  read-only
    STATUS      current
    DESCRIPTION
        "The value of tmnxMobPdnS6bASRDuplicateRx indicates the number of 
         Abort Session Request (ASR) messages received for a session that is
         currently processing a previously received ASR message."
    ::= { tmnxMobPdnS6bStatEntry 56 }
    
--
--  S6b table
--

tmnxMobPdnS6bTableLastChanged  OBJECT-TYPE
    SYNTAX      TimeStamp
    MAX-ACCESS  read-only
    STATUS      current
    DESCRIPTION
        "The value of tmnxMobPdnS6bTableLastChanged indicates the sysUpTime at
         the time of the last modification to tmnxMobPdnS6bTable by adding,
         deleting an entry or change to a writable object in the table.

         If no changes were made to the table since the last re-initialization
         of the local network management subsystem, then this object contains
         a zero value."
    ::= { tmnxMobPdnGlobalObjs 32 }

tmnxMobPdnS6bTable  OBJECT-TYPE
    SYNTAX      SEQUENCE OF TmnxMobPdnS6bEntry
    MAX-ACCESS  not-accessible
    STATUS      current
    DESCRIPTION
        "The tmnxMobPdnS6bTable provides an extension to the tmnxMobPdnTable
         for S6b reference point configuration."
    ::= { tmnxMobPdnConfObjs 26 }

tmnxMobPdnS6bEntry  OBJECT-TYPE
    SYNTAX      TmnxMobPdnS6bEntry
    MAX-ACCESS  not-accessible
    STATUS      current
    DESCRIPTION
        "Each row entry represents additional columns for S6b reference point
         configuration for a Packet Data Network Gateway (PGW)."
    AUGMENTS { tmnxMobPdnEntry }
    ::= { tmnxMobPdnS6bTable 1 }

TmnxMobPdnS6bEntry ::= SEQUENCE {
        tmnxMobPdnS6bLastChanged             TimeStamp,
        tmnxMobPdnS6bTransactionTimer        Unsigned32,
        tmnxMobPdnS6bRetryCount              Unsigned32
    }

tmnxMobPdnS6bLastChanged OBJECT-TYPE
    SYNTAX      TimeStamp
    MAX-ACCESS  read-only
    STATUS      current
    DESCRIPTION
        "The value of tmnxMobPdnS6bLastChanged indicates the timestamp of
         the last change to this row in tmnxMobPdnS6bTable."
    ::= { tmnxMobPdnS6bEntry 1 }

tmnxMobPdnS6bTransactionTimer OBJECT-TYPE
    SYNTAX      Unsigned32 (1..180)
    UNITS       "seconds"
    MAX-ACCESS  read-write
    STATUS      current
    DESCRIPTION
        "The value of tmnxMobPdnS6bTransactionTimer specifies the amount of  
         time the node waits for a diameter peer to respond before trying 
         another peer."
     DEFVAL { 30 }
     ::= {tmnxMobPdnS6bEntry 2}

tmnxMobPdnS6bRetryCount  OBJECT-TYPE
    SYNTAX      Unsigned32 (0..8)
    MAX-ACCESS  read-write
    STATUS      current
    DESCRIPTION
        "The value of tmnxMobPdnS6bRetryCount specifies the number of times 
         the system will try to send an S6b message before declaring a 
         failed attempt."
    DEFVAL { 0 }
     ::= {tmnxMobPdnS6bEntry 3}


-- ----------------------------------------------
-- Compliance Statements
-- ----------------------------------------------

tmnxMobPdnV1v0Compliance  MODULE-COMPLIANCE
    STATUS      obsolete
    DESCRIPTION
        "The compliance statement for management of the Packet Data Network 
         Gateway (PGW) on the Alcatel-Lucent 7750 Mobile Gateway systems R1.0."
    MODULE
        MANDATORY-GROUPS {
            tmnxMobPdnGlobalGroup,
            tmnxMobPdnGroup,
            tmnxMobPdnApnGroup,
            tmnxMobPdnChargingGroup,
            tmnxMobPdnBcGroup,
            tmnxMobPdnRefPointGroup,
            tmnxMobPdnStatGroup,
            tmnxMobPdnGgsnGroup,
            tmnxMobPdnApGroup
            --tmnxMobPdnUnsupportedGroup Not supported
        }
    ::= { tmnxMobPdnCompliances 1 }

tmnxMobPdnV3v0Compliance  MODULE-COMPLIANCE
    STATUS      obsolete
    DESCRIPTION
        "The compliance statement for management of the Packet Data Network 
         Gateway (PGW) on the Alcatel-Lucent 7750 Mobile Gateway systems R3.0."
    MODULE
        MANDATORY-GROUPS {
            tmnxMobPdnGlobalGroup,
            tmnxMobPdnGroup,
            tmnxMobPdnApnGroup,
            tmnxMobPdnChargingGroup,
            tmnxMobPdnBcGroup,
            tmnxMobPdnRefPointGroup,
            tmnxMobPdnStatGroup,
            tmnxMobPdnGgsnGroup,
            tmnxMobPdnApGroup,
            tmnxMobPdnRadiusGroup,
            tmnxMobPdnApnV3v0Group,
            tmnxMobPdnGyV3v0Group,
            tmnxMobPdnGyStatsV3v0Group,
            tmnxMobPdnGlobalV3Group,
            tmnxMobPdnAAGrpV3Group,
            tmnxMobPdnRefPointV3v0Group,
            tmnxMobPdnChargingV3Group,
            tmnxMobPdnGgsnV3Group,
            tmnxMobPdnStatV3Group,
            tmnxMobPdnRadiusStatsV3v0Group,
            tmnxMobPdnS2aV3v0Group,
            tmnxMobPdnThresV3v0Group,
            tmnxMobPdnV3v0Group                
            --tmnxMobPdnUnsupportedGroup Not supported
        }
    ::= { tmnxMobPdnCompliances 2 }

tmnxMobPdnV3v5Compliance  MODULE-COMPLIANCE
    STATUS      obsolete
    DESCRIPTION
        "The compliance statement for management of the Packet Data Network 
         Gateway (PGW) on the Alcatel-Lucent 7750 Mobile Gateway systems R3.0.

         This compliance statement was made obsolete in the R4.0 release."
    MODULE
        MANDATORY-GROUPS {
            tmnxMobPdnGlobalGroup,
            tmnxMobPdnGroup,
            tmnxMobPdnChargingGroup,
            tmnxMobPdnBcGroup,
            tmnxMobPdnRefPointGroup,
            tmnxMobPdnStatGroup,
            tmnxMobPdnGgsnGroup,
            tmnxMobPdnApGroup,
            tmnxMobPdnRadiusGroup,
            tmnxMobPdnApnV3v0Group,
            tmnxMobPdnGyV3v0Group,
            tmnxMobPdnGyStatsV3v0Group,
            tmnxMobPdnGlobalV3Group,
            tmnxMobPdnAAGrpV3Group,
            tmnxMobPdnRefPointV3v0Group,
            tmnxMobPdnChargingV3Group,
            tmnxMobPdnGgsnV3Group,
            tmnxMobPdnStatV3Group,
            tmnxMobPdnRadiusStatsV3v0Group,
            tmnxMobPdnS2aV3v0Group,
            tmnxMobPdnThresV3v0Group,
            tmnxMobPdnV3v0Group,
            tmnxMobPdnApnV3v5Group,
            tmnxMobPdnAcctStatsV3Group,
            tmnxMobPdnBcV3v5Group
            --tmnxMobPdnUnsupportedGroup Not supported
        }
    ::= { tmnxMobPdnCompliances 3 }

tmnxMobPdn7xxxV10v0Compl  MODULE-COMPLIANCE
    STATUS      current
    DESCRIPTION
        "The compliance statement for management of the Packet Data Network 
         Gateway (PGW) on the Alcatel-Lucent 7750 SROS R10.0."
    MODULE
        MANDATORY-GROUPS {
            tmnxMobPdnAAGrpV3Group,
            tmnxMobPdnAcctStatsV3Group,
            tmnxMobPdnApGroup,
            tmnxMobPdnApnV3v0Group,
            tmnxMobPdnApnV3v5Group,
            tmnxMobPdnBcGroup,
            tmnxMobPdnBcV3v5Group,
            tmnxMobPdnChargingGroup,
            tmnxMobPdnChargingV3Group,
            tmnxMobPdnGgsnGroup,
            tmnxMobPdnGgsnV3Group,
            tmnxMobPdnGlobalGroup,
            tmnxMobPdnGlobalV3Group,
            tmnxMobPdnGroup,
            tmnxMobPdnGyStatsV3v0Group,
            tmnxMobPdnGyV3v0Group,
            tmnxMobPdnRadiusGroup,
            tmnxMobPdnRadiusStatsV3v0Group,
            tmnxMobPdnRefPointGroup,
            tmnxMobPdnRefPointV3v0Group,
            tmnxMobPdnRefPointV4v0Group,
            tmnxMobPdnS2aV3v0Group,
            tmnxMobPdnStatGroup,
            tmnxMobPdnStatV3Group,
            tmnxMobPdnThresV3v0Group,
            tmnxMobPdnV3v0Group,
            tmnxMobPdnUnsupportedGroup
        }
    ::= { tmnxMobPdnCompliances 4 }

tmnxMobPdnV4v0Compliance  MODULE-COMPLIANCE     
    STATUS      current
    DESCRIPTION
        "The compliance statement for management of the Packet Data Network 
         Gateway (PGW) on the Alcatel-Lucent 7750 Mobile Gateway systems R4.0."
    MODULE
        MANDATORY-GROUPS {
            tmnxMobPdnAAGrpV3Group,
            tmnxMobPdnAcctStatsV3Group,
            tmnxMobPdnApGroup,
            tmnxMobPdnApnV3v0Group,
            tmnxMobPdnApnV3v5Group,
            tmnxMobPdnApnV4v0Group,
            tmnxMobPdnBcGroup,
            tmnxMobPdnBcV3v5Group,
            tmnxMobPdnChargingGroup,
            tmnxMobPdnChargingV3Group,
            tmnxMobPdnGgsnGroup,
            tmnxMobPdnGgsnV3Group,
            tmnxMobPdnGlobalGroup,
            tmnxMobPdnGlobalV3Group,
            tmnxMobPdnGroup,
            tmnxMobPdnGyStatsV3v0Group,
            tmnxMobPdnGyV3v0Group,
            tmnxMobPdnRadiusGroup,
            tmnxMobPdnRadiusStatsV3v0Group,
            tmnxMobPdnRefPointGroup,
            tmnxMobPdnRefPointV3v0Group,
            tmnxMobPdnRefPointV4v0Group,
            tmnxMobPdnS2aV3v0Group,
            tmnxMobPdnStatGroup,
            tmnxMobPdnStatV3Group,
            tmnxMobPdnThresV3v0Group,
            tmnxMobPdnV3v0Group,
            tmnxMobPdnUnsupportedGroup,
            tmnxMobPdnOnlineChargV4v0Group,
            tmnxMobPdnS6bV4v0Group,
            tmnxMobPdnV4v0Group
        }
    ::= { tmnxMobPdnCompliances 5 }

-- ----------------------------------------------
-- Units of Conformance
-- ----------------------------------------------

tmnxMobPdnGlobalGroup  OBJECT-GROUP
    OBJECTS {
                tmnxMobPdnTableLastChanged,
                tmnxMobPdnSigTableLastChanged,
                tmnxMobPdnGxTableLastChanged,
                tmnxMobPdnS5TableLastChanged,
                tmnxMobPdnApnTableLastChanged,
                tmnxMobPdnApnExtTableLastChanged,
                tmnxMobPdnApnExt2TableLastChangd,
                tmnxMobPdnApnIpPoolTableLastChgd,
                tmnxMobPdnRfTableLastChanged,
                tmnxMobPdnGxPeerTableLastChngd,
                tmnxMobPdnPccBasePolTableLstChgd,
                tmnxMobPdnApnBasePolTableLstChgd,
                tmnxMobPdnGaTableLastChanged,
                tmnxMobPdnGnTableLastChanged,
                tmnxMobPdnApTableLastChanged,
                tmnxMobPdnGnPeerTableLastChanged,
                tmnxMobPdnRadiusTableLastChanged,
                tmnxMobPdnApnDaccGrpTblLastChngd,
                tmnxMobPdnGyTableLastChanged,
                tmnxMobPdnRatingGrpTableLastChgd,
                tmnxMobPdnGyPeerTableLastChngd,
                tmnxMobPdnGaPeerTableLastChngd,
                tmnxMobPdnApnExt3TableLastChangd,
                tmnxMobPdnS6bPeerTableLastChngd,
                tmnxMobPdnS6bTableLastChanged
            }
    STATUS      current
    DESCRIPTION
        "The group of global objects supporting management of the Packet Data
         Network Gateway (PGW) on the Alcatel-Lucent 7750 Mobile Gateway 
         systems."
    ::= { tmnxMobPdnGroups 1 }
    
tmnxMobPdnGroup  OBJECT-GROUP
    OBJECTS {
                tmnxMobPdnLastChanged,
                tmnxMobPdnAdminState,
                tmnxMobPdnOperState,
                tmnxMobPdnGracefulShutTimeout,
                tmnxMobPdnMobNode,
                tmnxMobPdnPccDynamicState,
                tmnxMobPdnPccPrecedenceBoundary,
                tmnxMobPdnUplinkQciPolName,
                tmnxMobPdnDownlinkQciPolName,
                tmnxMobPdnSigLastChanged,
                tmnxMobPdnSigGtpcProfile,
                tmnxMobPdnSigGtpuProfile,
                tmnxMobPdnSigDiaOriginHost,
                tmnxMobPdnSigDiaOriginRealm,
                tmnxMobPdnSigDiaProfile,
                tmnxMobPdnSigDefaultIfVRtrId,
                tmnxMobPdnSigDefaultIfIndex,                
                tmnxMobPdnBearerGtpuUdpChecksum,
                tmnxMobPdnBearerGtpuSeqNumber,
                tmnxMobPdnGxLastChanged,
                tmnxMobPdnGxDiaIfVRtrId,
                tmnxMobPdnGxDiaIfIndex,
                tmnxMobPdnGxDiaTransTimer,
                tmnxMobPdnGxDiaRetryCount,
                tmnxMobPdnGxDefPriDiaPeer,
                tmnxMobPdnGxDefSecDiaPeer,
                tmnxMobPdnS5LastChanged,
                tmnxMobPdnS5PeerList,
                tmnxMobPdnS5GtpcIfVRtrId,
                tmnxMobPdnS5GtpcIfIndex,
                tmnxMobPdnS5GtpuIfVRtrId,
                tmnxMobPdnS5GtpuIfIndex,
                tmnxMobPdnS5GtpcProfile,
                tmnxMobPdnS5GtpuProfile,
                tmnxMobPdnS5DualStackPref,
                tmnxMobPdnPccBasePolRowStatus,
                tmnxMobPdnUmtsQosPolName,
                tmnxMobPdnSigMIP6AgntInfType,
                tmnxMobPdnSigMIP6AgntInfFqdnType,
                tmnxMobPdnSigMIP6AgntInfFqdn,
                tmnxMobPdnSigMIP6AgntInfRealm
            }
    STATUS      current
    DESCRIPTION
        "The group of objects supporting management of the Packet Data Network
         Gateway (PGW) on the Alcatel-Lucent 7750 Mobile Gateway systems."
    ::= { tmnxMobPdnGroups 2 }

tmnxMobPdnApnGroup  OBJECT-GROUP
    OBJECTS {
                tmnxMobPdnApnRowStatus,
                tmnxMobPdnApnLastChanged,
                tmnxMobPdnApnAdminState,
                tmnxMobPdnApnOperState,
                tmnxMobPdnApnGracefulShutTimeout,
                tmnxMobPdnApnType,
                tmnxMobPdnApnVRtrId,
                tmnxMobPdnApnVirtualApnName,
                tmnxMobPdnApnPdnTypeIpv4,
                tmnxMobPdnApnPdnTypeIpv6,
                tmnxMobPdnApnPdnTypeIpv4v6,
                tmnxMobPdnApnPdnAllocType,
                tmnxMobPdnApnPdnRestrictionType,
                tmnxMobPdnApnAllowMultiplePdns,
                tmnxMobPdnApnSelectSubscribed,
                tmnxMobPdnApnSelectMsProvided,
                tmnxMobPdnApnSelectNwProvided,
                tmnxMobPdnApnIpAllocLocalPool,
                tmnxMobPdnApnIpAllocHssStatic,
                tmnxMobPdnApnIpAllocAaa,
                tmnxMobPdnApnIpAllocDhcpProxy,
                tmnxMobPdnApnIpAllocDhcpRelay,
                tmnxMobPdnApnIpAllocDhcpServer,
                tmnxMobPdnApnPcrfDynamicPcc,
                tmnxMobPdnApnPcrfPriDiameterPeer,
                tmnxMobPdnApnPcrfSecDiameterPeer,
                tmnxMobPdnApnUplinkQciPolName,
                tmnxMobPdnApnDownlinkQciPolName,
                tmnxMobPdnApnAggrRateUplink,
                tmnxMobPdnApnAggrRateDownlink,
                tmnxMobPdnApnIdleTimeout,
                tmnxMobPdnApnSessionTimeout,
                tmnxMobPdnApnRejectForeignSub,
                tmnxMobPdnApnBlockedPlmnList,
                tmnxMobPdnApnUliReporting,
                tmnxMobPdnApnExtLastChanged,
                tmnxMobPdnApnDnsServerV4AddrType,
                tmnxMobPdnApnDnsServerV4Addr,
                tmnxMobPdnApnDnsServerV6AddrType,
                tmnxMobPdnApnDnsServerV6Addr,
                tmnxMobPdnApnDhcpRelayV4RouterId,
                tmnxMobPdnApnDhcpRlyV4GiAddrType,
                tmnxMobPdnApnDhcpRelayV4GiAddr,
                tmnxMobPdnApnDhcpRelayV6RouterId,
                tmnxMobPdnApnDhcpRlyV6GiAddrType,
                tmnxMobPdnApnDhcpRelayV6GiAddr,
                tmnxMobPdnApnDhcpProxyV4RouterId,
                tmnxMobPdnApnDhcpPxyV4GiAddrType,
                tmnxMobPdnApnDhcpProxyV4GiAddr,
                tmnxMobPdnApnDhcpProxyV6RouterId,
                tmnxMobPdnApnDhcpPxyV6GiAddrType,
                tmnxMobPdnApnDhcpProxyV6GiAddr,
                tmnxMobPdnApnPcoDnsV4PriAddrType,
                tmnxMobPdnApnPcoDnsV4PriAddr,
                tmnxMobPdnApnPcoDnsV4SecAddrType,
                tmnxMobPdnApnPcoDnsV4SecAddr,
                tmnxMobPdnApnPcoDnsV6PriAddrType,
                tmnxMobPdnApnPcoDnsV6PriAddr,
                tmnxMobPdnApnPcoDnsV6SecAddrType,
                tmnxMobPdnApnPcoDnsV6SecAddr,
                tmnxMobPdnApnPcoPcscfV4PriAdrTyp,
                tmnxMobPdnApnPcoPcscfV4PriAddr,
                tmnxMobPdnApnPcoPcscfV6PriAdrTyp,
                tmnxMobPdnApnPcoPcscfV6PriAddr,
                tmnxMobPdnApnPcoNbnsV4PriAdrType,
                tmnxMobPdnApnPcoNbnsV4PriAddr,
                tmnxMobPdnApnPcoNbnsV4SecAdrType,
                tmnxMobPdnApnPcoNbnsV4SecAddr,
                tmnxMobPdnApnPcoNbnsV6PriAdrType,
                tmnxMobPdnApnPcoNbnsV6PriAddr,
                tmnxMobPdnApnPcoNbnsV6SecAdrType,
                tmnxMobPdnApnPcoNbnsV6SecAddr,
                tmnxMobPdnApnExt2LastChanged,
                tmnxMobPdnApnChrgProfileHome,
                tmnxMobPdnApnChrgProfileVisiting,
                tmnxMobPdnApnChrgProfileRoaming,
                tmnxMobPdnApnChrgCcIgnoreAny,
                tmnxMobPdnApnChrgCcIgnoreHome,
                tmnxMobPdnApnChrgCcIgnoreVisit,
                tmnxMobPdnApnChrgCcIgnoreRoaming,
                tmnxMobPdnApnCdfPriDiaPeer,
                tmnxMobPdnApnCdfSecDiaPeer,
                tmnxMobPdnApnPreAuthType,
                tmnxMobPdnApnPreAuthUserName,
                tmnxMobPdnApnAuthType,
                tmnxMobPdnApnAuthUserName,
                tmnxMobPdnApnAcctType,
                tmnxMobPdnApnAcctUserName,
                tmnxMobPdnApnAcctInterimReport,
                tmnxMobPdnApnIpPoolRowStatus,
                tmnxMobPdnApnBasePolRowStatus,
                tmnxMobPdnApnUmtsQosPolName,
                tmnxMobPdnApnChrgCcReject,
                tmnxMobPdnApnAuthServerGroup,
                tmnxMobPdnApnAuthAcctSupImsi,
                tmnxMobPdnApnAcctServerGroup,
                tmnxMobPdnApnWaitAccounting,
                tmnxMobPdnApnPreAuthServerGroup
            }
    STATUS      obsolete
    DESCRIPTION
        "The group of objects supporting management of a Access Point Name 
         (APN) on a Packet Data Network Gateway (PGW) on the Alcatel-Lucent 
         7750 Mobile Gateway systems."
    ::= { tmnxMobPdnGroups 3 }
    
tmnxMobPdnUnsupportedGroup  OBJECT-GROUP
    OBJECTS {
              tmnxMobPdnHomePlmnList,
              tmnxMobPdnVisitingPlmnList,
              tmnxMobPdnSigPmipv6Profile,
              tmnxMobPdnSigPmipv6AddrScheme,
              tmnxMobPdnSigPmipv6RtrAdIntvl,
              tmnxMobPdnSigPmipv6RtrAdLife,
              tmnxMobPdnApnDescription,
              tmnxMobPdnApnGracefulShutTimeout,
              tmnxMobPdnStatVirtualApn
            }
    STATUS      current
    DESCRIPTION
        "This group of objects is not supported on the Alcatel-Lucent 7750 
         Mobile Gateway systems."
    ::= { tmnxMobPdnGroups 4 }

tmnxMobPdnChargingGroup  OBJECT-GROUP
    OBJECTS {
                tmnxMobPdnChargingProfHome,
                tmnxMobPdnChargingProfVisiting,
                tmnxMobPdnChargingProfRoaming,
                tmnxMobPdnChrgCcIgnoreAny,
                tmnxMobPdnChrgCcIgnoreHome,
                tmnxMobPdnChrgCcIgnoreVisiting,
                tmnxMobPdnChrgCcIgnoreRoaming,
                tmnxMobPdnRfLastChanged,
                tmnxMobPdnRfVRtrId,
                tmnxMobPdnRfIfIndex,
                tmnxMobPdnRfPriDiaPeer,
                tmnxMobPdnRfSecDiaPeer,
                tmnxMobPdnRfAcctIntmInterval,
                tmnxMobPdnRfApplTxTimer,
                tmnxMobPdnRfRetryCount,
                tmnxMobPdnRfChargingGroupID,
                tmnxMobPdnRfOperatorString,
                tmnxMobPdnRfAcctLevel,
                tmnxMobPdnRfNodeId,
                tmnxMobPdnRfOcFilePrivateInfo,
                tmnxMobPdnRfOcFileExtension,
                tmnxMobPdnRfOcFileClosureSize,
                tmnxMobPdnRfOcFileClsLifeTime,
                tmnxMobPdnRfOcFileClsMaxAcrs,
                tmnxMobPdnRfOcFileObsoleteTime,
                tmnxMobPdnRfOcPrimaryCf,
                tmnxMobPdnRfOcCf1State,
                tmnxMobPdnRfOcCf1Limit,
                tmnxMobPdnRfOcCf2State,
                tmnxMobPdnRfOcCf2Limit,
                tmnxMobPdnChrgCcReject,
                tmnxMobPdnChrgNodeId
            }
    STATUS      current
    DESCRIPTION
        "The group of objects supporting the management of the Packet Data 
         Network Gateway (PGW) charging applications on the Alcatel-Lucent 7750 
         Mobile Gateway systems."
    ::= { tmnxMobPdnGroups 5 }
        
tmnxMobPdnBcGroup  OBJECT-GROUP
    OBJECTS {
                tmnxMobPdnUeRowStatus,
                tmnxMobPdnUeRowStatus,
                tmnxMobPdnUeMsIsdn,
                tmnxMobPdnUeImei,
                tmnxMobPdnUeNai,
                tmnxMobPdnUeNwkMcc,
                tmnxMobPdnUeNwkMnc,
                tmnxMobPdnUeTrackingAreaId,
                tmnxMobPdnUeCellId,
                tmnxMobPdnUeState,
                tmnxMobPdnUeRat,
                tmnxMobPdnUePdnContexts,
                tmnxMobPdnUeBearerContexts,
                tmnxMobPdnUeRfPgwAddrType,
                tmnxMobPdnUeRfPgwAddr,
                tmnxMobPdnPcLinkedBearerId,
                tmnxMobPdnPcApnRestriction,
                tmnxMobPdnPcUlApnAmbr,
                tmnxMobPdnPcDlApnAmbr,
                tmnxMobPdnPcIpv4AddressType,
                tmnxMobPdnPcIpv4Address,
                tmnxMobPdnPcIpv6AddressType,
                tmnxMobPdnPcIpv6Address,
                tmnxMobPdnPcBearerContexts,
                tmnxMobPdnPcSessionState,
                tmnxMobPdnPcLastEvent,
                tmnxMobPdnPcSigProtocol,
                tmnxMobPdnPcTnlRemoteCtrlTeid,
                tmnxMobPdnPcTnlRemoteCtrlAddrTyp,
                tmnxMobPdnPcTnlRemoteCtrlAddr,
                tmnxMobPdnPcTnlRemV6CtrlAddrTyp,
                tmnxMobPdnPcTnlRemV6CtrlAddr,
                tmnxMobPdnPcTnlLocalCtrlTeid,
                tmnxMobPdnPcTnlLocalCtrlAddrType,
                tmnxMobPdnPcTnlLocalCtrlAddr,
                tmnxMobPdnPcTnlLocalV6CtrlAdrTyp,
                tmnxMobPdnPcTnlLocalV6CtrlAddr,
                tmnxMobPdnPcOfcBearerType,
                tmnxMobPdnPcPcrfEventTriggers,
                tmnxMobPdnPcGxPcrfAddressType,
                tmnxMobPdnPcGxPcrfAddress,
                tmnxMobPdnPcGxPgwAddressType,
                tmnxMobPdnPcGxPgwAddress,
                tmnxMobPdnBcBearerType,
                tmnxMobPdnBcUpTime,
                tmnxMobPdnBcQci,
                tmnxMobPdnBcArp,
                tmnxMobPdnBcSdfs,
                tmnxMobPdnBcFilters,
                tmnxMobPdnBcTnlRemoteTeid,
                tmnxMobPdnBcTnlRemoteDataAddrTyp,
                tmnxMobPdnBcTnlRemoteDataAddr,
                tmnxMobPdnBcTnlLocalTeid,
                tmnxMobPdnBcTnlLocalDataAddrType,
                tmnxMobPdnBcTnlLocalDataAddr,
                tmnxMobPdnBcTnlDLPackets,
                tmnxMobPdnBcTnlDLBytes,
                tmnxMobPdnBcSgiULPackets,
                tmnxMobPdnBcSgiULBytes,
                tmnxMobPdnBcTnlDLPacketsLow,
                tmnxMobPdnBcTnlDLPacketsHigh,
                tmnxMobPdnBcTnlDLBytesLow,
                tmnxMobPdnBcTnlDLBytesHigh,
                tmnxMobPdnBcSgiULPacketsLow,
                tmnxMobPdnBcSgiULPacketsHigh,
                tmnxMobPdnBcSgiULBytesLow,
                tmnxMobPdnBcSgiULBytesHigh,
                tmnxMobPdnBcOfcServerAddrType,
                tmnxMobPdnBcOfcServerAddr,
                tmnxMobPdnBcOfcServerState,
                tmnxMobPdnBcOfcChargingProfile,
                tmnxMobPdnBcOfcTriggeredRecords,
                tmnxMobPdnBcOfcInterimRecords,
                tmnxMobPdnBcSdfPcrfPrecedence,
                tmnxMobPdnBcSdfRuleName,
                tmnxMobPdnBcSdfPacketFilters,
                tmnxMobPdnBcSdfQosUlMbr,
                tmnxMobPdnBcSdfQosDlMbr,
                tmnxMobPdnBcSdfQosUlGbr,
                tmnxMobPdnBcSdfQosDlGbr,
                tmnxMobPdnBcSdfFilterProtocol,
                tmnxMobPdnBcSdfFilterSrcAdrType,
                tmnxMobPdnBcSdfFilterSrcAddr,
                tmnxMobPdnBcSdfFilterSrcPfxLen,
                tmnxMobPdnBcSdfFilterDstAdrType,
                tmnxMobPdnBcSdfFilterDestAddr,
                tmnxMobPdnBcSdfFilterDestPfxLen,
                tmnxMobPdnBcSdfFilterSrcPorts,
                tmnxMobPdnBcSdfFilterDestPorts,
                tmnxMobPdnBcSdfFirstSrcPortOper,
                tmnxMobPdnBcSdfFirstSrcPortVal1,
                tmnxMobPdnBcSdfFirstSrcPortVal2,
                tmnxMobPdnBcSdfSecndSrcPortOper,
                tmnxMobPdnBcSdfSecndSrcPortVal1,
                tmnxMobPdnBcSdfSecndSrcPortVal2,
                tmnxMobPdnBcSdfFirstDstPortOper,
                tmnxMobPdnBcSdfFirstDstPortVal1,
                tmnxMobPdnBcSdfFirstDstPortVal2,
                tmnxMobPdnBcSdfSecndDstPortOper,
                tmnxMobPdnBcSdfSecndDstPortVal1,
                tmnxMobPdnBcSdfSecndDstPortVal2,
                tmnxMobPdnUeCtxAccessType,
                tmnxMobPdnUeSubType,
                tmnxMobPdnBcAccessType,
                tmnxMobPdnPcAccessType,
                tmnxMobPdnPcSelectionMode,
                tmnxMobPdnPcTnlLocalDataAddrType,
                tmnxMobPdnPcTnlLocalDataAddr,
                tmnxMobPdnPcPGWGREkey, 
                tmnxMobPdnPcMAGGREkey,
                tmnxMobPdnPcTnlRemoteDataAddrTyp,
                tmnxMobPdnPcTnlRemoteDataAddr,
                tmnxMobPdnPcRfSrvAddrType,
                tmnxMobPdnPcRfSrvAddr,
                tmnxMobPdnPcRfServerState,
                tmnxMobPdnPcRfChargingLevel,
                tmnxMobPdnPcRfChargingProfile,
                tmnxMobPdnPcRfInterimRecords,
                tmnxMobPdnPcRfTriggeredRecords,
                tmnxMobPdnBcPGWGreKey,
                tmnxMobPdnBcMAGGreKey,
                tmnxMobPdnPcTnlDLPackets,
                tmnxMobPdnPcTnlDLBytes,
                tmnxMobPdnPcSgiULPackets,
                tmnxMobPdnPcSgiULBytes,
                tmnxMobPdnPcTnlDLPacketsLow,
                tmnxMobPdnPcTnlDLPacketsHigh,
                tmnxMobPdnPcTnlDLBytesLow,
                tmnxMobPdnPcTnlDLBytesHigh,
                tmnxMobPdnPcSgiULPacketsLow,
                tmnxMobPdnPcSgiULPacketsHigh,
                tmnxMobPdnPcSgiULBytesLow,
                tmnxMobPdnPcSgiULBytesHigh
            }
    STATUS      current
    DESCRIPTION
        "The group of objects supporting management of the Packet Data Network 
         Gateway (PGW) bearer contexts on the Alcatel-Lucent 7750 Mobile Gateway 
         systems."
    ::= { tmnxMobPdnGroups 6 }

tmnxMobPdnRefPointGroup  OBJECT-GROUP
    OBJECTS {
                tmnxMobPdnGxPeerLastChanged,
                tmnxMobPdnGxPeerCreateTime,
                tmnxMobPdnGxPeerPathMgmtState,
                tmnxMobPdnGxPeerDetailState,
                tmnxMobPdnGxStatTxCer,
                tmnxMobPdnGxStatRxCea,
                tmnxMobPdnGxStatRxDpr,
                tmnxMobPdnGxStatTxDpa,
                tmnxMobPdnGxStatTxDwr,
                tmnxMobPdnGxStatRxDwa,
                tmnxMobPdnGxStatConnAttempts,
                tmnxMobPdnGxStatConnFailures,
                tmnxMobPdnGxStatRxTransportDisc,
                tmnxMobPdnGxStatRxMsgUnexpectVer,
                tmnxMobPdnGxStatRxMsgTooBig,
                tmnxMobPdnGxStatRxMsgTooSmall,
                tmnxMobPdnGxStatRxInvalidCea,
                tmnxMobPdnGxStatRxMsgs,
                tmnxMobPdnGxStatTxMsgs,
                tmnxMobPdnGxStatTxRetransmitMsgs,
                tmnxMobPdnGxStatTxCcrInitial,
                tmnxMobPdnGxStatRxCcaInitial,
                tmnxMobPdnGxStatTxCcrUpdate,
                tmnxMobPdnGxStatRxCcaUpdate,
                tmnxMobPdnGxStatTxCcrTerminate,
                tmnxMobPdnGxStatRxCcaTerminate,
                tmnxMobPdnGxStatCcrInitFails,
                tmnxMobPdnGxStatCcrUpdateFails,
                tmnxMobPdnGxStatCcrTermFails,
                tmnxMobPdnGxStatRxRar,
                tmnxMobPdnGxStatTxRaa,
                tmnxMobPdnGxStatTxRaaNack,
                tmnxMobPdnGxStatBberfs,
                tmnxMobPdnGxStatRxMalformedPkts,
                tmnxMobPdnGxStatRxCcaIMalformPkt,
                tmnxMobPdnGxStatRxCcaUMalformPkt,
                tmnxMobPdnGxStatRxCcaTMalformPkt,
                tmnxMobPdnGxStatRxRarMalformPkts,
                tmnxMobPdnGxStatRxUnknownPkts,
                tmnxMobPdnGxStatRxCcaIUnknownPkt,
                tmnxMobPdnGxStatRxCcaUUnknownPkt,
                tmnxMobPdnGxStatRxCcaTUnknownPkt,
                tmnxMobPdnGxStatRxRarUnknownPkts,
                tmnxMobPdnGxStatRxMissingIePkts,
                tmnxMobPdnGxStatRxCcaIMissIePkts,
                tmnxMobPdnGxStatRxCcaUMissIePkts,
                tmnxMobPdnGxStatRxCcaTMissIePkts,
                tmnxMobPdnGxStatRxRarMissIePkts,
                tmnxMobPdnGxStatRxCcaIUnkSession,
                tmnxMobPdnGxStatRxCcaUUnkSession,
                tmnxMobPdnGxStatRxCcaTUnkSession,
                tmnxMobPdnGxStatRxRarUnkSession,
                tmnxMobPdnGnPeerLastChanged,
                tmnxMobPdnGnPeerCreateTime,
                tmnxMobPdnGnPeerPathMgmtState,
                tmnxMobPdnGnPeerGatewayId,
                tmnxMobPdnGnPeerType,
                tmnxMobPdnGnStatCreatePdpReq,
                tmnxMobPdnGnStatCreatePdpRsp,
                tmnxMobPdnGnStatDeletePdpReq,
                tmnxMobPdnGnStatDeletePdpRsp,
                tmnxMobPdnGnStatModifyPdpReq,
                tmnxMobPdnGnStatModifyPdpRsp,
                tmnxMobPdnGnStatRxEchoRequests,
                tmnxMobPdnGnStatTxEchoResponses,
                tmnxMobPdnGnStatTxEchoRequests,
                tmnxMobPdnGnStatRxEchoResponses,
                tmnxMobPdnGnStatRxErrorsIndCnt,
                tmnxMobPdnGnStatTxErrorsIndCnt,
                tmnxMobPdnGnStatRxMalformedPkts,
                tmnxMobPdnGnStatRxUnknownPkts,
                tmnxMobPdnGnStatRxMissingIePkts,
                tmnxMobPdnGnStatPeerRestarts,
                tmnxMobPdnGnStatPeerRestrtCount,
                tmnxMobPdnGnStatPathMgmtFails,
                tmnxMobPdnGaStatLastChanged,
                tmnxMobPdnGaStatCreateTime,
                tmnxMobPdnGaStatRxEchoRequests,
                tmnxMobPdnGaStatTxEchoResponses,
                tmnxMobPdnGaStatTxEchoRequests,
                tmnxMobPdnGaStatRxEchoResponses,
                tmnxMobPdnGaStatRxNodeAlRequests,
                tmnxMobPdnGaStatTxNodeAlResps,
                tmnxMobPdnGaStatTxDataRecReqs,
                tmnxMobPdnGaStatTxDataRecTferReq,
                tmnxMobPdnGaStatRetrDataRecReqs, 
                tmnxMobPdnGaStatRxDataRecReqs,
                tmnxMobPdnGaStatUnackDataRexReqs,
                tmnxMobPdnGaStatRxRedirectionReq,
                tmnxMobPdnGaStatTxRedrnResp,
                tmnxMobPdnGaStatRxInvalidMsgs,
                tmnxMobPdnGaStatRxVerNotSupp,            
                tmnxMobPdnGaStatTxCdrTermination,
                tmnxMobPdnGaStatTxCdrMaxChngCond,
                tmnxMobPdnGaStatTxCdrMsTmzChng,
                tmnxMobPdnGaStatTxCdrRatChng,
                tmnxMobPdnGaStatTxCdrTimeLimit,
                tmnxMobPdnGaStatTxCdrVolLimit,        
                tmnxMobPdnGaStatRxCdrReqAcc,
                tmnxMobPdnGaStatRxCdrNoResAva,
                tmnxMobPdnGaStatRxCdrReqNotFf,
                tmnxMobPdnGaStatRxCdrReqFfilled,
                tmnxMobPdnGaStatRxCdrDupReqFf,
                tmnxMobPdnGaStatRxCdrInvMsgFmat,
                tmnxMobPdnGaStatRxCdrVerNotSupp,
                tmnxMobPdnGaStatRxCdrSrvcNotSupp,
                tmnxMobPdnGaStatRxCdrMandIeInc,
                tmnxMobPdnGaStatRxCdrMandIeMiss,
                tmnxMobPdnGaStatRxCdrOptIeInc,
                tmnxMobPdnGaStatRxCdrSystemFail,
                tmnxMobPdnGaStatRtrEchoRequests,
                tmnxMobPdnGaStatGtpPrimeFail,
                tmnxMobPdnGaStatOperState,
                tmnxMobPdnGaStatUpTime,
                tmnxMobPdnS6bStatAARInitTx,
                tmnxMobPdnS6bStatAARExtnTx,
                tmnxMobPdnS6bStatAARDetachTx,
                tmnxMobPdnS6bStatAARReauthTx,
                tmnxMobPdnS6bStatAAAInitAtchRx,
                tmnxMobPdnS6bStatAAAExtnRx,
                tmnxMobPdnS6bStatAAADetachRx,
                tmnxMobPdnS6bStatAAAReauthRx,
                tmnxMobPdnS6bStatAAASuccessRx,
                tmnxMobPdnS6bStatAAARejectRx,
                tmnxMobPdnS6bStatRARequestRx,
                tmnxMobPdnS6bStatRAAnswerTx,
                tmnxMobPdnS6bStatSTRequestTx,
                tmnxMobPdnS6bStatSTAnswerRx,
                tmnxMobPdnS6bStatASRequestRx,
                tmnxMobPdnS6bStatASAnswerTx,
                tmnxMobPdnS6bStatAAAMissAVPPktRx,
                tmnxMobPdnS6bStatRARMissAVPPktRx,
                tmnxMobPdnS6bStatSTAMissAVPPktRx,
                tmnxMobPdnS6bStatASRMissAVPPktRx,
                tmnxMobPdnS6bStatAAAUnknSesPktRx,
                tmnxMobPdnS6bStatAARRetries,
                tmnxMobPdnS6bStatSTRRetries,
                tmnxMobPdnS6bStatMessagesTx,
                tmnxMobPdnS6bStatMessagesRx,
                tmnxMobPdnS6bStatCERMsgsTx,
                tmnxMobPdnS6bStatCEAMsgsRx,
                tmnxMobPdnS6bStatDPRMsgsTx,
                tmnxMobPdnS6bStatDPRMsgsRx,
                tmnxMobPdnS6bStatDPAMsgsTx,
                tmnxMobPdnS6bStatDPAMsgsRx,
                tmnxMobPdnS6bStatDWRMsgsTx,
                tmnxMobPdnS6bStatDWRMsgsRx,
                tmnxMobPdnS6bStatDWAMsgsTx,
                tmnxMobPdnS6bStatDWAMsgsRx,
                tmnxMobPdnS6bPeerLastChanged,
                tmnxMobPdnS6bPeerCreateTime,
                tmnxMobPdnS6bPeerPathMgmtState,
                tmnxMobPdnS6bPeerDetailState,
                tmnxMobPdnS6bStatConnAttempts,
                tmnxMobPdnS6bStatConnFailures,
                tmnxMobPdnS6bStatRxMsgUnexpctVer,
                tmnxMobPdnS6bStatRxMsgTooBig,
                tmnxMobPdnS6bStatRxMsgTooSmall,
                tmnxMobPdnS6bStatRxInvalidCea,
                tmnxMobPdnS6bStatTxRetrnsmitMsgs,
                tmnxMobPdnS6bStatRxTransportDisc,
                tmnxMobPdnGxStatTxDpr,
                tmnxMobPdnGxStatRxDpa,
                tmnxMobPdnGxStatRxDwr,
                tmnxMobPdnGxStatTxDwa,
                tmnxMobPdnS6bAARFinalTOTx,
                tmnxMobPdnS6bSTRUnknownSessTx,
                tmnxMobPdnS6bSTRFinalTOTx,
                tmnxMobPdnS6bASAUnknownSessTx,
                tmnxMobPdnS6bRAAUnknownSessTx,
                tmnxMobPdnS6bAAAMalformedPktsRx,
                tmnxMobPdnS6bSTAMalformedPktsRx,
                tmnxMobPdnS6bAAABadAVPValue,
                tmnxMobPdnS6bSTABadAVPValueRx,
                tmnxMobPdnS6bRARBadAVPValueRx,
                tmnxMobPdnS6bRARDuplicateRx,
                tmnxMobPdnS6bASRBadAVPValueRx,
                tmnxMobPdnS6bASRDuplicateRx
            }
    STATUS      current
    DESCRIPTION
        "The group of objects supporting management of the Packet Data Network
         Gateway (PGW) reference point statistics on the Alcatel-Lucent 
         7750 Mobile Gateway systems."
    ::= { tmnxMobPdnGroups 7 }

tmnxMobPdnStatGroup  OBJECT-GROUP
    OBJECTS {
         tmnxMobPdnStatBearers,  
         tmnxMobPdnStatDedicatedBearers,  
         tmnxMobPdnStatDefaultBearers,  
         tmnxMobPdnStatIpLocalPools,  
         tmnxMobPdnStatIpv4Bearers,  
         tmnxMobPdnStatIpv4Sdf,  
         tmnxMobPdnStatIpv4PdnSessions,  
         tmnxMobPdnStatIpv4v6Bearers,  
         tmnxMobPdnStatIpv4v6PdnSessions,  
         tmnxMobPdnStatIpv6Bearers,  
         tmnxMobPdnStatIpv6Sdf,  
         tmnxMobPdnStatIpv6PdnSessions,
         tmnxMobPdnStatRealApn,  
         tmnxMobPdnStatRoamers,  
         tmnxMobPdnStatPdnSessions,  
         tmnxMobPdnStatVPRNs,
         tmnxMobPdnProcDetach,  
         tmnxMobPdnProcDetachFail,  
         tmnxMobPdnProcHssQosModify,  
         tmnxMobPdnProcHssQosModifyFail,  
         tmnxMobPdnProcNwDedBrActv,  
         tmnxMobPdnProcNwDedBrActvFail,  
         tmnxMobPdnProcNwDedBrDeActv,  
         tmnxMobPdnProcNwDedBrDeActvFail,  
         tmnxMobPdnProcNwDedBrModify,  
         tmnxMobPdnProcNwDedBrModifyFail,  
         tmnxMobPdnProcPcrfQosModify,  
         tmnxMobPdnProcPcrfQosModifyFail,  
         tmnxMobPdnProcPgwPdnSessDel,  
         tmnxMobPdnProcPgwPdnSessDelFail,  
         tmnxMobPdnProcAttach,  
         tmnxMobPdnProcAttachFail,  
         tmnxMobPdnProcSgwReloc,  
         tmnxMobPdnProcSgwRelocFail,  
         tmnxMobPdnProcUeDedBrActv,  
         tmnxMobPdnProcUeDedBrActvFail,  
         tmnxMobPdnProcUeDedBrDeActv,  
         tmnxMobPdnProcUeDedBrDeActvFail,  
         tmnxMobPdnProcUeDedBrModify,  
         tmnxMobPdnProcUeDedBrModifyFail,
         tmnxMobPdnStatGnSgsns
    }
    STATUS      current
    DESCRIPTION
        "The group of objects supporting management of the Packet Data Network
         Gateway (PGW) status on the Alcatel-Lucent 7750 Mobile Gateway 
         systems."
    ::= { tmnxMobPdnGroups 8 }

tmnxMobPdnGgsnGroup  OBJECT-GROUP
    OBJECTS {
         tmnxMobPdnGaLastChanged,
         tmnxMobPdnGaIfVRtrId,
         tmnxMobPdnGaIfIndex,
         tmnxMobPdnGaGtpcProfile,
         tmnxMobPdnGaGtpPrimeGrpName,
         tmnxMobPdnGnLastChanged,
         tmnxMobPdnGnGtpcIfVRtrId,
         tmnxMobPdnGnGtpcIfIndex,
         tmnxMobPdnGnGtpuIfVRtrId,
         tmnxMobPdnGnGtpuIfIndex,
         tmnxMobPdnGnGtpcProfile,
         tmnxMobPdnGnGtpuProfile
    }
    STATUS      current
    DESCRIPTION
        "The group of objects supporting management of the Gateway GPRS Service 
         Node (GGSN) on the Packet Data Network Gateway (PGW) on the 
         Alcatel-Lucent 7750 Mobile Gateway systems."
    ::= { tmnxMobPdnGroups 9 }

tmnxMobPdnApGroup  OBJECT-GROUP
    OBJECTS {
                tmnxMobPdnApRowStatus,
                tmnxMobPdnApLastChanged,
                tmnxMobPdnApCollectAcctStats
            }
    STATUS      current
    DESCRIPTION
        "The group of objects supporting the management of the Packet Data 
         Network Gateway (PGW) Accounting Policies on the Alcatel-Lucent 7750
         Mobile Gateway systems."
    ::= { tmnxMobPdnGroups 10 }

tmnxMobPdnRadiusGroup  OBJECT-GROUP
    OBJECTS {
                tmnxMobPdnRadiusLastChanged,
                tmnxMobPdnRadiusIfVRtrId,
                tmnxMobPdnRadiusIfIndex,
                tmnxMobPdnRadiusDisconnect,
                tmnxMobPdnApnDaccGrpRowStatus,
                tmnxMobPdnApnDaccGrpLastChngd
            }
    STATUS      current
    DESCRIPTION
        "The group of objects supporting management of radius authentication 
         and accounting an Access Point Name (APN) on a Packet Data Network 
         Gateway (PGW) on the Alcatel-Lucent 7750 Mobile Gateway systems."
    ::= { tmnxMobPdnGroups 11 }

tmnxMobPdnApnV3v0Group  OBJECT-GROUP
    OBJECTS {
                tmnxMobPdnApnOcsPriDiaPeer,
                tmnxMobPdnApnOcsSecDiaPeer,
                tmnxMobPdnApnGyDccaProfile,
                tmnxMobPdnApnChangeRepAction,
                tmnxMobPdnApnSuppFramedRoute,
                tmnxMobPdnApnPccQciValue,
                tmnxMobPdnApnPccArpValue,
                tmnxMobPdnApnHttpRedirect,
                tmnxMobPdnApnAuthPriDiamPeer,
                tmnxMobPdnApnAuthSecDiamPeer,
                tmnxMobPdnApnAuthFixUserName,
                tmnxMobPdnApnAuthFixPassword,
                tmnxMobPdnApnDefAppProfile,
                tmnxMobPdnApnRedirTrafficPol,
                tmnxMobPdnApnRedirPolRouterInst,
                tmnxMobPdnApnRedirPolNHopAddrTyp,
                tmnxMobPdnApnRedirPolNHopAddr,
                tmnxMobPdnApnAllowEmergency
            }
    STATUS      current
    DESCRIPTION
        "The group of objects supporting management of a Access Point Name 
         (APN) on a Packet Data Network Gateway (PGW) on the Alcatel-Lucent 
         7750 Mobile Gateway systems."
    ::= { tmnxMobPdnGroups 12 }

tmnxMobPdnGyV3v0Group  OBJECT-GROUP
    OBJECTS {
         tmnxMobPdnGyLastChanged,
         tmnxMobPdnGyVRtrId,
         tmnxMobPdnGyIfIndex,
         tmnxMobPdnGyPriDiaPeer,
         tmnxMobPdnGySecDiaPeer,
         tmnxMobPdnGyDccaProf,
         tmnxMobPdnRatingGrpRowStatus,
         tmnxMobPdnRatingGrpLastChanged,
         tmnxMobPdnRatingGrpActvtThresold
    }
    STATUS      current
    DESCRIPTION
        "The group of objects supporting management of the Gy interface on the
         Packet Data Network Gateway (PGW) on the Alcatel-Lucent 7750 Mobile
         Gateway systems."
    ::= { tmnxMobPdnGroups 13 }

tmnxMobPdnGyStatsV3v0Group  OBJECT-GROUP
    OBJECTS {
         tmnxMobPdnGyPeerLastChanged,
         tmnxMobPdnGyPeerCreateTime,
         tmnxMobPdnGyPeerPathMgmtState,
         tmnxMobPdnGyPeerDetailState,
         tmnxMobPdnGyStatCcrGranted,
         tmnxMobPdnGyStatCcrDenied,
         tmnxMobPdnGyStatCcrInitialMsgTx,
         tmnxMobPdnGyStatCcrUpdateMsgTx,
         tmnxMobPdnGyStatCcrTermMsgTx,
         tmnxMobPdnGyStatCcaInitialMsgRx,
         tmnxMobPdnGyStatCcaUpdateMsgRx,
         tmnxMobPdnGyStatCcaTermMsgRx,
         tmnxMobPdnGyStatCcrInitMsgFails,
         tmnxMobPdnGyStatCcrUpdMsgFails,
         tmnxMobPdnGyStatCcrTermMsgFails,
         tmnxMobPdnGyStatAsrMsgRx,
         tmnxMobPdnGyStatAsaMsgTx,
         tmnxMobPdnGyStatAsaNackMsgTx,
         tmnxMobPdnGyStatRarMsgRx,
         tmnxMobPdnGyStatRaaMsgTx,
         tmnxMobPdnGyStatRaaNackMsgTx,
         tmnxMobPdnGyStatMalformedPktsRx,
         tmnxMobPdnGyStatCCAInitMalfPktRx,
         tmnxMobPdnGyStatCCAUpdtMalfPktRx,
         tmnxMobPdnGyStatCCATermMalfPktRx,
         tmnxMobPdnGyStatRarMalfPktRx,
         tmnxMobPdnGyStatAsrMalfPktRx,
         tmnxMobPdnGyStatUnkwnPktsRx,
         tmnxMobPdnGyStatCcaInitUnkPktRx,
         tmnxMobPdnGyStatCcaUpdUnkPktRx,
         tmnxMobPdnGyStatCcaTermUnkPktRx,
         tmnxMobPdnGyStatRarUnkPktRx,
         tmnxMobPdnGyStatAsrUnkPktRx,
         tmnxMobPdnGyStatMissingAvpPktRx,
         tmnxMobPdnGyStatCcaIMisAvpPktRx,
         tmnxMobPdnGyStatCcaUMisAvpPktRx,
         tmnxMobPdnGyStatCcaTMisAvpPktRx,
         tmnxMobPdnGyStatRarMisAvpPktRx,
         tmnxMobPdnGyStatAsrMisAvpPktRx,
         tmnxMobPdnGyStatCcaIUnkSessPkts,
         tmnxMobPdnGyStatCcaUUnkSessPkts,
         tmnxMobPdnGyStatCcaTUnkSessPkts,
         tmnxMobPdnGyStatRarUnkSessPkts,
         tmnxMobPdnGyStatAsrUnkSessPkts,
         tmnxMobPdnGyStatTxCer,
         tmnxMobPdnGyStatRxCea,
         tmnxMobPdnGyStatRxDpr,
         tmnxMobPdnGyStatTxDpa,
         tmnxMobPdnGyStatTxDwr,
         tmnxMobPdnGyStatRxDwa,
         tmnxMobPdnGyStatConnAttempts,
         tmnxMobPdnGyStatConnFailures,
         tmnxMobPdnGyStatRxTransportDisc,
         tmnxMobPdnGyStatRxMsgUnexpectVer,
         tmnxMobPdnGyStatRxMsgTooBig,
         tmnxMobPdnGyStatRxMsgTooSmall,
         tmnxMobPdnGyStatRxInvalidCea,
         tmnxMobPdnGyStatRxMsgs,
         tmnxMobPdnGyStatTxMsgs,
         tmnxMobPdnGyStatTxRetransmitMsgs,
         tmnxMobPdnGyStatTxDpr,
         tmnxMobPdnGyStatRxDpa,
         tmnxMobPdnGyStatRxDwr,
         tmnxMobPdnGyStatTxDwa
    }
    STATUS      current
    DESCRIPTION
        "The group of objects supporting management of the Gy interface
         statistics on the Packet Data Network Gateway (PGW) on the
         Alcatel-Lucent 7750 Mobile Gateway systems."
    ::= { tmnxMobPdnGroups 14 }

tmnxMobPdnGlobalV3Group  OBJECT-GROUP
    OBJECTS {
                tmnxMobPdnRadiusTableLastChanged,
                tmnxMobPdnApnDaccGrpTblLastChngd,
                tmnxMobPdnGyTableLastChanged,
                tmnxMobPdnRatingGrpTableLastChgd,
                tmnxMobPdnGyPeerTableLastChngd,
                tmnxMobPdnRadPeerTableLastChngd,
                tmnxMobPdnGpTableLastChanged,
                tmnxMobPdnGpPeerTableLastChanged,
                tmnxMobPdnS2aTableLastChanged,
                tmnxMobPdnS2aPeerTblLastChanged
            }
    STATUS      current
    DESCRIPTION
        "The group of global objects supporting management of the Packet Data
         Network Gateway (PGW) on the Alcatel-Lucent 7750 Mobile Gateway 
         systems in 3.0 release."
    ::= { tmnxMobPdnGroups 15 }

tmnxMobPdnAAGrpV3Group  OBJECT-GROUP
    OBJECTS {
                tmnxMobPdnAaGroupIndex,
                tmnxMobPdnAaGrpPartIndex,
                tmnxMobPdnApnAaGroupIndex,
                tmnxMobPdnApnAaGrpPartIndex
            }
    STATUS      current
    DESCRIPTION
        "The group of objects supporting the management of the Packet Data 
         Network Gateway (PGW) AA group on the Alcatel-Lucent 7750 
         Mobile Gateway systems in 3.0 release."
    ::= { tmnxMobPdnGroups 16 }

tmnxMobPdnRefPointV3v0Group  OBJECT-GROUP
    OBJECTS {
                tmnxMobPdnGaStatTxNodeAlRequests,
                tmnxMobPdnGaStatRxNodeAlResps,
                tmnxMobPdnGaStatNodeAlReqRetried,
                tmnxMobPdnGaStatCdrsTx,
                tmnxMobPdnGaStatCdrsRx,
                tmnxMobPdnGaPeerLastChanged,
                tmnxMobPdnGaPeerCreateTime,
                tmnxMobPdnGaPeerPathMgmtState,
                tmnxMobPdnGaPeerDetailState,
                tmnxMobPdnGaStatTxCdrPlmnChange,
                tmnxMobPdnGaStatTxCdrSerNdChLmt,
                tmnxMobPdnGaStatTxVerNotSupp,
                tmnxMobPdnGpPeerLastChanged,
                tmnxMobPdnGpPeerCreateTime,
                tmnxMobPdnGpPeerPathMgmtState,
                tmnxMobPdnGpPeerGatewayId,
                tmnxMobPdnGpPeerType,
                tmnxMobPdnGpStatCreatePdpReq,
                tmnxMobPdnGpStatCreatePdpRsp,
                tmnxMobPdnGpStatDeletePdpReq,
                tmnxMobPdnGpStatDeletePdpRsp,
                tmnxMobPdnGpStatModifyPdpReq,
                tmnxMobPdnGpStatModifyPdpRsp,
                tmnxMobPdnGpStatRxEchoRequests,
                tmnxMobPdnGpStatTxEchoResponses,
                tmnxMobPdnGpStatTxEchoRequests,
                tmnxMobPdnGpStatRxEchoResponses,
                tmnxMobPdnGpStatRxErrorsIndCnt,
                tmnxMobPdnGpStatTxErrorsIndCnt,
                tmnxMobPdnGpStatRxMalformedPkts,
                tmnxMobPdnGpStatRxUnknownPkts,
                tmnxMobPdnGpStatRxMissingIePkts,
                tmnxMobPdnGpStatPeerRestarts,
                tmnxMobPdnGpStatPeerRestrtCount,
                tmnxMobPdnGpStatPathMgmtFails,
                tmnxMobPdnS2aPeerLastChanged,
                tmnxMobPdnS2aPeerCreateTime,
                tmnxMobPdnS2aPeerPathMgmtState,
                tmnxMobPdnS2aPeerGatewayId,
                tmnxMobPdnS2aPeerType,
                tmnxMobPdnS2aStatPeerRestart,
                tmnxMobPdnS2aStatPathMgmtFail,
                tmnxMobPdnS2aStatPeerRestartCnt,
                tmnxMobPdnS2aStatHeartBeatReqTx,
                tmnxMobPdnS2aStatHeartBeatReqRx,
                tmnxMobPdnS2aStatHeartBeatRespTx,
                tmnxMobPdnS2aStatHeartBeatRespRx,
                tmnxMobPdnS2aStatPbu,
                tmnxMobPdnS2aStatBri,
                tmnxMobPdnS2aStatRxMalformedPkts,
                tmnxMobPdnS2aStatRxMissingIePkts,
                tmnxMobPdnS2aStatRxUnknownPkts,
                tmnxMobPdnS2aStatPbaFailure,
                tmnxMobPdnS2aStatBraFailure,
                tmnxMobPdnS2aStatPbaSuccess,
                tmnxMobPdnS2aStatBraSuccess,
                tmnxMobPdnGaStatTxCdrMgmtInterv,
                tmnxMobPdnS2aStatHBCompatible,
                tmnxMobPdnS2aPeerHBCompatible
            }
    STATUS      current
    DESCRIPTION
        "The group of objects supporting management of the Packet Data Network
         Gateway (PGW) reference point statistics on the Alcatel-Lucent 
         7750 Mobile Gateway systems in 3.0 release."
    ::= { tmnxMobPdnGroups 17 }

tmnxMobPdnChargingV3Group  OBJECT-GROUP
    OBJECTS {
                tmnxMobPdnCdrType
            }
    STATUS      current
    DESCRIPTION
        "The group of objects supporting the charging applications on the 
        Alcatel-Lucent 7750 Mobile Gateway systems in 3.0 release."
    ::= { tmnxMobPdnGroups 18 }

tmnxMobPdnGgsnV3Group  OBJECT-GROUP
    OBJECTS {
         tmnxMobPdnGnPeerList,
         tmnxMobPdnGpLastChanged,
         tmnxMobPdnGpGtpcIfVRtrId,
         tmnxMobPdnGpGtpcIfIndex,
         tmnxMobPdnGpGtpuIfVRtrId,
         tmnxMobPdnGpGtpuIfIndex,
         tmnxMobPdnGpGtpcProfile,
         tmnxMobPdnGpGtpuProfile,
         tmnxMobPdnGpPeerList
    }
    STATUS      current
    DESCRIPTION
        "The group of objects supporting management of the Gateway GPRS Service 
         Node (GGSN) on the Packet Data Network Gateway (PGW) on the 
         Alcatel-Lucent 7750 Mobile Gateway systems in 3.0 release."
    ::= { tmnxMobPdnGroups 19 }

tmnxMobPdnStatV3Group  OBJECT-GROUP
    OBJECTS {
                tmnxMobPdnProcAttachPiggyBack,
                tmnxMobPdnStatHomers,
                tmnxMobPdnStatVisitors,
                tmnxMobPdneHRPDAttachSuccess,
                tmnxMobPdneHRPDAttachFailure, 
                tmnxMobPdneHRPDDetachSuccess, 
                tmnxMobPdneHRPDDetachFailure,
                tmnxMobPdneHRPDToLTEHandOverSucc, 
                tmnxMobPdneHRPDToLTEHandOverFail,
                tmnxMobPdnLTEToeHRPDHandOverSucc,
                tmnxMobPdnLTEToeHRPDHandOverFail, 
                tmnxMobPdnInterHSGWHandOvrSucc, 
                tmnxMobPdnInterHSGWHandOvrFail,
                tmnxMobPdnStatHSSStaticIpv4Sess,
                tmnxMobPdnStatHSSStaticIpv6Sess,
                tmnxMobPdnStatHSSSttIpv4v6Sess,
                tmnxMobPdnStateHRPDPDNSess,
                tmnxMobPdnStatLTEPDNSess,
                tmnxMobPdnStat2G3GPDNSess,
                tmnxMobPdnStatNumSuspendedPDN,
                tmnxMobPdnProcPDNSuspendNotice,
                tmnxMobPdnProcPDNResumeNotice,
                tmnxMobPdnProcPDNIRSRP,
                tmnxMobPdnProcEmergncyAttachSuc,
                tmnxMobPdnStatEmergencyPdnSess,
                tmnxMobPdnProcMmeDedBrDeActiv,
                tmnxMobPdnProcMmeDedBrDeAcFails,
                tmnxMobPdnProcSessDeactDueToSt,
                tmnxMobPdnProcSessDeactDueToIt,
                tmnxMobPdnInterRat3gToEutranSucc,
                tmnxMobPdnInterRat3gToEutranFail,
                tmnxMobPdnInterRatEutranTo3gSucc,
                tmnxMobPdnInterRatEutranTo3gFail,
                tmnxMobPdnStatRfPeer,
                tmnxMobPdnStatRfAcctStartBuf,
                tmnxMobPdnStatRfAcctIntBuf,
                tmnxMobPdnStatRfAcctStopBuf,
                tmnxMobPdneHRPDSessDeactSessTO,
                tmnxMobPdneHRPDSessDeactIdleTO
            }
    STATUS      current
    DESCRIPTION
        "The group of objects supporting management of the Packet Data Network
         Gateway (PGW) status on the Alcatel-Lucent 7750 Mobile Gateway 
         systems in 3.0 release."
    ::= { tmnxMobPdnGroups 20 }

tmnxMobPdnRadiusStatsV3v0Group  OBJECT-GROUP
    OBJECTS {
         tmnxMobPdnRadPeerLastChanged,
         tmnxMobPdnRadPeerCreateTime,
         tmnxMobPdnRadPeerPathMgmtState,
         tmnxMobPdnRadPeerDetailState,
         tmnxMobPdnRadStatLastChanged,
         tmnxMobPdnRadStatAccessReqTx,
         tmnxMobPdnRadStatAccessAcceptRx,
         tmnxMobPdnRadStatAccessRejectRx,
         tmnxMobPdnRadStatAcctReqStartTx,
         tmnxMobPdnRadStatAcctReqIntrmTx,
         tmnxMobPdnRadStatAcctReqStopTx,
         tmnxMobPdnRadStatAcctResponseRx,
         tmnxMobPdnRadStatMandAttrMissing,
         tmnxMobPdnRadStatMandAttrErrors,
         tmnxMobPdnRadStatUnsupportedAttr,
         tmnxMobPdnRadStatOptionalAttrErr,
         tmnxMobPdnRadStatAuthError,
         tmnxMobPdnRadStatUnexpectedCode,
         tmnxMobPdnRadStatRespTimeBelow1,
         tmnxMobPdnRadStatRespTime1to4,
         tmnxMobPdnRadStatRespTimeAbove4,
         tmnxMobPdnRadStatRetries,
         tmnxMobPdnRadStatPrFinalTimeout,
         tmnxMobPdnRadStatDiscReqRx,
         tmnxMobPdnRadStatDiscAckTx,
         tmnxMobPdnRadStatDiscNakTx,
         tmnxMobPdnRadStatDiscMandAtrMiss,
         tmnxMobPdnRadStatDiscUnsupprAttr,
         tmnxMobPdnRadStatDiscSessNotFnd,
         tmnxMobPdnRadStatDiscAuthError,
         tmnxMobPdnRadStatDiscUnexpcCode,
         tmnxMobPdnRadStatMsgFinalTimeout
    }
    STATUS      current
    DESCRIPTION
        "The group of objects supporting management of the Radius
         statistics on the Packet Data Network Gateway (PGW) on the
         Alcatel-Lucent 7750 Mobile Gateway systems."
    ::= { tmnxMobPdnGroups 21 }

tmnxMobPdnS2aV3v0Group  OBJECT-GROUP
    OBJECTS {
              tmnxMobPdnS2aLastChanged,
              tmnxMobPdnS2aPeerList,
              tmnxMobPdnS2aIfPmipv6RtrId,
              tmnxMobPdnS2aIfPmipv6Interface,
              tmnxMobPdnS2aIfPmipv6Profile
    }
    STATUS      current
    DESCRIPTION 
          "The group of objects supporting management of S2a interface on 
          the Packet Data Network Gateway (PGW) on the Alcatel-Lucent
          7750 Mobile Gateway systems."
   ::= {tmnxMobPdnGroups 22}

tmnxMobPdnObsoletedV3Group  OBJECT-GROUP
    OBJECTS {
                tmnxMobPdnApnAuthAcctSupImsi
            }
    STATUS      current
    DESCRIPTION
        "The group of obsoleted objects which are no longer supported in the 3.0 
         release on the Alcatel-Lucent 7750 Mobile Gateway Systems."
    ::= { tmnxMobPdnGroups 23 }

tmnxMobPdnThresV3v0Group  OBJECT-GROUP
    OBJECTS {
          tmnxMobPdnThresLastChanged,
          tmnxMobPdnThresBrMgmtLmtUe,
          tmnxMobPdnThresBrMgmtLmtBr,
          tmnxMobPdnThresBrMgmtLmtDefBr,
          tmnxMobPdnThresBrMgmtLmtDedBr,
          tmnxMobPdnThresBrMgmtLmtActBr,
          tmnxMobPdnThresBrMgmtLmtUePgd,
          tmnxMobPdnThresBrMgmtCfsAttch,
          tmnxMobPdnThresBrMgmtCfsDedBr,
          tmnxMobPdnThresBrMgmtCfsReloc,
          tmnxMobPdnThresBrMgmtCffAttch,
          tmnxMobPdnThresBrMgmtCffDedBr,
          tmnxMobPdnThresBrMgmtCffHdOver,
          tmnxMobPdnThresBrMgmtCffSrUnavl,
          tmnxMobPdnThresBrTrfcThrptUL,
          tmnxMobPdnThresBrTrfcThrptDL,
          tmnxMobPdnThresBrTrfcAspFail,
          tmnxMobPdnThresBrTrfcBrBdvErr,
          tmnxMobPdnThresPthMgmtS5Fail,
          tmnxMobPdnThresPthMgmtS5Restart,
          tmnxMobPdnThresPthMgmtS5NoResp,
          tmnxMobPdnThresPthMgmtS5Peer,
          tmnxMobPdnThresPthMgmtS8Peer,
          tmnxMobPdnThresPthMgmtGxFail,
          tmnxMobPdnThresPthMgmtRfFail
    }
    STATUS      current
    DESCRIPTION
        "The group of objects supporting management of  the set of thresholds  
         of the Packet Data Network Gateway (PGW) on the Alcatel-Lucent 7750 
         Mobile Gateway systems."
    ::= { tmnxMobPdnGroups 24 }

tmnxMobPdnV3v0Group  OBJECT-GROUP
    OBJECTS {
               tmnxMobPdnHttpRedirect,
               tmnxMobPdnS8TableLastChanged,
               tmnxMobPdnS8LastChanged,
               tmnxMobPdnS8PeerList,
               tmnxMobPdnS8GtpcIfVRtrId,
               tmnxMobPdnS8GtpcIfIndex,
               tmnxMobPdnS8GtpuIfVRtrId,
               tmnxMobPdnS8GtpuIfIndex,
               tmnxMobPdnS8GtpcProfile,
               tmnxMobPdnS8GtpuProfile,
               tmnxMobPdnS8DualStackPref,
               tmnxMobPdnDefAppProfile
            }
    STATUS      current
    DESCRIPTION
        "The group of objects supporting management of the Packet Data Network
         Gateway (PGW) on the Alcatel-Lucent 7750 Mobile Gateway systems in 
         3.0 release."
   ::= {tmnxMobPdnGroups 25}

tmnxMobPdnApnV3v5Group  OBJECT-GROUP
    OBJECTS {
                tmnxMobPdnApnRowStatus,
                tmnxMobPdnApnLastChanged,
                tmnxMobPdnApnAdminState,
                tmnxMobPdnApnOperState,
                tmnxMobPdnApnGracefulShutTimeout,
                tmnxMobPdnApnType,
                tmnxMobPdnApnVRtrId,
                tmnxMobPdnApnVirtualApnName,
                tmnxMobPdnApnPdnTypeIpv4,
                tmnxMobPdnApnPdnTypeIpv6,
                tmnxMobPdnApnPdnTypeIpv4v6,
                tmnxMobPdnApnPdnAllocType,
                tmnxMobPdnApnPdnRestrictionType,
                tmnxMobPdnApnAllowMultiplePdns,
                tmnxMobPdnApnSelectSubscribed,
                tmnxMobPdnApnSelectMsProvided,
                tmnxMobPdnApnSelectNwProvided,
                tmnxMobPdnApnIpAllocLocalPool,
                tmnxMobPdnApnIpAllocHssStatic,
                tmnxMobPdnApnIpAllocAaa,
                tmnxMobPdnApnIpAllocDhcpProxy,
                tmnxMobPdnApnIpAllocDhcpRelay,
                tmnxMobPdnApnIpAllocDhcpServer,
                tmnxMobPdnApnPcrfDynamicPcc,
                tmnxMobPdnApnPcrfPriDiameterPeer,
                tmnxMobPdnApnPcrfSecDiameterPeer,
                tmnxMobPdnApnUplinkQciPolName,
                tmnxMobPdnApnDownlinkQciPolName,
                tmnxMobPdnApnAggrRateUplink,
                tmnxMobPdnApnAggrRateDownlink,
                tmnxMobPdnApnIdleTimeout,
                tmnxMobPdnApnSessionTimeout,
                tmnxMobPdnApnRejectForeignSub,
                tmnxMobPdnApnBlockedPlmnList,
                tmnxMobPdnApnUliReporting,
                tmnxMobPdnApnExtLastChanged,
                tmnxMobPdnApnDnsServerV4AddrType,
                tmnxMobPdnApnDnsServerV4Addr,
                tmnxMobPdnApnDnsServerV6AddrType,
                tmnxMobPdnApnDnsServerV6Addr,
                tmnxMobPdnApnDhcpRelayV4RouterId,
                tmnxMobPdnApnDhcpRlyV4GiAddrType,
                tmnxMobPdnApnDhcpRelayV4GiAddr,
                tmnxMobPdnApnDhcpRelayV6RouterId,
                tmnxMobPdnApnDhcpRlyV6GiAddrType,
                tmnxMobPdnApnDhcpRelayV6GiAddr,
                tmnxMobPdnApnDhcpProxyV4RouterId,
                tmnxMobPdnApnDhcpPxyV4GiAddrType,
                tmnxMobPdnApnDhcpProxyV4GiAddr,
                tmnxMobPdnApnDhcpProxyV6RouterId,
                tmnxMobPdnApnDhcpPxyV6GiAddrType,
                tmnxMobPdnApnDhcpProxyV6GiAddr,
                tmnxMobPdnApnPcoDnsV4PriAddrType,
                tmnxMobPdnApnPcoDnsV4PriAddr,
                tmnxMobPdnApnPcoDnsV4SecAddrType,
                tmnxMobPdnApnPcoDnsV4SecAddr,
                tmnxMobPdnApnPcoDnsV6PriAddrType,
                tmnxMobPdnApnPcoDnsV6PriAddr,
                tmnxMobPdnApnPcoDnsV6SecAddrType,
                tmnxMobPdnApnPcoDnsV6SecAddr,
                tmnxMobPdnApnPcoPcscfV4PriAdrTyp,
                tmnxMobPdnApnPcoPcscfV4PriAddr,
                tmnxMobPdnApnPcoPcscfV6PriAdrTyp,
                tmnxMobPdnApnPcoPcscfV6PriAddr,
                tmnxMobPdnApnPcoNbnsV4PriAdrType,
                tmnxMobPdnApnPcoNbnsV4PriAddr,
                tmnxMobPdnApnPcoNbnsV4SecAdrType,
                tmnxMobPdnApnPcoNbnsV4SecAddr,
                tmnxMobPdnApnPcoNbnsV6PriAdrType,
                tmnxMobPdnApnPcoNbnsV6PriAddr,
                tmnxMobPdnApnPcoNbnsV6SecAdrType,
                tmnxMobPdnApnPcoNbnsV6SecAddr,
                tmnxMobPdnApnExt2LastChanged,
                tmnxMobPdnApnChrgProfileHome,
                tmnxMobPdnApnChrgProfileVisiting,
                tmnxMobPdnApnChrgProfileRoaming,
                tmnxMobPdnApnChrgCcIgnoreAny,
                tmnxMobPdnApnChrgCcIgnoreHome,
                tmnxMobPdnApnChrgCcIgnoreVisit,
                tmnxMobPdnApnChrgCcIgnoreRoaming,
                tmnxMobPdnApnCdfPriDiaPeer,
                tmnxMobPdnApnCdfSecDiaPeer,
                tmnxMobPdnApnPreAuthType,
                tmnxMobPdnApnPreAuthUserName,
                tmnxMobPdnApnAuthType,
                tmnxMobPdnApnAuthUserName,
                tmnxMobPdnApnAcctType,
                tmnxMobPdnApnAcctUserName,
                tmnxMobPdnApnAcctInterimReport,
                tmnxMobPdnApnIpPoolRowStatus,
                tmnxMobPdnApnBasePolRowStatus,
                tmnxMobPdnApnUmtsQosPolName,
                tmnxMobPdnApnChrgCcReject,
                tmnxMobPdnApnAuthServerGroup,
                tmnxMobPdnApnAcctServerGroup,
                tmnxMobPdnApnWaitAccounting,
                tmnxMobPdnApnPreAuthServerGroup,
                tmnxMobPdnApnAuthSupImsi,
                tmnxMobPdnApnAcctSupImsi,
                tmnxMobPdnApnPreAuthSupImsi,
                tmnxMobPdnApnExt3LastChanged        
            }
    STATUS      current
    DESCRIPTION
        "The group of objects supporting management of a Access Point Name 
         (APN) on a Packet Data Network Gateway (PGW) on the Alcatel-Lucent 
         7750 Mobile Gateway systems."
    ::= { tmnxMobPdnGroups 26 }

tmnxMobPdnAcctStatsV3Group  OBJECT-GROUP
    OBJECTS {
                tmnxMobPdnBcAcctGaChargingId,
                tmnxMobPdnBcAcctGaUlSustRate,
                tmnxMobPdnBcAcctGaDlSustRate,
                tmnxMobPdnBcAcctGaAggrUlPkts,
                tmnxMobPdnBcAcctGaAggrUlPktsLow,
                tmnxMobPdnBcAcctGaAggrUlPktsHigh,
                tmnxMobPdnBcAcctGaAggrDlPkts,
                tmnxMobPdnBcAcctGaAggrDlPktsLow,
                tmnxMobPdnBcAcctGaAggrDlPktsHigh,
                tmnxMobPdnBcAcctGaAggrUlByts,
                tmnxMobPdnBcAcctGaAggrUlBytsLow,
                tmnxMobPdnBcAcctGaAggrUlBytsHigh,
                tmnxMobPdnBcAcctGaAggrDlByts,
                tmnxMobPdnBcAcctGaAggrDlBytsLow,
                tmnxMobPdnBcAcctGaAggrDlBytsHigh,
                tmnxMobPdnBcAcctGaNumPartCdrs,
                tmnxMobPdnBcAcctGaNumContainers,
                tmnxMobPdnBcAcctGaNumMaxChanges,
                tmnxMobPdnBcAcctGaNumRgs,
                tmnxMobPdnBcAcctGaNumOfRgSvcId,
                tmnxMobPdnBcGaChrgOnlnCharging,
                tmnxMobPdnBcGaChrgOfflnCharging,
                tmnxMobPdnBcGaChrgUlPkts,
                tmnxMobPdnBcGaChrgUlPktsLow,
                tmnxMobPdnBcGaChrgUlPktsHigh,
                tmnxMobPdnBcGaChrgDlPkts,
                tmnxMobPdnBcGaChrgDlPktsLow,
                tmnxMobPdnBcGaChrgDlPktsHigh,
                tmnxMobPdnBcGaChrgUlByts,
                tmnxMobPdnBcGaChrgUlBytsLow,
                tmnxMobPdnBcGaChrgUlBytsHigh,
                tmnxMobPdnBcGaChrgDlByts,
                tmnxMobPdnBcGaChrgDlBytsLow,
                tmnxMobPdnBcGaChrgDlBytsHigh,
                tmnxMobPdnBcAcctGyChargingId,
                tmnxMobPdnBcAcctGyUlSustRate,
                tmnxMobPdnBcAcctGyDlSustRate,
                tmnxMobPdnBcAcctGyAggrUlPkts,
                tmnxMobPdnBcAcctGyAggrUlPktsLow,
                tmnxMobPdnBcAcctGyAggrUlPktsHigh,
                tmnxMobPdnBcAcctGyAggrDlPkts,
                tmnxMobPdnBcAcctGyAggrDlPktsLow,
                tmnxMobPdnBcAcctGyAggrDlPktsHigh,
                tmnxMobPdnBcAcctGyAggrUlByts,
                tmnxMobPdnBcAcctGyAggrUlBytsLow,
                tmnxMobPdnBcAcctGyAggrUlBytsHigh,
                tmnxMobPdnBcAcctGyAggrDlByts,
                tmnxMobPdnBcAcctGyAggrDlBytsLow,
                tmnxMobPdnBcAcctGyAggrDlBytsHigh,
                tmnxMobPdnBcAcctGyNumRedirection,
                tmnxMobPdnBcAcctGyLastRedctTime,
                tmnxMobPdnBcAcctGyNumCreditsRepl,
                tmnxMobPdnBcAcctGyLstCrdReplTime,
                tmnxMobPdnBcAcctGyNumRgs,
                tmnxMobPdnBcAcctGyNumOfRgSvcId,
                tmnxMobPdnBcGyChrgTimeGranted,
                tmnxMobPdnBcGyChrgTimeUsed,
                tmnxMobPdnBcGyChrgGrntTtlOct,
                tmnxMobPdnBcGyChrgGrntTtlOctLow,
                tmnxMobPdnBcGyChrgGrntTtlOctHigh,
                tmnxMobPdnBcGyChrgGrntInOct,
                tmnxMobPdnBcGyChrgGrntInOctLow,
                tmnxMobPdnBcGyChrgGrntInOctHigh,
                tmnxMobPdnBcGyChrgGrntOutOct,
                tmnxMobPdnBcGyChrgGrntOutOctLow,
                tmnxMobPdnBcGyChrgGrntOutOctHigh,
                tmnxMobPdnBcGyChrgUsedTtlOct,
                tmnxMobPdnBcGyChrgUsedTtlOctLow,
                tmnxMobPdnBcGyChrgUsedTtlOctHigh,
                tmnxMobPdnBcGyChrgUsedInOct,
                tmnxMobPdnBcGyChrgUsedInOctLow,
                tmnxMobPdnBcGyChrgUsedInOctHigh,
                tmnxMobPdnBcGyChrgUsedOutOct,
                tmnxMobPdnBcGyChrgUsedOutOctLow,
                tmnxMobPdnBcGyChrgUsedOutOctHigh,
                tmnxMobPdnBcAcctRfChargingId,
                tmnxMobPdnBcAcctRfUlSustRate,
                tmnxMobPdnBcAcctRfDlSustRate,
                tmnxMobPdnBcAcctRfAggrUlPkts,
                tmnxMobPdnBcAcctRfAggrUlPktsLow,
                tmnxMobPdnBcAcctRfAggrUlPktsHigh,
                tmnxMobPdnBcAcctRfAggrDlPkts,
                tmnxMobPdnBcAcctRfAggrDlPktsLow,
                tmnxMobPdnBcAcctRfAggrDlPktsHigh,
                tmnxMobPdnBcAcctRfAggrUlByts,
                tmnxMobPdnBcAcctRfAggrUlBytsLow,
                tmnxMobPdnBcAcctRfAggrUlBytsHigh,
                tmnxMobPdnBcAcctRfAggrDlByts,
                tmnxMobPdnBcAcctRfAggrDlBytsLow,
                tmnxMobPdnBcAcctRfAggrDlBytsHigh,
                tmnxMobPdnBcAcctRfNumInterimSent,
                tmnxMobPdnBcAcctRfNumRgs,
                tmnxMobPdnBcAcctRfNumOfRgSvcId,
                tmnxMobPdnPcAcctRfAggrUlPkts,
                tmnxMobPdnPcAcctRfAggrUlPktsLow,
                tmnxMobPdnPcAcctRfAggrUlPktsHigh,
                tmnxMobPdnPcAcctRfAggrDlPkts,
                tmnxMobPdnPcAcctRfAggrDlPktsLow,
                tmnxMobPdnPcAcctRfAggrDlPktsHigh,
                tmnxMobPdnPcAcctRfAggrUlByts,
                tmnxMobPdnPcAcctRfAggrUlBytsLow,
                tmnxMobPdnPcAcctRfAggrUlBytsHigh,
                tmnxMobPdnPcAcctRfAggrDlByts,
                tmnxMobPdnPcAcctRfAggrDlBytsLow,
                tmnxMobPdnPcAcctRfAggrDlBytsHigh,
                tmnxMobPdnPcAcctRfUlAvgRate,
                tmnxMobPdnPcAcctRfDlAvgRate,
                tmnxMobPdnPcAcctRfNumInterimSent,
                tmnxMobPdnPcAcctRfNumRgs,
                tmnxMobPdnPcAcctRfNumOfRgSvcId,
                tmnxMobPdnPcRfChrgOnlnCharging,
                tmnxMobPdnPcRfChrgOfflnCharging,
                tmnxMobPdnPcRfChrgUlPkts,
                tmnxMobPdnPcRfChrgUlPktsLow,
                tmnxMobPdnPcRfChrgUlPktsHigh,
                tmnxMobPdnPcRfChrgDlPkts,
                tmnxMobPdnPcRfChrgDlPktsLow,
                tmnxMobPdnPcRfChrgDlPktsHigh,
                tmnxMobPdnPcRfChrgUlByts,
                tmnxMobPdnPcRfChrgUlBytsLow,
                tmnxMobPdnPcRfChrgUlBytsHigh,
                tmnxMobPdnPcRfChrgDlByts,
                tmnxMobPdnPcRfChrgDlBytsLow,
                tmnxMobPdnPcRfChrgDlBytsHigh,
                tmnxMobPdnBcGyChrgRatingGrpState,
                tmnxMobPdnBcGyChrgTimeBasedRep,
                tmnxMobPdnBcGyChrgVolumeBasedRep,
                tmnxMobPdnBcGyChrgQctPresent,
                tmnxMobPdnBcGyChrgQctGranted,
                tmnxMobPdnBcGyChrgQhtPresent,
                tmnxMobPdnBcGyChrgQhtGranted,
                tmnxMobPdnBcGyChrgQhtRemaining,
                tmnxMobPdnBcGyChrgQvtPresent,
                tmnxMobPdnBcGyChrgQvtRemaining,
                tmnxMobPdnBcGyChrgTtcPresent,
                tmnxMobPdnBcGyChrgTarrifTimeChng,
                tmnxMobPdnBcGyChrgFuiPresent,
                tmnxMobPdnBcGyChrgOnlineEnabled,
                tmnxMobPdnBcGyChrgTimeThreshold,
                tmnxMobPdnBcGyChrgVolThreshold,
                tmnxMobPdnBcGyChrgTrigger,
                tmnxMobPdnBcGyChrgActvThreshold,
                tmnxMobPdnBcGyChrgRedServerType,
                tmnxMobPdnBcGyChrgRedServer,
                tmnxMobPdnBcGyChrgBillingMethod,
                tmnxMobPdnBcGyChrgReportingLevel,
                tmnxMobPdnBcGyChrgResultCode
            }
    STATUS      current
    DESCRIPTION
        "The group of objects supporting management of the Packet Data Network 
         Gateway (PGW) accounting statistics on the Alcatel-Lucent 7750 Mobile
         Gateway systems."
    ::= { tmnxMobPdnGroups 27 }

tmnxMobPdnBcV3v5Group  OBJECT-GROUP
    OBJECTS {
                tmnxMobPdnKeyType,
                tmnxMobPdnPcImsiAuthStatus,
                tmnxMobPdnPcImeiStr,
                tmnxMobPdnPcImsiStr,
                tmnxMobPdnUeImsiStr,
                tmnxMobPdnPcSessConfigTime,
                tmnxMobPdnPcSessRemExpTime,
                tmnxMobPdnPcSessTimeDerivedFrom,
                tmnxMobPdnPcIdleConfigTime,
                tmnxMobPdnPcIdleRemExpTime,
                tmnxMobPdnPcIdleTimeDerivedFrom,
                tmnxMobPdnPcRefPointType,
                tmnxMobPdnBcRefPointType,
                tmnxMobPdnBcChargingChar,
                tmnxMobPdnBcQosBytes
            }
    STATUS      current
    DESCRIPTION
        "The group of objects supporting management of the Packet Data Network 
         Gateway (PGW) bearer contexts on the Alcatel-Lucent 7750 Mobile Gateway 
         systems."
    ::= { tmnxMobPdnGroups 28 }

tmnxMobPdnRefPointV4v0Group  OBJECT-GROUP
    OBJECTS {
                tmnxMobPdnGxStatRxCcaInitialFail,
                tmnxMobPdnGxStatRxCcaUpdateFail,
                tmnxMobPdnGxStatRxCcaTermFail,
                tmnxMobPdnGxStatReTxCcrInitial,
                tmnxMobPdnGxStatReTxCcrUpdate,
                tmnxMobPdnGxStatReTxCcrTerm
            }
    STATUS      current
    DESCRIPTION
        "The group of objects supporting management of the Packet Data Network
         Gateway (PGW) reference point statistics on the Alcatel-Lucent 
         7750 Mobile Gateway systems in R4.0 release."
    ::= { tmnxMobPdnGroups 29 }

tmnxMobPdnOnlineChargV4v0Group  OBJECT-GROUP
    OBJECTS {
         tmnxMobPdnGyOcsTableLastChanged,
         tmnxMobPdnGyDiaSession,
         tmnxMobPdnGyOcsSelIdType,
         tmnxMobPdnGyOcsSelIdMappingStyle,
         tmnxMobPdnGyOcsRowStatus,
         tmnxMobPdnGyOcsLastChanged,
         tmnxMobPdnGyOcsUeStartId,
         tmnxMobPdnGyOcsUeEndId,
         tmnxMobPdnGyOcsPriDiaPeer,
         tmnxMobPdnGyOcsSecDiaPeer,
         tmnxMobPdnGyOcsDccaProf
    }
    STATUS      current
    DESCRIPTION
        "The group of objects supporting management of the Online Charging on
         the Packet Data Network Gateway (PGW) on the Alcatel-Lucent 7750 Mobile
         Gateway systems in 4.0 release."
    ::= { tmnxMobPdnGroups 30 }

tmnxMobPdnApnV4v0Group  OBJECT-GROUP
    OBJECTS {
                tmnxMobPdnApnPcrfDynPccFHSession
            }
    STATUS      current
    DESCRIPTION
        "The group of objects supporting management of a Access Point Name 
         (APN) on a Packet Data Network Gateway (PGW) on the Alcatel-Lucent 
         7750 Mobile Gateway systems in R4.0 release."
    ::= { tmnxMobPdnGroups 31 }

tmnxMobPdnS6bV4v0Group OBJECT-GROUP
    OBJECTS {
                tmnxMobPdnS6bLastChanged,
                tmnxMobPdnS6bTransactionTimer,
                tmnxMobPdnS6bRetryCount
            }        

    STATUS    current
    DESCRIPTION
          "The group of objects supporting management of S6b interface on 
          the Packet Data Network Gateway (PGW) on the Alcatel-Lucent
          7750 Mobile Gateway systems."
   ::= {tmnxMobPdnGroups 32}

tmnxMobPdnV4v0Group  OBJECT-GROUP
    OBJECTS {
               tmnxMobPdnChargingAvpDiag,
               tmnxMobPdnRfSuppVendorAvps
            }
    STATUS      current
    DESCRIPTION
        "The group of objects supporting management of the Packet Data Network
         Gateway (PGW) on the Alcatel-Lucent 7750 Mobile Gateway systems in 
         4.0 release."
   ::= {tmnxMobPdnGroups 33}

END
