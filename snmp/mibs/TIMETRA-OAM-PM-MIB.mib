TIMETRA-OAM-PM-MIB DEFINITIONS ::= BEGIN

IMPORTS

    Dot1agCfmMepIdOrZero
    FROM IEEE8021-CFM-MIB

    InetAddress, InetAddressPrefixLength, InetAddressType, InetPortNumber
    FROM INET-ADDRESS-MIB

    MODULE-COMPLIANCE, NOTIFICATION-GROUP, OBJECT-GROUP
    FROM SNMPv2-CONF

    MODULE-IDENTITY, NOTIFICATION-TYPE, OBJECT-TYPE, Counter32, Counter64,
    Unsigned32
    FROM SNMPv2-SMI

    DateAndTime, MacAddress, RowStatus, TEXTUAL-CONVENTION, TimeStamp,
    TruthValue
    FROM SNMPv2-TC

    timetraSRMIBModules, tmnxSRConfs, tmnxSRNotifyPrefix, tmnxSRObjs
    FROM TIMETRA-GLOBAL-MIB

    svcId
    FROM TIMETRA-SERV-MIB

    TFCName, TItemDescription, TNamedItem, TNamedItemOrEmpty,
    TmnxEnabledDisabled, TmnxEnabledDisabledOrNA, TmnxOperState, TProfile
    FROM TIMETRA-TC-MIB
    ;

timetraOamPmMIBModule  MODULE-IDENTITY
    LAST-UPDATED
        "201307040000Z"
    ORGANIZATION
        "Alcatel-Lucent"
    CONTACT-INFO
        "Alcatel-Lucent SROS Support
         Web: http://support.alcatel-lucent.com"
    DESCRIPTION
        "This document is the SNMP MIB module for the Alcatel-Lucent SROS
         implementation of Service OAM Performance Monitoring.

         Copyright 2013-2014 Alcatel-Lucent. All rights reserved.
         Reproduction of this document is authorized on the condition that the
         foregoing copyright notice is included.

         This SNMP MIB module (Specification) embodies Alcatel-Lucent's
         proprietary intellectual property.  Alcatel-Lucent retains all title
         and ownership in the Specification, including any revisions.

         Alcatel-Lucent grants all interested parties a non-exclusive license to
         use and distribute an unmodified copy of this Specification in
         connection with management of Alcatel-Lucent products, and without fee,
         provided this copyright notice and license appear on all copies.

         This Specification is supplied `as is', and Alcatel-Lucent makes no
         warranty, either express or implied, as to the use, operation,
         condition, or performance of the Specification."
    REVISION
        "201307040000Z"
    DESCRIPTION
        "Initial release of the TIMETRA-OAM-PM-MIB (SROS release 12.0 R1)."
    ::= { timetraSRMIBModules 92 }

-- #############################################################################
-- Object Identifiers
-- #############################################################################
tmnxOamPmObjs                  OBJECT IDENTIFIER ::= { tmnxSRObjs 92 }
  tmnxOamPmCfgObjs             OBJECT IDENTIFIER ::= { tmnxOamPmObjs 1 }
    tmnxOamPmCfgScalarObjs     OBJECT IDENTIFIER ::= { tmnxOamPmCfgObjs 1 }
    tmnxOamPmTableLastChgObjs  OBJECT IDENTIFIER ::= { tmnxOamPmCfgObjs 2 }
    tmnxOamPmCfgTableObjs      OBJECT IDENTIFIER ::= { tmnxOamPmCfgObjs 3 }
  tmnxOamPmStatsObjs           OBJECT IDENTIFIER ::= { tmnxOamPmObjs 2 }
    tmnxOamPmStatsScalarObjs   OBJECT IDENTIFIER ::= { tmnxOamPmStatsObjs 1 }
    tmnxOamPmStatsTableObjs    OBJECT IDENTIFIER ::= { tmnxOamPmStatsObjs 2 }
  tmnxOamPmNotificationObjs    OBJECT IDENTIFIER ::= { tmnxOamPmObjs 3 }

tmnxOamPmNotifyPrefix          OBJECT IDENTIFIER ::= { tmnxSRNotifyPrefix 92 }
  tmnxOamPmNotifications       OBJECT IDENTIFIER ::= { tmnxOamPmNotifyPrefix 0 }

tmnxOamPmConformance           OBJECT IDENTIFIER ::= { tmnxSRConfs 92 }
  tmnxOamPmCompliances         OBJECT IDENTIFIER ::= { tmnxOamPmConformance 1 }
  tmnxOamPmObjGroups           OBJECT IDENTIFIER ::= { tmnxOamPmConformance 2 }
    tmnxOamPmV12v0ObjGroups    OBJECT IDENTIFIER ::= { tmnxOamPmObjGroups 1 }
  tmnxOamPmNotifGroups         OBJECT IDENTIFIER ::= { tmnxOamPmConformance 3 }
    tmnxOamPmV12v0NotifGroups  OBJECT IDENTIFIER ::= { tmnxOamPmNotifGroups 1 }

-- #############################################################################
-- Textual Conventions
-- #############################################################################

TmnxOamPmBinGroupId              ::= TEXTUAL-CONVENTION
    STATUS      current
    DESCRIPTION
        "An object of type TmnxOamPmBinGroupId identifies an OAM Performance
         Monitoring bin group."
    SYNTAX Unsigned32(1..255)

TmnxOamPmBinType                 ::= TEXTUAL-CONVENTION
    STATUS      current
    DESCRIPTION
        "An object of type TmnxOamPmBinType specifies the type of an OAM
         Performance Monitoring bin.

         Values:
            fd(1)
                A Frame Delay (FD) bin, as defined in MEF-35.
            fdr(2)
                A Frame Delay Range (FDR) bin, as defined in MEF-35.
            ifdv(3)
                An Inter-Frame Delay Variation (IFDV) bin, as defined in
                MEF-35."
    REFERENCE
        "MEF-35, 'Service OAM Performance Monitoring Implementation Agreement',
         Metro Ethernet Forum, April 2012, Section 9.2.2 'Measurement Bins'"
    SYNTAX INTEGER {
        fd(1),
        fdr(2),
        ifdv(3)
    }

TmnxOamPmMeasIntervalDuration    ::= TEXTUAL-CONVENTION
    STATUS      current
    DESCRIPTION
        "An object of type TmnxOamPmMeasIntervalDuration specifies the duration
         of an OAM Performance Monitoring measurement interval.

         Values:
            miRaw(1)
                A raw measurement interval starts when the associated test
                starts, and ends when the associated test ends.
            mi15Minutes(2)
                A 15 minute measurement interval, as defined in MEF-35 Section
                9.1.6.
            mi1Hour(3)
                A one hour measurement interval.
            mi1Day(4)
                A one day measurement interval."
    REFERENCE
        "MEF-35, 'Service OAM Performance Monitoring Implementation Agreement',
         Metro Ethernet Forum, April 2012, Section 9.1.6 'Measurement
         Intervals'"
    SYNTAX INTEGER {
        miRaw(1),
        mi15Minutes(2),
        mi1Hour(3),
        mi1Day(4)
    }

TmnxOamPmCfgMeasIntervalDuration ::= TEXTUAL-CONVENTION
    STATUS      current
    DESCRIPTION
        "An object of type TmnxOamPmCfgMeasIntervalDuration specifies the
         duration of a configurable OAM Performance Monitoring measurement
         interval.

         This TEXTUAL-CONVENTION is the same as TmnxOamPmMeasIntervalDuration,
         except the 'miRaw(1)' code point is absent here (because raw
         measurement intervals are not configurable)."
    REFERENCE
        "MEF-35, 'Service OAM Performance Monitoring Implementation Agreement',
         Metro Ethernet Forum, April 2012, Section 9.1.6 'Measurement
         Intervals'"
    SYNTAX INTEGER {
        mi15Minutes(2),
        mi1Hour(3),
        mi1Day(4)
    }

TmnxOamPmSessionType             ::= TEXTUAL-CONVENTION
    STATUS      current
    DESCRIPTION
        "An object of type TmnxOamPmSessionType specifies the type of an OAM
         Performance Monitoring session.

         Values:
            proactive(1)
                Test the service using a proactive session, as specified in
                MEF-35 Section 9.1.2.
            onDemand(2)
                Test the service using an on-demand session, as specified in
                MEF-35 Section 9.1.2."
    REFERENCE
        "MEF-35, 'Service OAM Performance Monitoring Implementation Agreement',
         Metro Ethernet Forum, April 2012, Section 9.1.2 'Proactive and
         On-Demand PM Sessions'"
    SYNTAX INTEGER {
        proactive(1),
        onDemand(2)
    }

TmnxOamPmStsIntvlNum             ::= TEXTUAL-CONVENTION
    STATUS      current
    DESCRIPTION
        "An object of type TmnxOamPmStsIntvlNum specifies the interval number of
         a Measurement Interval Data Set."
    REFERENCE
        "MEF-35, 'Service OAM Performance Monitoring Implementation Agreement',
         Metro Ethernet Forum, April 2012, Section 9.2.1 'Measurement Interval
         Data Sets'"
    SYNTAX Unsigned32 (1..4294967295)

TmnxOamPmTestFamily              ::= TEXTUAL-CONVENTION
    STATUS      current
    DESCRIPTION
        "An object of type TmnxOamPmTestFamily specifies the type of the service
         to be tested by an OAM Performance Monitoring test.

         Values:
            ethernet(1)
                Test an ethernet service, as specified in in MEF-35 Section 7.
            ip(2)
                Test an IP service."
    REFERENCE
        "MEF-35, 'Service OAM Performance Monitoring Implementation Agreement',
         Metro Ethernet Forum, April 2012, Section 7 'PM Considerations'"
    SYNTAX INTEGER {
        ethernet(1),
        ip(2)
    }

TmnxOamPmTestType                ::= TEXTUAL-CONVENTION
    STATUS      current
    DESCRIPTION
        "An object of type TmnxOamPmTestType specifies the type of an OAM
         Performance Monitoring test.

         Values:
            dmm(1)
                A Delay Measurement test, as specified in MEF-35 Section 10.1.
            slm(2)
                A Synthetic Loss Measurement test, as specified in MEF-35
                Section 10.2.
            twampLight(3)
                A TWAMP-Light test, using the TWAMP-Light protocol defined in
                RFC 5357, Appendix I.
            lmm(4)
                An ETH-LM test, as specified in Y.1731 Section 8.1.
        "
    REFERENCE
        "MEF-35, 'Service OAM Performance Monitoring Implementation Agreement',
         Metro Ethernet Forum, April 2012, Section 10.1, 'Single-Ended Delay
         Function for Delay, Frame Delay Range, and Inter Delay Variation'.
         MEF-35, 'Service OAM Performance Monitoring Implementation Agreement',
         Metro Ethernet Forum, April 2012, Section 10.2, 'Single-Ended Synthetic
         Loss Function for Frame Loss Ratio (FLR) and Availability'.
         RFC 5357, 'A Two-Way Active Measurement Protocol (TWAMP)', Appendix I,
         'TWAMP Light'.
         ITU-T G.8013/Y.1731, 'OAM functions and mechanisms for Ethernet based
         networks', 07/2011, Section 8.1 'Frame loss measurement (ETH-LM)'.
        "
    SYNTAX INTEGER {
        dmm(1),
        slm(2),
        twampLight(3),
        lmm(4)
    }

-- #############################################################################
-- Configuration Scalars
-- #############################################################################

tmnxOamPmCfgTwlRflInactTimer     OBJECT-TYPE
    SYNTAX      Unsigned32 (10..100)
    UNITS       "seconds"
    MAX-ACCESS  read-write
    STATUS      current
    DESCRIPTION
        "The value of tmnxOamPmCfgTwlRflInactTimer specifies the system
         inactivity timeout for TWAMP-Light reflectors.

         A TWAMP-Light reflector replies to TWAMP-Test PDUs.  When a reflector
         sees a TWAMP-Test PDU for a new session (i.e. a {source IP address,
         source UDP port, destination IP address} triple which is not known to
         the reflector), the reflector allocates a record for the session.  The
         record is used to ensure that reply PDUs sent for the session have
         consecutive sequence numbers.

         When a reflector sees tmnxOamPmCfgTwlRflInactTimer seconds pass without
         receiving a TWAMP-Test PDU for a particular session, an inactivity
         timeout has occurred, so the record allocated to the session is freed."
    DEFVAL { 100 }
    ::= { tmnxOamPmCfgScalarObjs 1 }

-- #############################################################################
-- Table Last Changed Timestamp Scalars
-- #############################################################################

tmnxOamPmCfgBinGroupTableLastChg OBJECT-TYPE
    SYNTAX      TimeStamp
    MAX-ACCESS  read-only
    STATUS      current
    DESCRIPTION
        "The value of tmnxOamPmCfgBinGroupTableLastChg indicates the time, since
         system startup, when tmnxOamPmCfgBinGroupTable last changed.

         If tmnxOamPmCfgBinGroupTable has not changed since system startup, zero
         is returned."
    ::= { tmnxOamPmTableLastChgObjs 1 }

tmnxOamPmCfgBinTableLastChg      OBJECT-TYPE
    SYNTAX      TimeStamp
    MAX-ACCESS  read-only
    STATUS      current
    DESCRIPTION
        "The value of tmnxOamPmCfgBinTableLastChg indicates the time, since
         system startup, when tmnxOamPmCfgBinTable last changed.

         If tmnxOamPmCfgBinTable has not changed since system startup, zero is
         returned."
    ::= { tmnxOamPmTableLastChgObjs 2 }

tmnxOamPmCfgSessTableLastChg     OBJECT-TYPE
    SYNTAX      TimeStamp
    MAX-ACCESS  read-only
    STATUS      current
    DESCRIPTION
        "The value of tmnxOamPmCfgSessTableLastChg indicates the time, since
         system startup, when tmnxOamPmCfgSessTable last changed.

         If tmnxOamPmCfgSessTable has not changed since system startup, zero is
         returned."
    ::= { tmnxOamPmTableLastChgObjs 3 }

tmnxOamPmCfgSessEthTableLastChg  OBJECT-TYPE
    SYNTAX      TimeStamp
    MAX-ACCESS  read-only
    STATUS      current
    DESCRIPTION
        "The value of tmnxOamPmCfgSessEthTableLastChg indicates the time, since
         system startup, when tmnxOamPmCfgSessEthTable last changed.

         If tmnxOamPmCfgSessEthTable has not changed since system startup, zero
         is returned."
    ::= { tmnxOamPmTableLastChgObjs 4 }

tmnxOamPmCfgDelayDmmTableLastChg OBJECT-TYPE
    SYNTAX      TimeStamp
    MAX-ACCESS  read-only
    STATUS      current
    DESCRIPTION
        "The value of tmnxOamPmCfgDelayDmmTableLastChg indicates the time, since
         system startup, when tmnxOamPmCfgDelayDmmTable last changed.

         If tmnxOamPmCfgDelayDmmTable has not changed since system startup, zero
         is returned."
    ::= { tmnxOamPmTableLastChgObjs 5 }

tmnxOamPmCfgLossSlmTableLastChg  OBJECT-TYPE
    SYNTAX      TimeStamp
    MAX-ACCESS  read-only
    STATUS      current
    DESCRIPTION
        "The value of tmnxOamPmCfgLossSlmTableLastChg indicates the time, since
         system startup, when tmnxOamPmCfgLossSlmTable last changed.

         If tmnxOamPmCfgLossSlmTable has not changed since system startup, zero
         is returned."
    ::= { tmnxOamPmTableLastChgObjs 6 }

tmnxOamPmCfgMeasIntvlTableLstChg OBJECT-TYPE
    SYNTAX      TimeStamp
    MAX-ACCESS  read-only
    STATUS      current
    DESCRIPTION
        "The value of tmnxOamPmCfgMeasIntvlTableLstChg indicates the time, since
         system startup, when tmnxOamPmCfgMeasIntvlTable last changed.

         If tmnxOamPmCfgMeasIntvlTable has not changed since system startup,
         zero is returned."
    ::= { tmnxOamPmTableLastChgObjs 7 }

tmnxOamPmCfgSessIpTableLastChg   OBJECT-TYPE
    SYNTAX      TimeStamp
    MAX-ACCESS  read-only
    STATUS      current
    DESCRIPTION
        "The value of tmnxOamPmCfgSessIpTableLastChg indicates the time, since
         system startup, when tmnxOamPmCfgSessIpTable last changed.

         If tmnxOamPmCfgSessIpTable has not changed since system startup, zero
         is returned."
    ::= { tmnxOamPmTableLastChgObjs 8 }

tmnxOamPmCfgTwampLtTableLastChg  OBJECT-TYPE
    SYNTAX      TimeStamp
    MAX-ACCESS  read-only
    STATUS      current
    DESCRIPTION
        "The value of tmnxOamPmCfgTwampLtTableLastChg indicates the time, since
         system startup, when tmnxOamPmCfgTwampLtTable last changed.

         If tmnxOamPmCfgTwampLtTable has not changed since system startup, zero
         is returned."
    ::= { tmnxOamPmTableLastChgObjs 9 }

tmnxOamPmCfgTwlRflTableLastChg   OBJECT-TYPE
    SYNTAX      TimeStamp
    MAX-ACCESS  read-only
    STATUS      current
    DESCRIPTION
        "The value of tmnxOamPmCfgTwlRflTableLastChg indicates the time, since
         system startup, when tmnxOamPmCfgTwlRflTable last changed.

         If tmnxOamPmCfgTwlRflTable has not changed since system startup, zero
         is returned."
    ::= { tmnxOamPmTableLastChgObjs 10 }

tmnxOamPmCfgTwlRflPfxTableLstChg OBJECT-TYPE
    SYNTAX      TimeStamp
    MAX-ACCESS  read-only
    STATUS      current
    DESCRIPTION
        "The value of tmnxOamPmCfgTwlRflPfxTableLstChg indicates the time, since
         system startup, when tmnxOamPmCfgTwlRflPfxTable last changed.

         If tmnxOamPmCfgTwlRflPfxTable has not changed since system startup,
         zero is returned."
    ::= { tmnxOamPmTableLastChgObjs 11 }


tmnxOamPmCfgLossLmmTableLastChg  OBJECT-TYPE
    SYNTAX      TimeStamp
    MAX-ACCESS  read-only
    STATUS      current
    DESCRIPTION
        "The value of tmnxOamPmCfgLossLmmTableLastChg indicates the time, since
         system startup, when tmnxOamPmCfgLossLmmTable last changed.

         If tmnxOamPmCfgLossLmmTable has not changed since system startup, zero
         is returned."
    ::= { tmnxOamPmTableLastChgObjs 12 }

-- #############################################################################
-- Configuration Tables
-- #############################################################################

--
-- OAM Performance Monitoring Bin Group Configuration Table
--

tmnxOamPmCfgBinGroupTable        OBJECT-TYPE
    SYNTAX      SEQUENCE OF TmnxOamPmCfgBinGroupEntry
    MAX-ACCESS  not-accessible
    STATUS      current
    DESCRIPTION
        "tmnxOamPmCfgBinGroupTable contains the configuration information for
         OAM Performance Monitoring bin groups."
    REFERENCE
        "MEF-35, 'Service OAM Performance Monitoring Implementation Agreement',
         Metro Ethernet Forum, April 2012, Section 9.2.2 'Measurement Bins'"
    ::= { tmnxOamPmCfgTableObjs 1 }

tmnxOamPmCfgBinGroupEntry        OBJECT-TYPE
    SYNTAX      TmnxOamPmCfgBinGroupEntry
    MAX-ACCESS  not-accessible
    STATUS      current
    DESCRIPTION
        "tmnxOamPmCfgBinGroupEntry contains the configuration information for
         one OAM Performance Monitoring bin group.

         Bin group 1 is created by the system on a CPM restart.

         The configuration of bin group 1 is shown in the following table.

         Object                             Value
         --------------------------------   ------------------------------
         tmnxOamPmCfgBinGroupId             1
         tmnxOamPmCfgBinGroupRowStatus      active(1)
         tmnxOamPmCfgBinGroupAdminStatus    enabled(1)
         tmnxOamPmCfgBinGroupDescription    'OAM PM default bin group (not
                                             modifiable)'
         tmnxOamPmCfgBinGroupFdBinCount     3
         tmnxOamPmCfgBinGroupFdrBinCount    2
         tmnxOamPmCfgBinGroupIfdvBinCount   2

         Bin group 1 cannot be changed or destroyed.

         The rest of the rows in this table are created or destroyed using
         tmnxOamPmCfgBinGroupRowStatus.

         When a row is created, the following objects must be set in the SNMP
         Set PDU:
            tmnxOamPmCfgBinGroupRowStatus
            tmnxOamPmCfgBinGroupFdBinCount
            tmnxOamPmCfgBinGroupFdrBinCount
            tmnxOamPmCfgBinGroupIfdvBinCount

         The value of the following objects cannot be changed after their row is
         created:
            tmnxOamPmCfgBinGroupFdBinCount
            tmnxOamPmCfgBinGroupFdrBinCount
            tmnxOamPmCfgBinGroupIfdvBinCount

         A row can be deleted if its administrative status
         (tmnxOamPmCfgBinGroupAdminStatus) is disabled, and no OAM Performance
         Monitoring sessions refer to the bin group."
    INDEX {
        tmnxOamPmCfgBinGroupId
    }
    ::= { tmnxOamPmCfgBinGroupTable 1 }

TmnxOamPmCfgBinGroupEntry        ::= SEQUENCE {
    tmnxOamPmCfgBinGroupId           TmnxOamPmBinGroupId,
    tmnxOamPmCfgBinGroupRowStatus    RowStatus,
    tmnxOamPmCfgBinGroupAdminStatus  TmnxEnabledDisabled,
    tmnxOamPmCfgBinGroupDescription  TItemDescription,
    tmnxOamPmCfgBinGroupFdBinCount   Unsigned32,
    tmnxOamPmCfgBinGroupFdrBinCount  Unsigned32,
    tmnxOamPmCfgBinGroupIfdvBinCount Unsigned32
}

tmnxOamPmCfgBinGroupId           OBJECT-TYPE
    SYNTAX      TmnxOamPmBinGroupId
    MAX-ACCESS  not-accessible
    STATUS      current
    DESCRIPTION
        "The value of tmnxOamPmCfgBinGroupId specifies the bin group to be
         configured or read."
    ::= { tmnxOamPmCfgBinGroupEntry 1 }

tmnxOamPmCfgBinGroupRowStatus    OBJECT-TYPE
    SYNTAX      RowStatus
    MAX-ACCESS  read-create
    STATUS      current
    DESCRIPTION
        "The value of tmnxOamPmCfgBinGroupRowStatus specifies the status of the
         configuration row for the specified bin group."
    ::= { tmnxOamPmCfgBinGroupEntry 2 }

tmnxOamPmCfgBinGroupAdminStatus  OBJECT-TYPE
    SYNTAX      TmnxEnabledDisabled
    MAX-ACCESS  read-create
    STATUS      current
    DESCRIPTION
        "The value of tmnxOamPmCfgBinGroupAdminStatus specifies whether or not
         the specified bin group is administratively enabled.

         An attempt to set this object to 'disabled(2)' will be rejected if
         tests referring to the specified bin group are enabled.

         An attempt to set this object to 'enabled(1)' will be rejected if one
         (or more) of the three sets of lower bounds for the specified bin group
         (as configured using tmnxOamPmCfgBinLowerBound) is not in strictly
         ascending order.

         For example, tmnxOamPmCfgBinGroupAdminStatus.255 cannot be set to
         'enabled(1)' if the following lower bound values are configured.

         Object ID                               Value (in microseconds)
         -------------------------------------   -----------------------
         tmnxOamPmCfgBinLowerBound.255.fd(1).1                      5000
         tmnxOamPmCfgBinLowerBound.255.fd(1).2                      5000
         tmnxOamPmCfgBinLowerBound.255.fd(1).3                      5002

         Setting this object to 'disabled(2)' deletes ALL the OAM-PM statistics
         for each test belonging to each session which refers to the specified
         bin group.  For example, if session 'Sess1' has a DMM test and an SLM
         test configured, and 'Sess1' uses bin-group 255, then disabling
         bin-group 255 will delete all the DMM and SLM statistics for 'Sess1'."
    DEFVAL { disabled }
    ::= { tmnxOamPmCfgBinGroupEntry 3 }

tmnxOamPmCfgBinGroupDescription  OBJECT-TYPE
    SYNTAX      TItemDescription
    MAX-ACCESS  read-create
    STATUS      current
    DESCRIPTION
        "The value of tmnxOamPmCfgBinGroupDescription specifies the descriptive
         text for the specified bin group."
    DEFVAL { "" }
    ::= { tmnxOamPmCfgBinGroupEntry 4 }

tmnxOamPmCfgBinGroupFdBinCount   OBJECT-TYPE
    SYNTAX      Unsigned32 (2..10)
    MAX-ACCESS  read-create
    STATUS      current
    DESCRIPTION
        "The value of tmnxOamPmCfgBinGroupFdBinCount specifies the number of
         Frame Delay bins to be created for the specified bin group.

         There is no default value for this object.  A value must be provided on
         row creation.  See the DESCRIPTION clause for tmnxOamPmCfgBinGroupEntry
         for more information."
    ::= { tmnxOamPmCfgBinGroupEntry 5 }

tmnxOamPmCfgBinGroupFdrBinCount  OBJECT-TYPE
    SYNTAX      Unsigned32 (2..10)
    MAX-ACCESS  read-create
    STATUS      current
    DESCRIPTION
        "The value of tmnxOamPmCfgBinGroupFdrBinCount specifies the number of
         Frame Delay Range bins to be created for the specified bin group.

         There is no default value for this object.  A value must be provided on
         row creation.  See the DESCRIPTION clause for tmnxOamPmCfgBinGroupEntry
         for more information."
    ::= { tmnxOamPmCfgBinGroupEntry 6 }

tmnxOamPmCfgBinGroupIfdvBinCount OBJECT-TYPE
    SYNTAX      Unsigned32 (2..10)
    MAX-ACCESS  read-create
    STATUS      current
    DESCRIPTION
        "The value of tmnxOamPmCfgBinGroupIfdvBinCount specifies the number of
         Inter-Frame Delay Variation bins to be created for the specified bin
         group.

         There is no default value for this object.  A value must be provided on
         row creation.  See the DESCRIPTION clause for tmnxOamPmCfgBinGroupEntry
         for more information."
    ::= { tmnxOamPmCfgBinGroupEntry 7 }

--
-- OAM Performance Monitoring Bin Configuration Table
--
tmnxOamPmCfgBinTable             OBJECT-TYPE
    SYNTAX      SEQUENCE OF TmnxOamPmCfgBinEntry
    MAX-ACCESS  not-accessible
    STATUS      current
    DESCRIPTION
        "tmnxOamPmCfgBinTable contains the configuration information for OAM
         Performance Monitoring bins."
    REFERENCE
        "MEF-35, 'Service OAM Performance Monitoring Implementation Agreement',
         Metro Ethernet Forum, April 2012, Section 9.2.2 'Measurement Bins'"
    ::= { tmnxOamPmCfgTableObjs 2 }

tmnxOamPmCfgBinEntry             OBJECT-TYPE
    SYNTAX      TmnxOamPmCfgBinEntry
    MAX-ACCESS  not-accessible
    STATUS      current
    DESCRIPTION
        "tmnxOamPmCfgBinEntry contains the configuration information for
         one OAM Performance Monitoring bin.

         Rows are created in this table when the following objects are set:
            tmnxOamPmCfgBinGroupFdBinCount
            tmnxOamPmCfgBinGroupFdrBinCount
            tmnxOamPmCfgBinGroupIfdvBinCount.

         Suppose, for example, that the following values are set for bin group
         255.

         Object                               Value
         ------------------------------------ -----
         tmnxOamPmCfgBinGroupFdBinCount.255       4
         tmnxOamPmCfgBinGroupFdrBinCount.255      3
         tmnxOamPmCfgBinGroupIfdvBinCount.255     2

         Then, the following rows will be created in this table (where index
         columns are underlined with '#', column names have been abbreviated by
         replacing 'tmnxOamPmCfg' with '_', and the _BinLowerBound column shows
         the default values).

         _BinGroupId _BinGroupType _BinId _BinLowerBound (microsec)
         ########### ############# ###### -------------------------
         255                 fd(1)      1                      5000
         255                 fd(1)      2                     10000
         255                 fd(1)      3                     15000
         255                fdr(2)      1                      5000
         255                fdr(2)      2                     10000
         255               ifdv(3)      1                      5000

         Note that tmnxOamPmCfgBinGroupFdBinCount.255 is 4, but there are only
         three corresponding rows in this table.  The fourth bin is bin 0, which
         has a hard coded lower bound of 0 microseconds.  Bin 0 never has a row
         in this table.

         The lower bounds for a particular <_BinGroupId, _BinGroupType> pair
         must be strictly ascending.  See the tmnxOamPmCfgBinGroupAdminStatus
         DESCRIPTION clause for more information."
    INDEX {
        tmnxOamPmCfgBinGroupId,
        tmnxOamPmCfgBinType,
        tmnxOamPmCfgBinNum
    }
    ::= { tmnxOamPmCfgBinTable 1 }

TmnxOamPmCfgBinEntry             ::= SEQUENCE {
    tmnxOamPmCfgBinType              TmnxOamPmBinType,
    tmnxOamPmCfgBinNum               Unsigned32,
    tmnxOamPmCfgBinLowerBound        Unsigned32
}

tmnxOamPmCfgBinType              OBJECT-TYPE
    SYNTAX      TmnxOamPmBinType
    MAX-ACCESS  not-accessible
    STATUS      current
    DESCRIPTION
        "The value of tmnxOamPmCfgBinType specifies the type of the bin to be
         configured or read."
    ::= { tmnxOamPmCfgBinEntry 1 }

tmnxOamPmCfgBinNum               OBJECT-TYPE
    SYNTAX      Unsigned32(1..9)
    MAX-ACCESS  not-accessible
    STATUS      current
    DESCRIPTION
        "The value of tmnxOamPmCfgBinNum specifies the number of the bin to be
         configured or read."
    ::= { tmnxOamPmCfgBinEntry 2 }

tmnxOamPmCfgBinLowerBound        OBJECT-TYPE
    SYNTAX      Unsigned32(1..4294967295)
    UNITS       "microseconds"
    MAX-ACCESS  read-write
    STATUS      current
    DESCRIPTION
        "The value of tmnxOamPmCfgBinLowerBound specifies the lower bound (in
         microseconds) for the specified bin.

         A lower bound can be changed if the administrative state (i.e.
         tmnxOamPmCfgBinGroupAdminStatus) for the parent bin group is disabled.
         Please see additional restrictions on setting lower bounds in the
         tmnxOamPmCfgBinEntry DESCRIPTION clause.

         The default lower bound for bin number 1 is 5000 microseconds.  The
         default lower bound for a subsequent bin number is computed using
            defLowerBound(n) = defLowerBound(n-1) + (5000 microseconds)."
    ::= { tmnxOamPmCfgBinEntry 3 }

--
-- OAM Performance Monitoring Session Configuration Table
--

tmnxOamPmCfgSessTable            OBJECT-TYPE
    SYNTAX      SEQUENCE OF TmnxOamPmCfgSessEntry
    MAX-ACCESS  not-accessible
    STATUS      current
    DESCRIPTION
        "tmnxOamPmCfgSessTable contains the configuration information for OAM
         Performance Monitoring sessions."
    REFERENCE
        "MEF-35, 'Service OAM Performance Monitoring Implementation Agreement',
         Metro Ethernet Forum, April 2012, Section 9.1.2 'Proactive and
         On-Demand PM Sessions'"
    ::= { tmnxOamPmCfgTableObjs 3 }

tmnxOamPmCfgSessEntry            OBJECT-TYPE
    SYNTAX      TmnxOamPmCfgSessEntry
    MAX-ACCESS  not-accessible
    STATUS      current
    DESCRIPTION
        "tmnxOamPmCfgSessEntry contains the configuration information for one
         OAM Performance Monitoring session.

         Rows are created or destroyed by SNMP Set operations on
         tmnxOamPmCfgSessRowStatus.

         An attempt to change the tmnxOamPmCfgSessBinGroupId value in a row
         (or an attempt to delete the row) for a particular session will be 
         rejected if an administratively enabled test (e.g. an SLM test) exists
         for the session."
    INDEX {
        tmnxOamPmCfgSessName
    }
    ::= { tmnxOamPmCfgSessTable 1 }

TmnxOamPmCfgSessEntry            ::= SEQUENCE {
    tmnxOamPmCfgSessName             TNamedItem,
    tmnxOamPmCfgSessRowStatus        RowStatus,
    tmnxOamPmCfgSessTestFamily       TmnxOamPmTestFamily,
    tmnxOamPmCfgSessType             TmnxOamPmSessionType,
    tmnxOamPmCfgSessBinGroupId       TmnxOamPmBinGroupId,
    tmnxOamPmCfgSessDescription      TItemDescription
}

tmnxOamPmCfgSessName             OBJECT-TYPE
    SYNTAX      TNamedItem
    MAX-ACCESS  not-accessible
    STATUS      current
    DESCRIPTION
        "The value of tmnxOamPmCfgSessName specifies the name of the session to
         be configured or read."
    ::= { tmnxOamPmCfgSessEntry 1 }

tmnxOamPmCfgSessRowStatus        OBJECT-TYPE
    SYNTAX      RowStatus
    MAX-ACCESS  read-create
    STATUS      current
    DESCRIPTION
        "The value of tmnxOamPmCfgSessRowStatus specifies the status of the
         configuration row for the specified session."
    ::= { tmnxOamPmCfgSessEntry 2 }

tmnxOamPmCfgSessTestFamily       OBJECT-TYPE
    SYNTAX      TmnxOamPmTestFamily
    MAX-ACCESS  read-create
    STATUS      current
    DESCRIPTION
        "The value of tmnxOamPmCfgSessTestFamily specifies the type of service
         (e.g. 'ethernet(1)') to be tested by the specified session.

         When a session is created, tmnxOamPmCfgSessRowStatus and
         tmnxOamPmCfgSessTestFamily must be specified in the same SNMP Set PDU.

         After a session is created, tmnxOamPmCfgSessTestFamily cannot be
         changed."
    ::= { tmnxOamPmCfgSessEntry 3 }

tmnxOamPmCfgSessType             OBJECT-TYPE
    SYNTAX      TmnxOamPmSessionType
    MAX-ACCESS  read-create
    STATUS      current
    DESCRIPTION
        "The value of tmnxOamPmCfgSessType specifies the type (e.g.
         'onDemand(2)') of the specified session.

         When a session is created, tmnxOamPmCfgSessRowStatus and
         tmnxOamPmCfgSessType can be specified in the same SNMP Set PDU.  Or,
         tmnxOamPmCfgSessType can be left at its default value.

         After a session is created, tmnxOamPmCfgSessType cannot be changed."
    DEFVAL { proactive }
    ::= { tmnxOamPmCfgSessEntry 4 }

tmnxOamPmCfgSessBinGroupId       OBJECT-TYPE
    SYNTAX      TmnxOamPmBinGroupId
    MAX-ACCESS  read-create
    STATUS      current
    DESCRIPTION
        "The value of tmnxOamPmCfgSessBinGroupId specifies the bin group to be
         used by the specified session.

         Changing the bin group for a session deletes ALL the OAM-PM statistics
         for the session's tests."
    DEFVAL { 1 }
    ::= { tmnxOamPmCfgSessEntry 5 }

tmnxOamPmCfgSessDescription      OBJECT-TYPE
    SYNTAX      TItemDescription
    MAX-ACCESS  read-create
    STATUS      current
    DESCRIPTION
        "The value of tmnxOamPmCfgSessDescription specifies the descriptive text
         for the specified session."
    DEFVAL { "" }
    ::= { tmnxOamPmCfgSessEntry 6 }

--
-- OAM Performance Monitoring Ethernet Session Configuration Table
--

tmnxOamPmCfgSessEthTable         OBJECT-TYPE
    SYNTAX      SEQUENCE OF TmnxOamPmCfgSessEthEntry
    MAX-ACCESS  not-accessible
    STATUS      current
    DESCRIPTION
        "tmnxOamPmCfgSessEthTable contains the Ethernet endpoint configuration
         information for OAM Performance Monitoring sessions."
    REFERENCE
        "ITU-T G.8013/Y.1731, 'OAM functions and mechanisms for Ethernet based
         networks', 07/2011.
         MEF-35, 'Service OAM Performance Monitoring Implementation Agreement',
         Metro Ethernet Forum, April 2012, Section 9.4 'MEP Placement'."
    ::= { tmnxOamPmCfgTableObjs 4 }

tmnxOamPmCfgSessEthEntry         OBJECT-TYPE
    SYNTAX      TmnxOamPmCfgSessEthEntry
    MAX-ACCESS  not-accessible
    STATUS      current
    DESCRIPTION
        "tmnxOamPmCfgSessEthEntry contains the Ethernet endpoint configuration
         information for one OAM Performance Monitoring session.

         A row is created when a tmnxOamPmCfgSessTable row is created with
         tmnxOamPmCfgSessTestFamily = 'ethernet(1)'.

         A row is destroyed when a tmnxOamPmCfgSessTable row with
         tmnxOamPmCfgSessTestFamily = 'ethernet(1)' is destroyed.

         An attempt to change a value in a row for a particular session will be
         rejected if an administratively enabled test (e.g. an SLM test) exists
         for the session."
    INDEX {
        tmnxOamPmCfgSessName
    }
    ::= { tmnxOamPmCfgSessEthTable 1 }

TmnxOamPmCfgSessEthEntry         ::= SEQUENCE {
    tmnxOamPmCfgSessEthSrcMepId      Dot1agCfmMepIdOrZero,
    tmnxOamPmCfgSessEthSrcMdIndex    Unsigned32,
    tmnxOamPmCfgSessEthSrcMaIndex    Unsigned32,
    tmnxOamPmCfgSessEthPriority      Unsigned32,
    tmnxOamPmCfgSessEthDestMacAddr   MacAddress
}

tmnxOamPmCfgSessEthSrcMepId      OBJECT-TYPE
    SYNTAX      Dot1agCfmMepIdOrZero
    MAX-ACCESS  read-write
    STATUS      current
    DESCRIPTION
        "The value of tmnxOamPmCfgSessEthSrcMepId specifies the source Ethernet
         Maintenance association End Point (MEP) identifier to be used by the
         specified session.

         Zero indicates a value has not been configured."
    DEFVAL { 0 }
    ::= { tmnxOamPmCfgSessEthEntry 1 }

tmnxOamPmCfgSessEthSrcMdIndex    OBJECT-TYPE
    SYNTAX      Unsigned32
    MAX-ACCESS  read-write
    STATUS      current
    DESCRIPTION
        "The value of tmnxOamPmCfgSessEthSrcMdIndex specifies the source
         Ethernet Maintenance Domain (MD) index to be used by the specified
         session.

         Zero indicates a value has not been configured."
    DEFVAL { 0 }
    ::= { tmnxOamPmCfgSessEthEntry 2 }

tmnxOamPmCfgSessEthSrcMaIndex    OBJECT-TYPE
    SYNTAX      Unsigned32
    MAX-ACCESS  read-write
    STATUS      current
    DESCRIPTION
        "The value of tmnxOamPmCfgSessEthSrcMaIndex specifies the source
         Ethernet Maintenance Association (MA) index to be used by the specified
         session.

         Zero indicates a value has not been configured."
    DEFVAL { 0 }
    ::= { tmnxOamPmCfgSessEthEntry 3 }

tmnxOamPmCfgSessEthPriority      OBJECT-TYPE
    SYNTAX      Unsigned32(0..7)
    MAX-ACCESS  read-write
    STATUS      current
    DESCRIPTION
        "The value of tmnxOamPmCfgSessEthPriority specifies the value to be
         copied into the priority field when launching a test PDU for the
         specified session."
    DEFVAL { 0 }
    ::= { tmnxOamPmCfgSessEthEntry 4 }

tmnxOamPmCfgSessEthDestMacAddr   OBJECT-TYPE
    SYNTAX      MacAddress
    MAX-ACCESS  read-write
    STATUS      current
    DESCRIPTION
        "The value of tmnxOamPmCfgSessEthDestMacAddr specifies the destination
         MAC addresss for the specified session.

         The all-zeros MAC address indicates a value has not been configured."
    DEFVAL { '000000000000'H }
    ::= { tmnxOamPmCfgSessEthEntry 5 }

--
-- OAM Performance Monitoring Ethernet DMM Delay Test Configuration Table
--

tmnxOamPmCfgDelayDmmTable        OBJECT-TYPE
    SYNTAX      SEQUENCE OF TmnxOamPmCfgDelayDmmEntry
    MAX-ACCESS  not-accessible
    STATUS      current
    DESCRIPTION
        "tmnxOamPmCfgDelayDmmTable contains the configuration information for
         OAM Performance Monitoring Delay Measurement Message (DMM) tests."
    REFERENCE
        "MEF-35, 'Service OAM Performance Monitoring Implementation Agreement',
         Metro Ethernet Forum, April 2012, Section 7.1 'Frame Delay
         Measurements'"
    ::= { tmnxOamPmCfgTableObjs 5 }

tmnxOamPmCfgDelayDmmEntry        OBJECT-TYPE
    SYNTAX      TmnxOamPmCfgDelayDmmEntry
    MAX-ACCESS  not-accessible
    STATUS      current
    DESCRIPTION
        "tmnxOamPmCfgDelayDmmEntry contains the configuration information for
         one OAM Performance Monitoring Delay Measurement Message (DMM) test.

         Rows are created or destroyed by SNMP Set operations on
         tmnxOamPmCfgDelayDmmRowStatus.

         An attempt to change any value in a row (except
         tmnxOamPmCfgDelayDmmAdminStatus and tmnxOamPmCfgDelayDmmOnDmndStatus)
         will be rejected if tmnxOamPmCfgDelayDmmAdminStatus is 'enabled(1)'."
    INDEX {
        tmnxOamPmCfgSessName
    }
    ::= { tmnxOamPmCfgDelayDmmTable 1 }

TmnxOamPmCfgDelayDmmEntry        ::= SEQUENCE {
    tmnxOamPmCfgDelayDmmRowStatus    RowStatus,
    tmnxOamPmCfgDelayDmmAdminStatus  TmnxEnabledDisabled,
    tmnxOamPmCfgDelayDmmOnDmndStatus TmnxEnabledDisabledOrNA,
    tmnxOamPmCfgDelayDmmTestId       Unsigned32,
    tmnxOamPmCfgDelayDmmInterval     Unsigned32,
    tmnxOamPmCfgDelayDmmDataTlvSize  Unsigned32,
    tmnxOamPmCfgDelayDmmTestDuration Unsigned32,
    tmnxOamPmCfgDelayDmmRunTimeLeft  Unsigned32
}

tmnxOamPmCfgDelayDmmRowStatus    OBJECT-TYPE
    SYNTAX      RowStatus
    MAX-ACCESS  read-create
    STATUS      current
    DESCRIPTION
        "The value of tmnxOamPmCfgDelayDmmRowStatus specifies the status of the
         configuration row for the specified session's DMM test.

         An attempt to create a row for a session with
         tmnxOamPmCfgSessTestFamily other than 'ethernet(1)' will be rejected."
    ::= { tmnxOamPmCfgDelayDmmEntry 1 }

tmnxOamPmCfgDelayDmmAdminStatus  OBJECT-TYPE
    SYNTAX      TmnxEnabledDisabled
    MAX-ACCESS  read-create
    STATUS      current
    DESCRIPTION
        "The value of tmnxOamPmCfgDelayDmmAdminStatus specifies whether or not
         the specified session's DMM test is administratively enabled.

         If the session type (tmnxOamPmCfgSessType) is 'proactive(1)', setting
         tmnxOamPmCfgDelayDmmAdminStatus to 'enabled(1)'/'disabled(2)'
         starts/stops the test.

         If the session type is 'onDemand(2)', see the DESCRIPTION clause for
         tmnxOamPmCfgDelayDmmOnDmndStatus for information on starting/stopping
         the test.

         An attempt to set this object to 'enabled(1)' will be rejected if the
         tmnxOamPmCfgSessEthTable row for the specified session has incomplete
         endpoint information for the test (e.g. if
         tmnxOamPmCfgSessEthDestMacAddr is the all-zeroes MAC address)."
    DEFVAL { disabled }
    ::= { tmnxOamPmCfgDelayDmmEntry 2 }

tmnxOamPmCfgDelayDmmOnDmndStatus OBJECT-TYPE
    SYNTAX      TmnxEnabledDisabledOrNA
    MAX-ACCESS  read-create
    STATUS      current
    DESCRIPTION
        "The value of tmnxOamPmCfgDelayDmmOnDmndStatus specifies the status of
         the on-demand DMM test for the specified session.

         Values:
            'enabled(1)'
                Set by an SNMP manager to start an on-demand DMM test.  The test
                will start if tmnxOamPmCfgDelayDmmAdminStatus is 'enabled(1)'.
            'disabled(2)'
                Set by an SNMP manager to stop an on-demand DMM test.
                Set by SROS to indicate an on-demand DMM test has stopped
                running because the configured period for the test (i.e.
                tmnxOamPmCfgDelayDmmTestDuration) has ended.
                Set by SROS for an on-demand DMM test when
                tmnxOamPmCfgDelayDmmAdminStatus is set to 'disabled(2)'.
            'notApplicable(3)'
                This code point is the only acceptable value for a proactive
                DMM test.  An attempt to set this code point for an on-demand
                DMM test will be rejected.

         The default value is 'disabled(2)' for an on-demand DMM test, and
         'notApplicable(3)' for a proactive DMM test."
    ::= { tmnxOamPmCfgDelayDmmEntry 3 }

tmnxOamPmCfgDelayDmmTestId       OBJECT-TYPE
    SYNTAX      Unsigned32(0..2147483647)
    MAX-ACCESS  read-create
    STATUS      current
    DESCRIPTION
        "The value of tmnxOamPmCfgDelayDmmTestId specifies the test identifier
         for the specified session's DMM test.

         When a DMM test is created, tmnxOamPmCfgDelayDmmRowStatus and
         tmnxOamPmCfgDelayDmmTestId must be specified in the same SNMP Set PDU.

         When a Y.1731 DMM PDU is being built, the test identifier is copied
         into the PDU's Test ID TLV.

         An attempt to add a duplicate test identifier to this table will be
         rejected.

         Test identifier values larger than 2147483647 are reserved for internal
         use."
    REFERENCE
        "ITU-T G.8013/Y.1731, 'OAM functions and mechanisms for Ethernet based
         networks', 07/2011, Figure 9.14-3, 'Test ID TLV format', and Section
         9.15, 'DMM PDU'."
    ::= { tmnxOamPmCfgDelayDmmEntry 4 }

tmnxOamPmCfgDelayDmmInterval     OBJECT-TYPE
    SYNTAX      Unsigned32(100|1000)
    UNITS       "milliseconds"
    MAX-ACCESS  read-create
    STATUS      current
    DESCRIPTION
        "The value of tmnxOamPmCfgDelayDmmInterval specifies the elapsed time
         between transmission of Y.1731 DMM PDUs for the specified session's DMM
         test."
    DEFVAL { 1000 }
    ::= { tmnxOamPmCfgDelayDmmEntry 5 }

tmnxOamPmCfgDelayDmmDataTlvSize  OBJECT-TYPE
    SYNTAX      Unsigned32(0|3..2000)
    UNITS       "octets"
    MAX-ACCESS  read-create
    STATUS      current
    DESCRIPTION
        "The value of tmnxOamPmCfgDelayDmmDataTlvSize specifies the amount of
         padding to be added to each launched Y.1731 DMM PDU for the specified
         session's DMM test.

         Zero specifies that a Data TLV should not be added to each launched
         Y.1731 DMM PDU.

         A value larger than zero specifies the total size (including the
         header) of the Data TLV added to each launched Y.1731 DMM PDU."
    REFERENCE
        "ITU-T G.8013/Y.1731, 'OAM functions and mechanisms for Ethernet based
         networks', 07/2011, Figure 9.3-3, 'Data TLV format', and Section
         9.15, 'DMM PDU'."
    DEFVAL { 0 }
    ::= { tmnxOamPmCfgDelayDmmEntry 6 }

tmnxOamPmCfgDelayDmmTestDuration OBJECT-TYPE
    SYNTAX      Unsigned32 (0..86400)
    UNITS       "seconds"
    MAX-ACCESS  read-create
    STATUS      current
    DESCRIPTION
        "The value of tmnxOamPmCfgDelayDmmTestDuration specifies the test
         duration for the specified session's DMM test.

         Zero specifies a test which runs until it is manually stopped.

         An attempt to set a non-zero value will be rejected if
         tmnxOamPmCfgSessType is 'proactive(1)'."
    DEFVAL { 0 }
    ::= { tmnxOamPmCfgDelayDmmEntry 7 }

tmnxOamPmCfgDelayDmmRunTimeLeft  OBJECT-TYPE
    SYNTAX      Unsigned32 (0..86400)
    UNITS       "seconds"
    MAX-ACCESS  read-only
    STATUS      current
    DESCRIPTION
        "The value of tmnxOamPmCfgDelayDmmRunTimeLeft indicates the run time
         remaining for the specified session's DMM test.

         For example, suppose a DMM test has the following configuration:

         tmnxOamPmCfgSessType   tmnxOamPmCfgDelayDmmTestDuration
         --------------------   --------------------------------
         'onDemand(2)'          1000 (seconds)

         Then, when the DMM test is started (see
         tmnxOamPmCfgDelayDmmOnDmndStatus), tmnxOamPmCfgDelayDmmRunTimeLeft is
         initialized to 1000 seconds.  After a minute,
         tmnxOamPmCfgDelayDmmRunTimeLeft is 940 seconds.

         If tmnxOamPmCfgSessType is 'proactive(1)', zero is always returned
         (because a proactive test runs until it is manually stopped).

         If tmnxOamPmCfgSessType is 'onDemand(2)' and the test is stopped (see
         tmnxOamPmCfgDelayDmmOnDmndStatus), zero is returned (because the test
         is not running)."
    ::= { tmnxOamPmCfgDelayDmmEntry 8 }

--
-- OAM Performance Monitoring Ethernet SLM Loss Test Configuration Table
--

tmnxOamPmCfgLossSlmTable         OBJECT-TYPE
    SYNTAX      SEQUENCE OF TmnxOamPmCfgLossSlmEntry
    MAX-ACCESS  not-accessible
    STATUS      current
    DESCRIPTION
        "tmnxOamPmCfgLossSlmTable contains the configuration information for
         OAM Performance Monitoring Synthetic Loss Message (SLM) tests."
    REFERENCE
        "MEF-35, 'Service OAM Performance Monitoring Implementation Agreement',
         Metro Ethernet Forum, April 2012, Section 7.2 'Frame Loss
         Measurements'"
    ::= { tmnxOamPmCfgTableObjs 6 }

tmnxOamPmCfgLossSlmEntry         OBJECT-TYPE
    SYNTAX      TmnxOamPmCfgLossSlmEntry
    MAX-ACCESS  not-accessible
    STATUS      current
    DESCRIPTION
        "tmnxOamPmCfgLossSlmEntry contains the configuration information for one
         OAM Performance Monitoring Synthetic Loss Message (SLM) test.

         Rows are created or destroyed by SNMP Set operations on
         tmnxOamPmCfgLossSlmRowStatus.

         An attempt to change any value in a row (except
         tmnxOamPmCfgLossSlmAdminStatus and tmnxOamPmCfgLossSlmOnDmndStatus)
         will be rejected if tmnxOamPmCfgLossSlmAdminStatus is 'enabled(1)'.

         The following objects must all be set together in one SNMP Set PDU:
            tmnxOamPmCfgLossSlmChliThreshold,
            tmnxOamPmCfgLossSlmConsecDeltaTs,
            tmnxOamPmCfgLossSlmInterval,
            tmnxOamPmCfgLossSlmTxFrmsPerDelT."
    INDEX {
        tmnxOamPmCfgSessName
    }
    ::= { tmnxOamPmCfgLossSlmTable 1 }

TmnxOamPmCfgLossSlmEntry         ::= SEQUENCE {
    tmnxOamPmCfgLossSlmRowStatus     RowStatus,
    tmnxOamPmCfgLossSlmAdminStatus   TmnxEnabledDisabled,
    tmnxOamPmCfgLossSlmOnDmndStatus  TmnxEnabledDisabledOrNA,
    tmnxOamPmCfgLossSlmTestId        Unsigned32,
    tmnxOamPmCfgLossSlmInterval      Unsigned32,
    tmnxOamPmCfgLossSlmDataTlvSize   Unsigned32,
    tmnxOamPmCfgLossSlmTxFrmsPerDelT Unsigned32,
    tmnxOamPmCfgLossSlmConsecDeltaTs Unsigned32,
    tmnxOamPmCfgLossSlmChliThreshold Unsigned32,
    tmnxOamPmCfgLossSlmFlrThreshold  Unsigned32,
    tmnxOamPmCfgLossSlmTestDuration  Unsigned32,
    tmnxOamPmCfgLossSlmRunTimeLeft   Unsigned32
}

tmnxOamPmCfgLossSlmRowStatus     OBJECT-TYPE
    SYNTAX      RowStatus
    MAX-ACCESS  read-create
    STATUS      current
    DESCRIPTION
        "The value of tmnxOamPmCfgLossSlmRowStatus specifies the status of the
         configuration row for the specified session's SLM test.

         An attempt to create a row for a session with
         tmnxOamPmCfgSessTestFamily other than 'ethernet(1)' will be rejected."
    ::= { tmnxOamPmCfgLossSlmEntry 1 }

tmnxOamPmCfgLossSlmAdminStatus   OBJECT-TYPE
    SYNTAX      TmnxEnabledDisabled
    MAX-ACCESS  read-create
    STATUS      current
    DESCRIPTION
        "The value of tmnxOamPmCfgLossSlmAdminStatus specifies whether or not
         the specified session's SLM test is administratively enabled.

         If the session type (tmnxOamPmCfgSessType) is 'proactive(1)', setting
         tmnxOamPmCfgLossSlmAdminStatus to 'enabled(1)'/'disabled(2)'
         starts/stops the test.

         If the session type is 'onDemand(2)', see the DESCRIPTION clause for
         tmnxOamPmCfgLossSlmOnDmndStatus for information on starting/stopping
         the test.

         An attempt to set this object to 'enabled(1)' will be rejected if the
         tmnxOamPmCfgSessEthTable row for the specified session has incomplete
         endpoint information for the test (e.g. if
         tmnxOamPmCfgSessEthDestMacAddr is the all-zeroes MAC address)."
    DEFVAL { disabled }
    ::= { tmnxOamPmCfgLossSlmEntry 2 }

tmnxOamPmCfgLossSlmOnDmndStatus  OBJECT-TYPE
    SYNTAX      TmnxEnabledDisabledOrNA
    MAX-ACCESS  read-create
    STATUS      current
    DESCRIPTION
        "The value of tmnxOamPmCfgLossSlmOnDmndStatus specifies the status of
         the on-demand SLM test for the specified session.

         Values:
            'enabled(1)'
                Set by an SNMP manager to start an on-demand SLM test.  The test
                will start if tmnxOamPmCfgLossSlmAdminStatus is 'enabled(1)'.
            'disabled(2)'
                Set by an SNMP manager to stop an on-demand SLM test.
                Set by SROS to indicate an on-demand SLM test has stopped
                running because the configured period for the test (i.e.
                tmnxOamPmCfgLossSlmTestDuration) has ended.
                Set by SROS for an on-demand SLM test when
                tmnxOamPmCfgLossSlmAdminStatus is set to 'disabled(2)'.
            'notApplicable(3)'
                This code point is the only acceptable value for a proactive SLM
                test.  An attempt to set this code point for an on-demand SLM
                test will be rejected.

         The default value is 'disabled(2)' for an on-demand SLM test, and
         'notApplicable(3)' for a proactive SLM test."
    ::= { tmnxOamPmCfgLossSlmEntry 3 }

tmnxOamPmCfgLossSlmTestId        OBJECT-TYPE
    SYNTAX      Unsigned32(0..2147483647)
    MAX-ACCESS  read-create
    STATUS      current
    DESCRIPTION
        "The value of tmnxOamPmCfgLossSlmTestId specifies the test identifier
         for the specified session's SLM test.

         When an SLM test is created, tmnxOamPmCfgLossSlmRowStatus and
         tmnxOamPmCfgLossSlmTestId must be specified in the same SNMP Set PDU.

         When a Y.1731 SLM PDU is being built, the test identifier is copied
         into the PDU's Test ID field.

         An attempt to add a duplicate test identifier to this table will be
         rejected.

         Test identifier values larger than 2147483647 are reserved for internal
         use."
    REFERENCE
        "ITU-T G.8013/Y.1731, 'OAM functions and mechanisms for Ethernet based
         networks', 07/2011, Section 9.22, 'SLM PDU'."
    ::= { tmnxOamPmCfgLossSlmEntry 4 }

tmnxOamPmCfgLossSlmInterval      OBJECT-TYPE
    SYNTAX      Unsigned32(100|1000)
    UNITS       "milliseconds"
    MAX-ACCESS  read-create
    STATUS      current
    DESCRIPTION
        "The value of tmnxOamPmCfgLossSlmInterval specifies the elapsed time
         between transmission of Y.1731 SLM PDUs for the specified session's SLM
         test."
    DEFVAL { 100 }
    ::= { tmnxOamPmCfgLossSlmEntry 5 }

tmnxOamPmCfgLossSlmDataTlvSize   OBJECT-TYPE
    SYNTAX      Unsigned32(0|3..2000)
    UNITS       "octets"
    MAX-ACCESS  read-create
    STATUS      current
    DESCRIPTION
        "The value of tmnxOamPmCfgLossSlmDataTlvSize specifies the amount of
         padding to be added to each launched Y.1731 SLM PDU for the specified
         session's SLM test.

         Zero specifies that a Data TLV should not be added to each launched
         Y.1731 SLM PDU.

         A value larger than zero specifies the total size (including the
         header) of the Data TLV added to each launched Y.1731 SLM PDU."
    REFERENCE
        "ITU-T G.8013/Y.1731, 'OAM functions and mechanisms for Ethernet based
         networks', 07/2011, Figure 9.3-3, 'Data TLV format', and Section
         9.22, 'SLM PDU'."
    DEFVAL { 0 }
    ::= { tmnxOamPmCfgLossSlmEntry 6 }

tmnxOamPmCfgLossSlmTxFrmsPerDelT OBJECT-TYPE
    SYNTAX      Unsigned32(1..50)
    UNITS       "frames"
    MAX-ACCESS  read-create
    STATUS      current
    DESCRIPTION
        "The value of tmnxOamPmCfgLossSlmTxFrmsPerDelT specifies the number of
         Y.1731 SLM frames to send in one MEF-35 'delta_t' (also known as 'Small
         Time Interval') for the specified session's SLM test.

         Expressed in milliseconds,
         delta_t =tmnxOamPmCfgLossSlmTxFrmsPerDelT*tmnxOamPmCfgLossSlmInterval."
    REFERENCE
        "MEF-35, 'Service OAM Performance Monitoring Implementation Agreement',
         Metro Ethernet Forum, April 2012, Section 10.2 'Single-Ended Synthetic
         Loss Function for Frame Loss Ratio (FLR) and Availability'."
    DEFVAL { 10 }
    ::= { tmnxOamPmCfgLossSlmEntry 7 }

tmnxOamPmCfgLossSlmConsecDeltaTs OBJECT-TYPE
    SYNTAX      Unsigned32(2..10)
    MAX-ACCESS  read-create
    STATUS      current
    DESCRIPTION
        "The value of tmnxOamPmCfgLossSlmConsecDeltaTs specifies the number of
         consecutive MEF-35 'delta_t's (also known as 'Small Time Intervals')
         which constitute a MEF-35 'Availability Window'.

         The duration of an Availability Window (in milliseconds) is
         tmnxOamPmCfgLossSlmTxFrmsPerDelT * tmnxOamPmCfgLossSlmInterval *
         tmnxOamPmCfgLossSlmConsecDeltaTs.  An attempt to change the duration of
         an Availability Window to more than 10,000 milliseconds will be
         rejected.

         An attempt to change tmnxOamPmCfgLossSlmConsecDeltaTs to a value less
         than or equal to tmnxOamPmCfgLossSlmChliThreshold will be rejected."
    REFERENCE
        "MEF-35, 'Service OAM Performance Monitoring Implementation Agreement',
         Metro Ethernet Forum, April 2012, Section 10.2 'Single-Ended Synthetic
         Loss Function for Frame Loss Ratio (FLR) and Availability'."
    DEFVAL { 10 }
    ::= { tmnxOamPmCfgLossSlmEntry 8 }

tmnxOamPmCfgLossSlmChliThreshold OBJECT-TYPE
    SYNTAX      Unsigned32(1..9)
    MAX-ACCESS  read-create
    STATUS      current
    DESCRIPTION
        "The value of tmnxOamPmCfgLossSlmChliThreshold specifies the MEF-35
         Consecutive High Loss Intervals (CHLI) threshold for the specified
         session's SLM test.

         An attempt to change tmnxOamPmCfgLossSlmChliThreshold to a value
         greater than or equal to tmnxOamPmCfgLossSlmConsecDeltaTs will be
         rejected."
    REFERENCE
        "MEF-35, 'Service OAM Performance Monitoring Implementation Agreement',
         Metro Ethernet Forum, April 2012, Section 10.2 'Single-Ended Synthetic
         Loss Function for Frame Loss Ratio (FLR) and Availability'."
    DEFVAL { 5 }
    ::= { tmnxOamPmCfgLossSlmEntry 9 }

tmnxOamPmCfgLossSlmFlrThreshold  OBJECT-TYPE
    SYNTAX      Unsigned32(0..100)
    UNITS       "percent"
    MAX-ACCESS  read-create
    STATUS      current
    DESCRIPTION
        "The value of tmnxOamPmCfgLossSlmFlrThreshold specifies the MEF-35
         Frame Loss Ratio (FLR) threshold for the specified session's SLM test.

         The FLR threshold is used to decide if a MEF-35 Small Time Interval
         (also known as delta_t) is Available or Unavailable."
    REFERENCE
        "MEF-35, 'Service OAM Performance Monitoring Implementation Agreement',
         Metro Ethernet Forum, April 2012, Section 10.2 'Single-Ended Synthetic
         Loss Function for Frame Loss Ratio (FLR) and Availability'."
    DEFVAL { 50 }
    ::= { tmnxOamPmCfgLossSlmEntry 10 }

tmnxOamPmCfgLossSlmTestDuration  OBJECT-TYPE
    SYNTAX      Unsigned32 (0..86400)
    UNITS       "seconds"
    MAX-ACCESS  read-create
    STATUS      current
    DESCRIPTION
        "The value of tmnxOamPmCfgLossSlmTestDuration specifies the test
         duration for the specified session's SLM test.

         Zero specifies a test which runs until it is manually stopped.

         An attempt to set a non-zero value will be rejected if
         tmnxOamPmCfgSessType is 'proactive(1)'."
    DEFVAL { 0 }
    ::= { tmnxOamPmCfgLossSlmEntry 11 }

tmnxOamPmCfgLossSlmRunTimeLeft   OBJECT-TYPE
    SYNTAX      Unsigned32 (0..86400)
    UNITS       "seconds"
    MAX-ACCESS  read-only
    STATUS      current
    DESCRIPTION
        "The value of tmnxOamPmCfgLossSlmRunTimeLeft indicates the run time
         remaining for the specified session's SLM test.

         For example, suppose an SLM test has the following configuration:

         tmnxOamPmCfgSessType   tmnxOamPmCfgLossSlmTestDuration
         --------------------   --------------------------------
         'onDemand(2)'          1000 (seconds)

         Then, when the SLM test is started (see
         tmnxOamPmCfgLossSlmOnDmndStatus), tmnxOamPmCfgLossSlmRunTimeLeft is
         initialized to 1000 seconds.  After a minute,
         tmnxOamPmCfgLossSlmRunTimeLeft is 940 seconds.

         If tmnxOamPmCfgSessType is 'proactive(1)', zero is always returned
         (because a proactive test runs until it is manually stopped).

         If tmnxOamPmCfgSessType is 'onDemand(2)' and the test is stopped (see
         tmnxOamPmCfgLossSlmOnDmndStatus), zero is returned (because the test
         is not running)."
    ::= { tmnxOamPmCfgLossSlmEntry 12 }

--
-- OAM Performance Monitoring Measurement Interval Configuration Table
--

tmnxOamPmCfgMeasIntvlTable       OBJECT-TYPE
    SYNTAX      SEQUENCE OF TmnxOamPmCfgMeasIntvlEntry
    MAX-ACCESS  not-accessible
    STATUS      current
    DESCRIPTION
        "tmnxOamPmCfgMeasIntvlTable contains the configuration information for
         OAM Performance Monitoring measurement intervals."
    REFERENCE
        "MEF-35, 'Service OAM Performance Monitoring Implementation Agreement',
         Metro Ethernet Forum, April 2012, Section 9.1.6, 'Measurement
         Intervals'"
    ::= { tmnxOamPmCfgTableObjs 7 }

tmnxOamPmCfgMeasIntvlEntry       OBJECT-TYPE
    SYNTAX      TmnxOamPmCfgMeasIntvlEntry
    MAX-ACCESS  not-accessible
    STATUS      current
    DESCRIPTION
        "tmnxOamPmCfgMeasIntvlEntry contains the configuration information for
         the OAM Performance Monitoring measurement intervals associated with
         the specified session and measurement interval duration.

         Rows are created or destroyed by SNMP Set operations on
         tmnxOamPmCfgMeasIntvlRowStatus."
    INDEX {
        tmnxOamPmCfgSessName,
        tmnxOamPmCfgMeasIntvlDuration
    }
    ::= { tmnxOamPmCfgMeasIntvlTable 1 }

TmnxOamPmCfgMeasIntvlEntry       ::= SEQUENCE {
    tmnxOamPmCfgMeasIntvlDuration    TmnxOamPmCfgMeasIntervalDuration,
    tmnxOamPmCfgMeasIntvlRowStatus   RowStatus,
    tmnxOamPmCfgMeasIntvlAccntPolicy Unsigned32,
    tmnxOamPmCfgMeasIntvlsStored     Unsigned32,
    tmnxOamPmCfgMeasIntvlBoundaryTyp INTEGER,
    tmnxOamPmCfgMeasIntvlClockOffset Unsigned32
}

tmnxOamPmCfgMeasIntvlDuration    OBJECT-TYPE
    SYNTAX      TmnxOamPmCfgMeasIntervalDuration
    MAX-ACCESS  not-accessible
    STATUS      current
    DESCRIPTION
        "The value of tmnxOamPmCfgMeasIntvlDuration specifies the duration of
         the measurement interval (e.g. 'mi15Minutes(2)') to be read or
         configured."
    ::= { tmnxOamPmCfgMeasIntvlEntry 1 }

tmnxOamPmCfgMeasIntvlRowStatus   OBJECT-TYPE
    SYNTAX      RowStatus
    MAX-ACCESS  read-create
    STATUS      current
    DESCRIPTION
        "The value of tmnxOamPmCfgMeasIntvlRowStatus specifies the status of the
         configuration row for the specified session and measurement interval
         duration."
    ::= { tmnxOamPmCfgMeasIntvlEntry 2 }

tmnxOamPmCfgMeasIntvlAccntPolicy OBJECT-TYPE
    SYNTAX      Unsigned32 (0|1..99)
    MAX-ACCESS  read-create
    STATUS      current
    DESCRIPTION
        "The value of tmnxOamPmCfgMeasIntvlAccntPolicy specifies the accounting
         policy for the specified session and measurement interval duration.

         Zero specifies that the specified session and measurement interval
         duration has no associated accounting policy."
    DEFVAL { 0 }
    ::= { tmnxOamPmCfgMeasIntvlEntry 3 }

tmnxOamPmCfgMeasIntvlsStored     OBJECT-TYPE
    SYNTAX      Unsigned32 (1..96)
    MAX-ACCESS  read-create
    STATUS      current
    DESCRIPTION
        "The value of tmnxOamPmCfgMeasIntvlsStored specifies the maximum number
         of historical measurement intervals which can be read using SNMP Get
         operations.

         For example, suppose tmnxOamPmCfgMeasIntvlsStored is 32 in the row
         indexed by <'mySess1', 'mi15Minutes(2)'>.  Suppose 'mySess1' has a DMM
         test which has been running for at least 8 hours (i.e. 15
         minutes/interval * 32 intervals).  Then, the number of SNMP accessible
         15 minute intervals for the test is shown in the following table.

         Test State  Number of SNMP Accessible 15 Minute Intervals
         ----------  -----------------------------------------------------------
         running     33 (i.e. 32 historical intervals, and the current interval)
         stopped     32 (i.e. 32 historical intervals)

         At the moment when a test is stopped, the current interval becomes the
         newest historical interval.  If that makes the total number of
         historical intervals larger than tmnxOamPmCfgMeasIntvlsStored, the
         oldest historical interval is made SNMP inaccessible.

         In a typical configuration, older statistics are recorded in a local
         file (see tmnxOamPmCfgMeasIntvlAccntPolicy).  Statistics in the file
         are not SNMP accessible.

         The range and default of tmnxOamPmCfgMeasIntvlsStored varies with the
         row's measurement interval duration index value, as follows.

         tmnxOamPmCfgMeasIntvlDuration Intvls Stored Range Intvls Stored Default
         ----------------------------- ------------------- ---------------------
         'mi15Minutes(2)'                            1..96                    32
         'mi1Hour(3)'                                1..24                     8
         'mi1Day(4)'                                  1..1                     1
        "
    ::= { tmnxOamPmCfgMeasIntvlEntry 4 }

tmnxOamPmCfgMeasIntvlBoundaryTyp OBJECT-TYPE
    SYNTAX      INTEGER {
                    clockAligned(1),
                    testRelative(2)
                }
    MAX-ACCESS  read-create
    STATUS      current
    DESCRIPTION
        "The value of tmnxOamPmCfgMeasIntvlBoundaryTyp specifies whether or not
         the start of each measurement interval is aligned to the wall clock.

         Values:
            clockAligned(1)
                For example, if the specified tmnxOamPmCfgMeasIntvlDuration is
                'mi1Day(4)', the first measurement interval for the test will
                start at midnight (UTC).  See the DESCRIPTION clause for
                tmnxOamPmCfgMeasIntvlClockOffset for additional information.
            testRelative(2)
                The first measurement interval for the test will start when the
                test starts."
    DEFVAL { clockAligned }
    ::= { tmnxOamPmCfgMeasIntvlEntry 5 }

tmnxOamPmCfgMeasIntvlClockOffset OBJECT-TYPE
    SYNTAX      Unsigned32 (0..86399)
    UNITS       "seconds"
    MAX-ACCESS  read-create
    STATUS      current
    DESCRIPTION
        "The value of tmnxOamPmCfgMeasIntvlClockOffset specifies the offset (in
         seconds) for the start of a measurement interval.

         For example, the following set of values will result in each one day
         measurement interval for the specified session starting 6 seconds after
         midnight (UTC).

         Object                            Value
         --------------------------------  -----------------
         tmnxOamPmCfgMeasIntvlDuration     'mi1Day(4)'
         tmnxOamPmCfgMeasIntvlBoundaryTyp  'clockAligned(1)'
         tmnxOamPmCfgMeasIntvlClockOffset  6

         This value must be less than tmnxOamPmCfgMeasIntvlDuration (expressed
         in seconds).  For example, if tmnxOamPmCfgMeasIntvlDuration is
         'mi15Minutes(2)' (i.e. 900 seconds), this value must be in the range
         0..899.

         An attempt to set this object to a non-zero value when
         tmnxOamPmCfgMeasIntvlBoundaryTyp is 'testRelative(2)' will be
         rejected."
    DEFVAL { 0 }
    ::= { tmnxOamPmCfgMeasIntvlEntry 6 }

--
-- OAM Performance Monitoring IP Session Configuration Table
--

tmnxOamPmCfgSessIpTable          OBJECT-TYPE
    SYNTAX      SEQUENCE OF TmnxOamPmCfgSessIpEntry
    MAX-ACCESS  not-accessible
    STATUS      current
    DESCRIPTION
        "tmnxOamPmCfgSessIpTable contains the IP endpoint configuration for the
         IP tests belonging to OAM Performance Monitoring sessions."
    ::= { tmnxOamPmCfgTableObjs 8 }

tmnxOamPmCfgSessIpEntry          OBJECT-TYPE
    SYNTAX      TmnxOamPmCfgSessIpEntry
    MAX-ACCESS  not-accessible
    STATUS      current
    DESCRIPTION
        "tmnxOamPmCfgSessIpEntry contains the IP endpoint configuration for the
         IP tests belonging to one OAM Performance Monitoring session.

         A row is created when a tmnxOamPmCfgSessTable row is created with
         tmnxOamPmCfgSessTestFamily = 'ip(2)'.

         A row is destroyed when a tmnxOamPmCfgSessTable row with
         tmnxOamPmCfgSessTestFamily = 'ip(2)' is destroyed.

         An attempt to change a value in a row for a particular session will be
         rejected if an administratively enabled test (e.g. a TWAMP-Light test)
         exists for the session."
    INDEX {
        tmnxOamPmCfgSessName
    }
    ::= { tmnxOamPmCfgSessIpTable 1 }

TmnxOamPmCfgSessIpEntry          ::= SEQUENCE {
    tmnxOamPmCfgSessIpServiceId      Unsigned32,
    tmnxOamPmCfgSessIpSrcAddressType InetAddressType,
    tmnxOamPmCfgSessIpSrcAddress     InetAddress,
    tmnxOamPmCfgSessIpDstAddressType InetAddressType,
    tmnxOamPmCfgSessIpDstAddress     InetAddress,
    tmnxOamPmCfgSessIpDstUdpPort     InetPortNumber,
    tmnxOamPmCfgSessIpBypassRouting  TruthValue,
    tmnxOamPmCfgSessIpEgressIfName   TNamedItemOrEmpty,
    tmnxOamPmCfgSessIpNhAddressType  InetAddressType,
    tmnxOamPmCfgSessIpNhAddress      InetAddress,
    tmnxOamPmCfgSessIpForwardClass   TFCName,
    tmnxOamPmCfgSessIpProfile        TProfile,
    tmnxOamPmCfgSessIpTtl            Unsigned32
}

tmnxOamPmCfgSessIpServiceId      OBJECT-TYPE
    SYNTAX      Unsigned32 (0..2147483647)
    MAX-ACCESS  read-write
    STATUS      current
    DESCRIPTION
        "The value of tmnxOamPmCfgSessIpServiceId specifies the virtual router
         to be used by IP tests belonging to the specified session.

         Zero specifies the Base virtual router, as defined in
         TIMETRA-VRTR-MIB::vRtrConfTable.

         A value larger than zero must be the service identifier of a VPRN
         service (as configured by setting TIMETRA-SERV-MIB::svcType to
         'vprn(4)')."
    DEFVAL { 0 }
    ::= { tmnxOamPmCfgSessIpEntry 1 }

tmnxOamPmCfgSessIpSrcAddressType OBJECT-TYPE
    SYNTAX      InetAddressType
    MAX-ACCESS  read-write
    STATUS      current
    DESCRIPTION
        "The value of tmnxOamPmCfgSessIpSrcAddressType specifies the address
         type of tmnxOamPmCfgSessIpSrcAddress."
    DEFVAL { unknown }
    ::= { tmnxOamPmCfgSessIpEntry 2 }

tmnxOamPmCfgSessIpSrcAddress     OBJECT-TYPE
    SYNTAX      InetAddress (SIZE (0|4|16))
    MAX-ACCESS  read-write
    STATUS      current
    DESCRIPTION
        "The value of tmnxOamPmCfgSessIpSrcAddress specifies the source IP
         address to be used by IP tests belonging to the specified session.

         tmnxOamPmCfgSessIpSrcAddressType and tmnxOamPmCfgSessIpSrcAddress must
         be set in one SNMP PDU."
    DEFVAL { ''H }
    ::= { tmnxOamPmCfgSessIpEntry 3 }

tmnxOamPmCfgSessIpDstAddressType OBJECT-TYPE
    SYNTAX      InetAddressType
    MAX-ACCESS  read-write
    STATUS      current
    DESCRIPTION
        "The value of tmnxOamPmCfgSessIpDstAddressType specifies the address
         type of tmnxOamPmCfgSessIpDstAddress."
    DEFVAL { unknown }
    ::= { tmnxOamPmCfgSessIpEntry 4 }

tmnxOamPmCfgSessIpDstAddress     OBJECT-TYPE
    SYNTAX      InetAddress (SIZE (0|4|16))
    MAX-ACCESS  read-write
    STATUS      current
    DESCRIPTION
        "The value of tmnxOamPmCfgSessIpDstAddress specifies the destination IP
         address to be used by IP tests belonging to the specified session.

         tmnxOamPmCfgSessIpDstAddressType and tmnxOamPmCfgSessIpDstAddress must
         be set in one SNMP PDU."
    DEFVAL { ''H }
    ::= { tmnxOamPmCfgSessIpEntry 5 }

tmnxOamPmCfgSessIpDstUdpPort     OBJECT-TYPE
    SYNTAX      InetPortNumber(0 | 1024..65535)
    MAX-ACCESS  read-write
    STATUS      current
    DESCRIPTION
        "The value of tmnxOamPmCfgSessIpDstUdpPort specifies the destination UDP
         port to be used by IP tests belonging to the specified session.

         Zero indicates that no destination UDP port has been configured."
    DEFVAL { 0 }
    ::= { tmnxOamPmCfgSessIpEntry 6 }

tmnxOamPmCfgSessIpBypassRouting  OBJECT-TYPE
    SYNTAX      TruthValue
    MAX-ACCESS  read-write
    STATUS      current
    DESCRIPTION
        "The value of tmnxOamPmCfgSessIpBypassRouting specifies whether or not
         to send the ping request (for an IP test which belongs to the specified
         session) to a host on a directly attached network, bypassing the
         routing table.

         At most one of tmnxOamPmCfgSessIpBypassRouting,
         tmnxOamPmCfgSessIpEgressIfName, and tmnxOamPmCfgSessIpNhAddress can be
         set to a non-default value."
    DEFVAL { false }
    ::= { tmnxOamPmCfgSessIpEntry 7 }

tmnxOamPmCfgSessIpEgressIfName   OBJECT-TYPE
    SYNTAX      TNamedItemOrEmpty
    MAX-ACCESS  read-write
    STATUS      current
    DESCRIPTION
        "The value of tmnxOamPmCfgSessIpEgressIfName specifies the name of the
         interface to be used to transmit a ping request (for an IP test which
         belongs to the specified session).

         At most one of tmnxOamPmCfgSessIpBypassRouting,
         tmnxOamPmCfgSessIpEgressIfName, and tmnxOamPmCfgSessIpNhAddress can be
         set to a non-default value."
    DEFVAL { ''H }
    ::= { tmnxOamPmCfgSessIpEntry 8 }

tmnxOamPmCfgSessIpNhAddressType  OBJECT-TYPE
    SYNTAX      InetAddressType
    MAX-ACCESS  read-write
    STATUS      current
    DESCRIPTION
        "The value of tmnxOamPmCfgSessIpNhAddressType specifies the address
         type of tmnxOamPmCfgSessIpNhAddress."
    DEFVAL { unknown }
    ::= { tmnxOamPmCfgSessIpEntry 9 }

tmnxOamPmCfgSessIpNhAddress      OBJECT-TYPE
    SYNTAX      InetAddress (SIZE (0|4|16))
    MAX-ACCESS  read-write
    STATUS      current
    DESCRIPTION
        "The value of tmnxOamPmCfgSessIpNhAddress specifies the next-hop IP
         address to be used by IP tests belonging to the specified session.

         tmnxOamPmCfgSessIpNhAddressType and tmnxOamPmCfgSessIpNhAddress must
         be set in one SNMP PDU.

         At most one of tmnxOamPmCfgSessIpBypassRouting,
         tmnxOamPmCfgSessIpEgressIfName, and tmnxOamPmCfgSessIpNhAddress can be
         set to a non-default value."
    DEFVAL { ''H }
    ::= { tmnxOamPmCfgSessIpEntry 10 }

tmnxOamPmCfgSessIpForwardClass   OBJECT-TYPE
    SYNTAX      TFCName
    MAX-ACCESS  read-create
    STATUS      current
    DESCRIPTION
        "The value of tmnxOamPmCfgSessIpForwardClass specifies the forwarding
         class name to be used when launching a ping request for an IP test
         belonging to the specified session.  The forwarding class name must be
         present in the index column of TIMETRA-QOS-MIB::tFCNameTable."
    DEFVAL { "be" }
    ::= { tmnxOamPmCfgSessIpEntry 11 }

tmnxOamPmCfgSessIpProfile        OBJECT-TYPE
    SYNTAX      TProfile
    MAX-ACCESS  read-create
    STATUS      current
    DESCRIPTION
        "The value of tmnxOamPmCfgSessIpProfile specifies the profile to be used
         when launching a ping request for an IP test belonging to the specified
         session."
    DEFVAL { out }
    ::= { tmnxOamPmCfgSessIpEntry 12 }

tmnxOamPmCfgSessIpTtl            OBJECT-TYPE
    SYNTAX      Unsigned32(1..255)
    MAX-ACCESS  read-create
    STATUS      current
    DESCRIPTION
        "The value of tmnxOamPmCfgSessIpTtl specifies the time-to-live to be
         used when launching a ping request for an IP test belonging to the
         specified session."
    DEFVAL { 255 }
    ::= { tmnxOamPmCfgSessIpEntry 13 }

--
-- OAM Performance Monitoring TWAMP-Light Test Configuration Table
--

tmnxOamPmCfgTwampLtTable         OBJECT-TYPE
    SYNTAX      SEQUENCE OF TmnxOamPmCfgTwampLtEntry
    MAX-ACCESS  not-accessible
    STATUS      current
    DESCRIPTION
        "tmnxOamPmCfgTwampLtTable contains the configuration information for OAM
         Performance Monitoring TWAMP-Light (Two-Way Active Measurement
         Protocol, Light) tests."
    REFERENCE
        "RFC 5357, 'A Two-Way Active Measurement Protocol (TWAMP)', Appendix I,
        'TWAMP Light'."
    ::= { tmnxOamPmCfgTableObjs 9 }

tmnxOamPmCfgTwampLtEntry         OBJECT-TYPE
    SYNTAX      TmnxOamPmCfgTwampLtEntry
    MAX-ACCESS  not-accessible
    STATUS      current
    DESCRIPTION
        "tmnxOamPmCfgTwampLtEntry contains the configuration information for the
         OAM Performance Monitoring TWAMP-Light test for the specified session.

         Rows are created or destroyed by SNMP Set operations on
         tmnxOamPmCfgTwampLtRowStatus.

         An attempt to change any value in a row (except
         tmnxOamPmCfgTwampLtAdminStatus and tmnxOamPmCfgTwampLtOnDmndStatus)
         will be rejected if tmnxOamPmCfgTwampLtAdminStatus is 'enabled(1)'."
    INDEX {
        tmnxOamPmCfgSessName
    }
    ::= { tmnxOamPmCfgTwampLtTable 1 }

TmnxOamPmCfgTwampLtEntry         ::= SEQUENCE {
    tmnxOamPmCfgTwampLtRowStatus     RowStatus,
    tmnxOamPmCfgTwampLtAdminStatus   TmnxEnabledDisabled,
    tmnxOamPmCfgTwampLtOnDmndStatus  TmnxEnabledDisabledOrNA,
    tmnxOamPmCfgTwampLtTestId        Unsigned32,
    tmnxOamPmCfgTwampLtInterval      Unsigned32,
    tmnxOamPmCfgTwampLtPadSize       Unsigned32,
    tmnxOamPmCfgTwampLtTestDuration  Unsigned32,
    tmnxOamPmCfgTwampLtRunTimeLeft   Unsigned32
}

tmnxOamPmCfgTwampLtRowStatus     OBJECT-TYPE
    SYNTAX      RowStatus
    MAX-ACCESS  read-create
    STATUS      current
    DESCRIPTION
        "The value of tmnxOamPmCfgTwampLtRowStatus specifies the status of the
         configuration row for the specified session's TWAMP-Light test.

         An attempt to create a row for a session with
         tmnxOamPmCfgSessTestFamily other than 'ip(2)' will be rejected."
    ::= { tmnxOamPmCfgTwampLtEntry 1 }

tmnxOamPmCfgTwampLtAdminStatus   OBJECT-TYPE
    SYNTAX      TmnxEnabledDisabled
    MAX-ACCESS  read-create
    STATUS      current
    DESCRIPTION
        "The value of tmnxOamPmCfgTwampLtAdminStatus specifies whether or not
         the specified session's TWAMP-Light test is administratively enabled.

         If the session type (tmnxOamPmCfgSessType) is 'proactive(1)', setting
         tmnxOamPmCfgTwampLtAdminStatus to 'enabled(1)'/'disabled(2)'
         starts/stops the test.

         If the session type is 'onDemand(2)', see the DESCRIPTION clause for
         tmnxOamPmCfgTwampLtOnDmndStatus for information on starting/stopping
         the test.

         An attempt to set this object to 'enabled(1)' will be rejected if the
         tmnxOamPmCfgSessIpTable row for the specified session has incomplete
         information for the test (e.g. if tmnxOamPmCfgSessIpSrcAddressType is
         'unknown(0)')."
    DEFVAL { disabled }
    ::= { tmnxOamPmCfgTwampLtEntry 2 }

tmnxOamPmCfgTwampLtOnDmndStatus  OBJECT-TYPE
    SYNTAX      TmnxEnabledDisabledOrNA
    MAX-ACCESS  read-create
    STATUS      current
    DESCRIPTION
        "The value of tmnxOamPmCfgTwampLtOnDmndStatus specifies the status of
         the on-demand TWAMP-Light test for the specified session.

         Values:
            'enabled(1)'
                Set by an SNMP manager to start an on-demand TWAMP-Light test.
                The test will start if tmnxOamPmCfgTwampLtAdminStatus is
                'enabled(1)'.
            'disabled(2)'
                Set by an SNMP manager to stop an on-demand TWAMP-Light test.
                Set by SROS to indicate an on-demand TWAMP-Light test has
                stopped running because the configured period for the test (i.e.
                tmnxOamPmCfgTwampLtTestDuration) has ended.
                Set by SROS for an on-demand TWAMP-Light test when
                tmnxOamPmCfgTwampLtAdminStatus is set to 'disabled(2)'.
            'notApplicable(3)'
                This code point is the only acceptable value for a proactive
                TWAMP-Light test.  An attempt to set this code point for an
                on-demand TWAMP-Light test will be rejected.

         The default value is 'disabled(2)' for an on-demand TWAMP-Light test,
         and 'notApplicable(3)' for a proactive TWAMP-Light test."
    ::= { tmnxOamPmCfgTwampLtEntry 3 }

tmnxOamPmCfgTwampLtTestId        OBJECT-TYPE
    SYNTAX      Unsigned32(0..2147483647)
    MAX-ACCESS  read-create
    STATUS      current
    DESCRIPTION
        "The value of tmnxOamPmCfgTwampLtTestId specifies the test identifier
         for the specified session's TWAMP-Light test.

         When a TWAMP-Light test is created, tmnxOamPmCfgTwampLtRowStatus and
         tmnxOamPmCfgTwampLtTestId must be specified in the same SNMP Set PDU.

         An attempt to add a duplicate test identifier to this table will be
         rejected.

         Test identifier values larger than 2147483647 are reserved for internal
         use."
    ::= { tmnxOamPmCfgTwampLtEntry 4 }

tmnxOamPmCfgTwampLtInterval      OBJECT-TYPE
    SYNTAX      Unsigned32(100|1000)
    UNITS       "milliseconds"
    MAX-ACCESS  read-create
    STATUS      current
    DESCRIPTION
        "The value of tmnxOamPmCfgTwampLtInterval specifies the elapsed time
         between transmission of TWAMP-Test PDUs for the specified session's
         TWAMP-Light test."
    DEFVAL { 1000 }
    ::= { tmnxOamPmCfgTwampLtEntry 5 }

tmnxOamPmCfgTwampLtPadSize       OBJECT-TYPE
    SYNTAX      Unsigned32(0..2000)
    UNITS       "octets"
    MAX-ACCESS  read-create
    STATUS      current
    DESCRIPTION
        "The value of tmnxOamPmCfgTwampLtPadSize specifies the amount of padding
         to be added to each launched TWAMP-Test PDU for the specified session's
         TWAMP-Light test."
    REFERENCE
        "RFC 5357, 'A Two-Way Active Measurement Protocol (TWAMP)', Section
         4.1.2, 'Packet Format and Content'."
    DEFVAL { 0 }
    ::= { tmnxOamPmCfgTwampLtEntry 6 }

tmnxOamPmCfgTwampLtTestDuration  OBJECT-TYPE
    SYNTAX      Unsigned32 (0..86400)
    UNITS       "seconds"
    MAX-ACCESS  read-create
    STATUS      current
    DESCRIPTION
        "The value of tmnxOamPmCfgTwampLtTestDuration specifies the test
         duration for the specified session's TWAMP-Light test.

         Zero specifies a test which runs until it is manually stopped.

         An attempt to set a non-zero value will be rejected if
         tmnxOamPmCfgSessType is 'proactive(1)'."
    DEFVAL { 0 }
    ::= { tmnxOamPmCfgTwampLtEntry 7 }

tmnxOamPmCfgTwampLtRunTimeLeft   OBJECT-TYPE
    SYNTAX      Unsigned32 (0..86400)
    UNITS       "seconds"
    MAX-ACCESS  read-only
    STATUS      current
    DESCRIPTION
        "The value of tmnxOamPmCfgTwampLtRunTimeLeft indicates the run time
         remaining for the specified session's TWAMP-Light test.

         For example, suppose a TWAMP-Light test has the following
         configuration:

         tmnxOamPmCfgSessType   tmnxOamPmCfgTwampLtTestDuration
         --------------------   -------------------------------
         'onDemand(2)'          1000 (seconds)

         Then, when the TWAMP-Light test is started (see
         tmnxOamPmCfgTwampLtOnDmndStatus), tmnxOamPmCfgTwampLtRunTimeLeft is
         initialized to 1000 seconds.  After a minute,
         tmnxOamPmCfgTwampLtRunTimeLeft is 940 seconds.

         If tmnxOamPmCfgSessType is 'proactive(1)', zero is always returned
         (because a proactive test runs until it is manually stopped).

         If tmnxOamPmCfgSessType is 'onDemand(2)' and the test is stopped (see
         tmnxOamPmCfgTwampLtOnDmndStatus), zero is returned (because the test
         is not running)."
    ::= { tmnxOamPmCfgTwampLtEntry 8 }

--
-- OAM Performance Monitoring TWAMP-Light Reflector Configuration Table
--

tmnxOamPmCfgTwlRflTable          OBJECT-TYPE
    SYNTAX      SEQUENCE OF TmnxOamPmCfgTwlRflEntry
    MAX-ACCESS  not-accessible
    STATUS      current
    DESCRIPTION
        "tmnxOamPmCfgTwlRflTable contains the configuration information for OAM
         Performance Monitoring TWAMP-Light (Two-Way Active Measurement
         Protocol, Light) reflectors.

         A TWAMP-Light reflector responds to TWAMP-Test frames."
    REFERENCE
        "RFC 5357, 'A Two-Way Active Measurement Protocol (TWAMP)', Appendix I,
        'TWAMP Light'."
    ::= { tmnxOamPmCfgTableObjs 10 }

tmnxOamPmCfgTwlRflEntry          OBJECT-TYPE
    SYNTAX      TmnxOamPmCfgTwlRflEntry
    MAX-ACCESS  not-accessible
    STATUS      current
    DESCRIPTION
        "tmnxOamPmCfgTwlRflEntry contains the configuration information for the
         OAM Performance Monitoring TWAMP-Light reflector for the virtual router
         specified by the given service identifier.

         Service identifier zero specifies the Base virtual router (i.e. the
         virtual router with TIMETRA-VRTR-MIB::vRtrName = 'Base').

         A service identifier larger than zero must be the service identifier of
         a VPRN service (i.e. a service with
         TIMETRA-SERV-MIB::svcType = 'vprn(4)').

         Rows are created or destroyed by SNMP Set operations on
         tmnxOamPmCfgTwlRflRowStatus.

         A row indexed by a VPRN service identifier is destroyed when the VPRN
         service is destroyed."
    INDEX {
        svcId
    }
    ::= { tmnxOamPmCfgTwlRflTable 1 }

TmnxOamPmCfgTwlRflEntry          ::= SEQUENCE {
    tmnxOamPmCfgTwlRflRowStatus      RowStatus,
    tmnxOamPmCfgTwlRflAdminStatus    TmnxEnabledDisabled,
    tmnxOamPmCfgTwlRflDescription    TItemDescription,
    tmnxOamPmCfgTwlRflListenUdpPort  Unsigned32
}

tmnxOamPmCfgTwlRflRowStatus      OBJECT-TYPE
    SYNTAX      RowStatus
    MAX-ACCESS  read-create
    STATUS      current
    DESCRIPTION
        "The value of tmnxOamPmCfgTwlRflRowStatus specifies the status of the
         configuration row for the TWAMP-Light reflector for the virtual router
         specified by the given service identifier.

         When a reflector is created, tmnxOamPmCfgTwlRflRowStatus and
         tmnxOamPmCfgTwlRflListenUdpPort must be specified in the same SNMP Set
         PDU."
    ::= { tmnxOamPmCfgTwlRflEntry 1 }

tmnxOamPmCfgTwlRflAdminStatus    OBJECT-TYPE
    SYNTAX      TmnxEnabledDisabled
    MAX-ACCESS  read-create
    STATUS      current
    DESCRIPTION
        "The value of tmnxOamPmCfgTwlRflAdminStatus specifies whether or not the
         specified TWAMP-Light reflector is administratively enabled.

         tmnxOamPmCfgTwlRflListenUdpPort cannot be changed while
         tmnxOamPmCfgTwlRflAdminStatus is 'enabled(1)'."
    DEFVAL { disabled }
    ::= { tmnxOamPmCfgTwlRflEntry 2 }

tmnxOamPmCfgTwlRflDescription    OBJECT-TYPE
    SYNTAX      TItemDescription
    MAX-ACCESS  read-create
    STATUS      current
    DESCRIPTION
        "The value of tmnxOamPmCfgTwlRflDescription specifies the descriptive
         text for the specified TWAMP-Light reflector."
    DEFVAL { "" }
    ::= { tmnxOamPmCfgTwlRflEntry 3 }

tmnxOamPmCfgTwlRflListenUdpPort  OBJECT-TYPE
    SYNTAX      Unsigned32(1024..65535)
    MAX-ACCESS  read-create
    STATUS      current
    DESCRIPTION
        "The value of tmnxOamPmCfgTwlRflListenUdpPort specifies the UDP port on
         which the specified TWAMP-Light reflector listens for TWAMP PDUs.

         When a reflector is created, tmnxOamPmCfgTwlRflRowStatus and
         tmnxOamPmCfgTwlRflListenUdpPort must be specified in the same SNMP Set
         PDU.

         tmnxOamPmCfgTwlRflListenUdpPort cannot be changed while
         tmnxOamPmCfgTwlRflAdminStatus is 'enabled(1)'."
    ::= { tmnxOamPmCfgTwlRflEntry 4 }

--
-- OAM Performance Monitoring TWAMP-Light Reflector Prefix Configuration Table
--

tmnxOamPmCfgTwlRflPfxTable       OBJECT-TYPE
    SYNTAX      SEQUENCE OF TmnxOamPmCfgTwlRflPfxEntry
    MAX-ACCESS  not-accessible
    STATUS      current
    DESCRIPTION
        "tmnxOamPmCfgTwlRflPfxTable contains the configuration information for
         OAM Performance Monitoring TWAMP-Light (Two-Way Active Measurement
         Protocol, Light) reflector prefixes.

         The set of prefixes configured for a TWAMP-Light reflector defines a
         set of valid source addresses for the reflector.  When the reflector is
         validating an incoming TWAMP-Test PDU, the PDU is rejected (and
         counted) if its source address is invalid."
    REFERENCE
        "RFC 5357, 'A Two-Way Active Measurement Protocol (TWAMP)', Appendix I,
        'TWAMP Light'."
    ::= { tmnxOamPmCfgTableObjs 11 }

tmnxOamPmCfgTwlRflPfxEntry       OBJECT-TYPE
    SYNTAX      TmnxOamPmCfgTwlRflPfxEntry
    MAX-ACCESS  not-accessible
    STATUS      current
    DESCRIPTION
        "tmnxOamPmCfgTwlRflPfxEntry contains the configuration information for
         the OAM Performance Monitoring TWAMP-Light reflector prefix specified
         by the indices.

         Rows are created or destroyed by SNMP Set operations on
         tmnxOamPmCfgTwlRflPfxRowStatus.

         Rows are destroyed when the corresponding tmnxOamPmCfgTwlRflTable row
         is destroyed."
    INDEX {
        svcId,
        tmnxOamPmCfgTwlRflPfxPrefixType,
        tmnxOamPmCfgTwlRflPfxPrefix,
        tmnxOamPmCfgTwlRflPfxPrefixLen
    }
    ::= { tmnxOamPmCfgTwlRflPfxTable 1 }

TmnxOamPmCfgTwlRflPfxEntry       ::= SEQUENCE {
    tmnxOamPmCfgTwlRflPfxPrefixType  InetAddressType,
    tmnxOamPmCfgTwlRflPfxPrefix      InetAddress,
    tmnxOamPmCfgTwlRflPfxPrefixLen   InetAddressPrefixLength,
    tmnxOamPmCfgTwlRflPfxRowStatus   RowStatus,
    tmnxOamPmCfgTwlRflPfxDescription TItemDescription
}

tmnxOamPmCfgTwlRflPfxPrefixType  OBJECT-TYPE
    SYNTAX      InetAddressType (1|2)
    MAX-ACCESS  not-accessible
    STATUS      current
    DESCRIPTION
        "The value of tmnxOamPmCfgTwlRflPfxPrefixType specifies the prefix type
         of tmnxOamPmCfgTwlRflPfxPrefix."
    ::= { tmnxOamPmCfgTwlRflPfxEntry 1 }

tmnxOamPmCfgTwlRflPfxPrefix      OBJECT-TYPE
    SYNTAX      InetAddress (SIZE (4|16))
    MAX-ACCESS  not-accessible
    STATUS      current
    DESCRIPTION
        "The value of tmnxOamPmCfgTwlRflPfxPrefix (in combination with
         tmnxOamPmCfgTwlRflPfxPrefixType and tmnxOamPmCfgTwlRflPfxPrefixLen)
         specifies a valid source prefix for the TWAMP-Light reflector specified
         by the given service identifier.

         A TWAMP-Test PDU with an invalid source address (i.e. a source address
         which matches none of the prefixes configured against the reflector)
         will be counted and dropped by the reflector.  Therefore, if no
         prefixes are configured against a reflector, the reflector will drop
         and count all incoming PDUs.

         Configuring the prefix 0.0.0.0/0 instructs the reflector to accept the
         source address in each incoming IPv4 TWAMP-Test PDU.

         Configuring the prefix 0::0/0 instructs the reflector to accept the
         source address in each incoming IPv6 TWAMP-Test PDU."
    ::= { tmnxOamPmCfgTwlRflPfxEntry 2 }

tmnxOamPmCfgTwlRflPfxPrefixLen   OBJECT-TYPE
    SYNTAX      InetAddressPrefixLength (0..128)
    MAX-ACCESS  not-accessible
    STATUS      current
    DESCRIPTION
        "The value of tmnxOamPmCfgTwlRflPfxPrefixLen (in combination with
         tmnxOamPmCfgTwlRflPfxPrefixType and tmnxOamPmCfgTwlRflPfxPrefix)
         specifies a valid source prefix for the TWAMP-Light reflector specified
         by the given service identifier."
    ::= { tmnxOamPmCfgTwlRflPfxEntry 3 }

tmnxOamPmCfgTwlRflPfxRowStatus   OBJECT-TYPE
    SYNTAX      RowStatus
    MAX-ACCESS  read-create
    STATUS      current
    DESCRIPTION
        "The value of tmnxOamPmCfgTwlRflPfxRowStatus specifies the status of the
         configuration row for the specified TWAMP-Light reflector prefix.

         An attempt to create a row will be rejected if there is no row with the
         same svcId in tmnxOamPmCfgTwlRflTable."
    ::= { tmnxOamPmCfgTwlRflPfxEntry 4 }

tmnxOamPmCfgTwlRflPfxDescription OBJECT-TYPE
    SYNTAX      TItemDescription
    MAX-ACCESS  read-create
    STATUS      current
    DESCRIPTION
        "The value of tmnxOamPmCfgTwlRflPfxDescription specifies the descriptive
         text for the specified TWAMP-Light reflector prefix."
    DEFVAL { "" }
    ::= { tmnxOamPmCfgTwlRflPfxEntry 5 }

--
-- OAM Performance Monitoring Ethernet LMM Loss Test Configuration Table
--

tmnxOamPmCfgLossLmmTable         OBJECT-TYPE
    SYNTAX      SEQUENCE OF TmnxOamPmCfgLossLmmEntry
    MAX-ACCESS  not-accessible
    STATUS      current
    DESCRIPTION
        "tmnxOamPmCfgLossLmmTable contains the configuration information for
         OAM Performance Monitoring Loss Measurement Message (LMM) tests."
    REFERENCE
        "ITU-T G.8013/Y.1731, 'OAM functions and mechanisms for Ethernet based
         networks', 07/2011, Section 8.1 'Frame loss measurement (ETH-LM)'."
    ::= { tmnxOamPmCfgTableObjs 12 }

tmnxOamPmCfgLossLmmEntry         OBJECT-TYPE
    SYNTAX      TmnxOamPmCfgLossLmmEntry
    MAX-ACCESS  not-accessible
    STATUS      current
    DESCRIPTION
        "tmnxOamPmCfgLossLmmEntry contains the configuration information for one
         OAM Performance Monitoring Loss Measurement Message (LMM) test.

         Rows are created or destroyed by SNMP Set operations on
         tmnxOamPmCfgLossLmmRowStatus.

         An attempt to change any value in a row (except
         tmnxOamPmCfgLossLmmAdminStatus and tmnxOamPmCfgLossLmmOnDmndStatus)
         will be rejected if tmnxOamPmCfgLossLmmAdminStatus is 'enabled(1)'."
    INDEX {
        tmnxOamPmCfgSessName
    }
    ::= { tmnxOamPmCfgLossLmmTable 1 }

TmnxOamPmCfgLossLmmEntry         ::= SEQUENCE {
    tmnxOamPmCfgLossLmmRowStatus     RowStatus,
    tmnxOamPmCfgLossLmmAdminStatus   TmnxEnabledDisabled,
    tmnxOamPmCfgLossLmmOnDmndStatus  TmnxEnabledDisabledOrNA,
    tmnxOamPmCfgLossLmmTestId        Unsigned32,
    tmnxOamPmCfgLossLmmInterval      Unsigned32,
    tmnxOamPmCfgLossLmmTestDuration  Unsigned32,
    tmnxOamPmCfgLossLmmRunTimeLeft   Unsigned32
}

tmnxOamPmCfgLossLmmRowStatus     OBJECT-TYPE
    SYNTAX      RowStatus
    MAX-ACCESS  read-create
    STATUS      current
    DESCRIPTION
        "The value of tmnxOamPmCfgLossLmmRowStatus specifies the status of the
         configuration row for the specified session's LMM test.

         An attempt to create a row for a session with
         tmnxOamPmCfgSessTestFamily other than 'ethernet(1)' will be rejected."
    ::= { tmnxOamPmCfgLossLmmEntry 1 }

tmnxOamPmCfgLossLmmAdminStatus   OBJECT-TYPE
    SYNTAX      TmnxEnabledDisabled
    MAX-ACCESS  read-create
    STATUS      current
    DESCRIPTION
        "The value of tmnxOamPmCfgLossLmmAdminStatus specifies whether or not
         the specified session's LMM test is administratively enabled.

         If the session type (tmnxOamPmCfgSessType) is 'proactive(1)', setting
         tmnxOamPmCfgLossLmmAdminStatus to 'enabled(1)'/'disabled(2)'
         starts/stops the test.

         If the session type is 'onDemand(2)', see the DESCRIPTION clause for
         tmnxOamPmCfgLossLmmOnDmndStatus for information on starting/stopping
         the test.

         An attempt to set this object to 'enabled(1)' will be rejected if the
         tmnxOamPmCfgSessEthTable row for the specified session has incomplete
         endpoint information for the test (e.g. if
         tmnxOamPmCfgSessEthDestMacAddr is the all-zeroes MAC address)."
    DEFVAL { disabled }
    ::= { tmnxOamPmCfgLossLmmEntry 2 }

tmnxOamPmCfgLossLmmOnDmndStatus  OBJECT-TYPE
    SYNTAX      TmnxEnabledDisabledOrNA
    MAX-ACCESS  read-create
    STATUS      current
    DESCRIPTION
        "The value of tmnxOamPmCfgLossLmmOnDmndStatus specifies the status of
         the on-demand LMM test for the specified session.

         Values:
            'enabled(1)'
                Set by an SNMP manager to start an on-demand LMM test.  The test
                will start if tmnxOamPmCfgLossLmmAdminStatus is 'enabled(1)'.
            'disabled(2)'
                Set by an SNMP manager to stop an on-demand LMM test.
                Set by SROS to indicate an on-demand LMM test has stopped
                running because the configured period for the test (i.e.
                tmnxOamPmCfgLossLmmTestDuration) has ended.
                Set by SROS for an on-demand LMM test when
                tmnxOamPmCfgLossLmmAdminStatus is set to 'disabled(2)'.
            'notApplicable(3)'
                This code point is the only acceptable value for a proactive LMM
                test.  An attempt to set this code point for an on-demand LMM
                test will be rejected.

         The default value is 'disabled(2)' for an on-demand LMM test, and
         'notApplicable(3)' for a proactive LMM test."
    ::= { tmnxOamPmCfgLossLmmEntry 3 }

tmnxOamPmCfgLossLmmTestId        OBJECT-TYPE
    SYNTAX      Unsigned32(0..2147483647)
    MAX-ACCESS  read-create
    STATUS      current
    DESCRIPTION
        "The value of tmnxOamPmCfgLossLmmTestId specifies the test identifier
         for the specified session's LMM test.

         When an LMM test is created, tmnxOamPmCfgLossLmmRowStatus and
         tmnxOamPmCfgLossLmmTestId must be specified in the same SNMP Set PDU.

         An attempt to add a duplicate test identifier to this table will be
         rejected.

         Test identifier values larger than 2147483647 are reserved for internal
         use."
    ::= { tmnxOamPmCfgLossLmmEntry 4 }

tmnxOamPmCfgLossLmmInterval      OBJECT-TYPE
    SYNTAX      Unsigned32(100|1000|10000)
    UNITS       "milliseconds"
    MAX-ACCESS  read-create
    STATUS      current
    DESCRIPTION
        "The value of tmnxOamPmCfgLossLmmInterval specifies the elapsed time
         between transmission of Y.1731 LMM PDUs for the specified session's LMM
         test."
    DEFVAL { 1000 }
    ::= { tmnxOamPmCfgLossLmmEntry 5 }

tmnxOamPmCfgLossLmmTestDuration  OBJECT-TYPE
    SYNTAX      Unsigned32 (0..86400)
    UNITS       "seconds"
    MAX-ACCESS  read-create
    STATUS      current
    DESCRIPTION
        "The value of tmnxOamPmCfgLossLmmTestDuration specifies the test
         duration for the specified session's LMM test.

         Zero specifies a test which runs until it is manually stopped.

         An attempt to set a non-zero value will be rejected if
         tmnxOamPmCfgSessType is 'proactive(1)'."
    DEFVAL { 0 }
    ::= { tmnxOamPmCfgLossLmmEntry 6 }

tmnxOamPmCfgLossLmmRunTimeLeft   OBJECT-TYPE
    SYNTAX      Unsigned32 (0..86400)
    UNITS       "seconds"
    MAX-ACCESS  read-only
    STATUS      current
    DESCRIPTION
        "The value of tmnxOamPmCfgLossLmmRunTimeLeft indicates the run time
         remaining for the specified session's LMM test.

         For example, suppose an LMM test has the following configuration:

         tmnxOamPmCfgSessType   tmnxOamPmCfgLossLmmTestDuration
         --------------------   --------------------------------
         'onDemand(2)'          1000 (seconds)

         Then, when the LMM test is started (see
         tmnxOamPmCfgLossLmmOnDmndStatus), tmnxOamPmCfgLossLmmRunTimeLeft is
         initialized to 1000 seconds.  After a minute,
         tmnxOamPmCfgLossLmmRunTimeLeft is 940 seconds.

         If tmnxOamPmCfgSessType is 'proactive(1)', zero is always returned
         (because a proactive test runs until it is manually stopped).

         If tmnxOamPmCfgSessType is 'onDemand(2)' and the test is stopped (see
         tmnxOamPmCfgLossLmmOnDmndStatus), zero is returned (because the test
         is not running)."
    ::= { tmnxOamPmCfgLossLmmEntry 7 }

-- #############################################################################
-- Statistics Scalars
-- #############################################################################

-- #############################################################################
-- Statistics Tables
-- #############################################################################

--
-- OAM Performance Monitoring Statistics Base Table
--

tmnxOamPmStsBaseTable            OBJECT-TYPE
    SYNTAX      SEQUENCE OF TmnxOamPmStsBaseEntry
    MAX-ACCESS  not-accessible
    STATUS      current
    DESCRIPTION
        "tmnxOamPmStsBaseTable contains the base statistics for OAM
         Performance Monitoring Measurement Interval Data Sets.  The statistics
         in this table are common to all test types (e.g. Delay Measurement and
         Synthetic Loss Measurement tests)."
    REFERENCE
        "MEF-35, 'Service OAM Performance Monitoring Implementation Agreement',
         Metro Ethernet Forum, April 2012, Section 9.2.1 'Measurement Interval
         Data Sets'"
    ::= { tmnxOamPmStatsTableObjs 1 }

tmnxOamPmStsBaseEntry            OBJECT-TYPE
    SYNTAX      TmnxOamPmStsBaseEntry
    MAX-ACCESS  not-accessible
    STATUS      current
    DESCRIPTION
        "tmnxOamPmStsBaseEntry contains the base statistics for one OAM
         Performance Monitoring Measurement Interval Data Set.

         Rows are created in this table when a test is started (e.g. using
         tmnxOamPmCfgDelayDmmAdminStatus and tmnxOamPmCfgDelayDmmOnDmndStatus).
         At that time, a row for the current interval (with the index value
         tmnxOamPmStsIntvlNum=1) is created for each row with a matching session
         name in tmnxOamPmCfgMeasIntvlTable.  In addition, a row is created in
         this table for the test's 'miRaw(1)' interval.

         After that, the timed creation and destruction of rows in this table is
         explained using the following example.

         Suppose the configured number of intervals to be retained is as follows
         (where index columns are underlined with octothorpes, and 'tmnxOamPm'
         is abbreviated as '_'):

         _CfgSessName  _CfgMeasIntvlDuration  _CfgMeasIntvlsStored
         ############  #####################  --------------------
         'mySess1'     'mi15Minutes(2)'                          3

         Suppose statistics collection started at t = 0 (minutes).

         Suppose the following rows exist in tmnxOamPmStsBaseTable at t = 59
         (minutes):

         _CfgSessName  _StsBaseTestType  _StsIntvlDuration  _StsIntvlNum
         ############  ################  #################  ############
         'mySess1'     'dmm(1)'          'mi15Minutes(2)'              1
         'mySess1'     'dmm(1)'          'mi15Minutes(2)'              2
         'mySess1'     'dmm(1)'          'mi15Minutes(2)'              3
         'mySess1'     'dmm(1)'          'mi15Minutes(2)'              4

         The interval numbers are assigned as follows:
         1 - the historical interval ended at t = 15 minutes
         2 - the historical interval ended at t = 30 minutes
         3 - the historical interval ended at t = 45 minutes
         4 - the current interval

         Then, after the next 15 minute interval ends (e.g. at t = 61 minutes),
         the following rows will exist:

         _CfgSessName  _StsBaseTestType  _StsIntvlDuration  _StsIntvlNum
         ############  ################  #################  ############
         'mySess1'     'dmm(1)'          'mi15Minutes(2)'              2
         'mySess1'     'dmm(1)'          'mi15Minutes(2)'              3
         'mySess1'     'dmm(1)'          'mi15Minutes(2)'              4
         'mySess1'     'dmm(1)'          'mi15Minutes(2)'              5

         The interval numbers are assigned as follows:
         2 - the historical interval ended at t = 30 minutes
         3 - the historical interval ended at t = 45 minutes
         4 - the historical interval ended at t = 60 minutes
         5 - the current interval

         The row with interval number 1 was destroyed, because
         tmnxOamPmCfgMeasIntvlsStored=3 specifies that at most three historical
         intervals be retained.

         Rows are also destroyed in this table when the corresponding
         tmnxOamPmCfgMeasIntvlTable row is destroyed.

         When the index value tmnxOamPmStsMeasIntvlDuration is 'miRaw(1)', only
         one interval is available (i.e. tmnxOamPmStsIntvlNum = 1).

         When a test is running, the measurement interval data set for a test's
         'miRaw(1)' measurement interval duration can be cleared using
         TIMETRA-CLEAR-MIB::tmnxClearAction.  The change to the objects in the
         specified row is as follows.

         Object                        Change on Clear Operation
         ----------------------------  --------------------------------------
         tmnxOamPmStsBaseOperStatus    No change
         tmnxOamPmStsBaseSuspect       Set to 'true(1)'
         tmnxOamPmStsBaseStartTime     Set to UTC time of the clear operation
         tmnxOamPmStsBaseElapsedTime   Set to zero
         tmnxOamPmStsBaseTestFramesTx  Set to zero
         tmnxOamPmStsBaseTestFramesRx  Set to zero

         Measurement interval data sets for  measurement interval durations
         other than 'miRaw(1)' cannot be cleared."
    INDEX {
        tmnxOamPmCfgSessName,
        tmnxOamPmStsBaseTestType,
        tmnxOamPmStsMeasIntvlDuration,
        tmnxOamPmStsIntvlNum
    }
    ::= { tmnxOamPmStsBaseTable 1 }

TmnxOamPmStsBaseEntry            ::= SEQUENCE {
    tmnxOamPmStsBaseTestType         TmnxOamPmTestType,
    tmnxOamPmStsMeasIntvlDuration    TmnxOamPmMeasIntervalDuration,
    tmnxOamPmStsIntvlNum             TmnxOamPmStsIntvlNum,
    tmnxOamPmStsBaseOperStatus       INTEGER,
    tmnxOamPmStsBaseSuspect          TruthValue,
    tmnxOamPmStsBaseStartTime        DateAndTime,
    tmnxOamPmStsBaseElapsedTime      Unsigned32,
    tmnxOamPmStsBaseTestFramesTx     Unsigned32,
    tmnxOamPmStsBaseTestFramesRx     Unsigned32
}

tmnxOamPmStsBaseTestType         OBJECT-TYPE
    SYNTAX      TmnxOamPmTestType
    MAX-ACCESS  not-accessible
    STATUS      current
    DESCRIPTION
        "The value of tmnxOamPmStsBaseTestType specifies the type of test for
         which statistics are to be read (e.g. 'dmm(1)')."
    ::= { tmnxOamPmStsBaseEntry 1 }

tmnxOamPmStsMeasIntvlDuration    OBJECT-TYPE
    SYNTAX      TmnxOamPmMeasIntervalDuration
    MAX-ACCESS  not-accessible
    STATUS      current
    DESCRIPTION
        "The value of tmnxOamPmStsMeasIntvlDuration specifies the duration of
         the interval of the statistics to be read (e.g. 'mi15Minutes(2)')."
    ::= { tmnxOamPmStsBaseEntry 2 }

tmnxOamPmStsIntvlNum             OBJECT-TYPE
    SYNTAX      TmnxOamPmStsIntvlNum
    MAX-ACCESS  not-accessible
    STATUS      current
    DESCRIPTION
        "The value of tmnxOamPmStsIntvlNum specifies the interval number of the
         statistics to be read.

         The system's creation and destruction of interval numbers is described
         in the tmnxOamPmStsBaseEntry DESCRIPTION clause."
    ::= { tmnxOamPmStsBaseEntry 3 }

tmnxOamPmStsBaseOperStatus       OBJECT-TYPE
    SYNTAX      INTEGER {
        inProgress(1),
        completed(2)
    }
    MAX-ACCESS  read-only
    STATUS      current
    DESCRIPTION
        "The value of tmnxOamPmStsBaseOperStatus indicates the operational
         status of the specified measurement interval data set.

         If the interval is historical and the operational status is
         'inprogress(1)', the interval is closing (i.e. waiting for a response
         for the final test request sent)."
    ::= { tmnxOamPmStsBaseEntry 4 }

tmnxOamPmStsBaseSuspect          OBJECT-TYPE
    SYNTAX      TruthValue
    MAX-ACCESS  read-only
    STATUS      current
    DESCRIPTION
        "The value of tmnxOamPmStsBaseSuspect indicates whether or not the
         specified measurement interval data set contains suspect information."
    REFERENCE
        "MEF-35, 'Service OAM Performance Monitoring Implementation Agreement',
         Metro Ethernet Forum, April 2012, Section 9.2.4, 'Measurement Interval
         Status'."
    ::= { tmnxOamPmStsBaseEntry 5 }

tmnxOamPmStsBaseStartTime        OBJECT-TYPE
    SYNTAX      DateAndTime (SIZE (8))
    MAX-ACCESS  read-only
    STATUS      current
    DESCRIPTION
        "The value of tmnxOamPmStsBaseStartTime indicates the start time (in
         UTC) of the specified measurement interval data set."
    ::= { tmnxOamPmStsBaseEntry 6 }

tmnxOamPmStsBaseElapsedTime      OBJECT-TYPE
    SYNTAX      Unsigned32
    UNITS       "seconds"
    MAX-ACCESS  read-only
    STATUS      current
    DESCRIPTION
        "The value of tmnxOamPmStsBaseElapsedTime indicates the time elapsed
         since data collection started for the specified measurement interval
         data set."
    ::= { tmnxOamPmStsBaseEntry 7 }

tmnxOamPmStsBaseTestFramesTx     OBJECT-TYPE
    SYNTAX      Unsigned32
    UNITS       "frames"
    MAX-ACCESS  read-only
    STATUS      current
    DESCRIPTION
        "The value of tmnxOamPmStsBaseTestFramesTx indicates the number of test
         frames sent for the specified measurement interval data set."
    ::= { tmnxOamPmStsBaseEntry 8 }

tmnxOamPmStsBaseTestFramesRx     OBJECT-TYPE
    SYNTAX      Unsigned32
    UNITS       "frames"
    MAX-ACCESS  read-only
    STATUS      current
    DESCRIPTION
        "The value of tmnxOamPmStsBaseTestFramesRx indicates the number of test
         frames received for the specified measurement interval data set."
    ::= { tmnxOamPmStsBaseEntry 9 }

--
-- OAM Performance Monitoring Statistics Measurement Interval Index Table
--

tmnxOamPmStsMeasIntvlIndexTable  OBJECT-TYPE
    SYNTAX      SEQUENCE OF TmnxOamPmStsMeasIntvlIndexEntry
    MAX-ACCESS  not-accessible
    STATUS      current
    DESCRIPTION
        "tmnxOamPmStsMeasIntvlIndexTable contains the interval number of the
         newest interval for all the active combinations of session, test type
         (e.g. 'dmm(1)'), and interval duration (e.g. 'mi15Minutes(2)')."
    ::= { tmnxOamPmStatsTableObjs 2 }

tmnxOamPmStsMeasIntvlIndexEntry  OBJECT-TYPE
    SYNTAX      TmnxOamPmStsMeasIntvlIndexEntry
    MAX-ACCESS  not-accessible
    STATUS      current
    DESCRIPTION
        "tmnxOamPmStsMeasIntvlIndexEntry contains the interval number of the
         newest interval for the specified combination of session, test type
         (e.g. 'dmm(1)'), and interval duration (e.g. 'mi15Minutes(2)').

         Rows are created in this table when a test is enabled (e.g. using
         tmnxOamPmCfgDelayDmmAdminStatus and tmnxOamPmCfgDelayDmmOnDmndStatus).

         A row is destroyed in this table when the corresponding
         tmnxOamPmCfgMeasIntvlTable row is destroyed."
    INDEX {
        tmnxOamPmCfgSessName,
        tmnxOamPmStsBaseTestType,
        tmnxOamPmStsMeasIntvlDuration
    }
    ::= { tmnxOamPmStsMeasIntvlIndexTable 1 }

TmnxOamPmStsMeasIntvlIndexEntry  ::= SEQUENCE {
    tmnxOamPmStsMeasIntvlIndexNewest TmnxOamPmStsIntvlNum
}

tmnxOamPmStsMeasIntvlIndexNewest OBJECT-TYPE
    SYNTAX      TmnxOamPmStsIntvlNum
    MAX-ACCESS  read-only
    STATUS      current
    DESCRIPTION
        "The value of tmnxOamPmStsMeasIntvlIndexNewest indicates the interval
         number of the newest interval for the specified session, test type
         (e.g. 'dmm(1)'), and interval duration (e.g. 'mi15Minutes(2)').  This
         value is provided as the tmnxOamPmStsIntvlNum index value when reading
         a row for the newest interval in an OAM PM statistics table.

         For a running test, the newest interval is the current interval.

         For a stopped test, the newest interval is the most recent historical
         interval.  A stopped test does not have a current interval.

         The interval number of the oldest interval for the specified session,
         test type, and interval duration can be computed from this value.

         For a running test, the formula is
         interval_number_of_the_oldest_interval =
         MAX(tmnxOamPmStsMeasIntvlIndexNewest-tmnxOamPmCfgMeasIntvlsStored,  1).

         For a stopped test, the formula is
         interval_number_of_the_oldest_interval =
         MAX(tmnxOamPmStsMeasIntvlIndexNewest-tmnxOamPmCfgMeasIntvlsStored+1,1).
        "
    ::= { tmnxOamPmStsMeasIntvlIndexEntry 1 }

--
-- OAM Performance Monitoring Statistics Frame Loss SLM Table
--

tmnxOamPmStsLossSlmTable         OBJECT-TYPE
    SYNTAX      SEQUENCE OF TmnxOamPmStsLossSlmEntry
    MAX-ACCESS  not-accessible
    STATUS      current
    DESCRIPTION
        "tmnxOamPmStsLossSlmTable contains the frame loss statistics for OAM
         Performance Monitoring SLM (Synthetic Loss Measurement) tests."
    REFERENCE
        "MEF-35, 'Service OAM Performance Monitoring Implementation Agreement',
         Metro Ethernet Forum, April 2012, Section 10.2, 'Single-Ended Synthetic
         Loss Function for Frame Loss Ratio (FLR) and Availability'."
    ::= { tmnxOamPmStatsTableObjs 3 }

tmnxOamPmStsLossSlmEntry         OBJECT-TYPE
    SYNTAX      TmnxOamPmStsLossSlmEntry
    MAX-ACCESS  not-accessible
    STATUS      current
    DESCRIPTION
        "tmnxOamPmStsLossSlmEntry contains the SLM test statistics for one OAM
         Performance Monitoring Measurement Interval Data Set.

         A row is created in this table when a tmnxOamPmStsBaseTable row is
         created with tmnxOamPmStsBaseTestType = 'slm(2)'.

         A row is destroyed in this table when the corresponding
         tmnxOamPmCfgMeasIntvlTable row is destroyed.

         When a test is running, the SLM statistics for a test's raw (i.e.
         'miRaw(1)') measurement interval duration can be cleared using
         TIMETRA-CLEAR-MIB::tmnxClearAction.  A successful clear operation
         zeros all the statistics in the specified row."
    INDEX {
        tmnxOamPmCfgSessName,
        tmnxOamPmStsMeasIntvlDuration,
        tmnxOamPmStsIntvlNum
    }
    ::= { tmnxOamPmStsLossSlmTable 1 }

TmnxOamPmStsLossSlmEntry         ::= SEQUENCE {
    tmnxOamPmStsLossSlmTxFwd         Unsigned32,
    tmnxOamPmStsLossSlmRxFwd         Unsigned32,
    tmnxOamPmStsLossSlmTxBwd         Unsigned32,
    tmnxOamPmStsLossSlmRxBwd         Unsigned32,
    tmnxOamPmStsLossSlmAvailIndFwd   Unsigned32,
    tmnxOamPmStsLossSlmAvailIndBwd   Unsigned32,
    tmnxOamPmStsLossSlmUnavlIndFwd   Unsigned32,
    tmnxOamPmStsLossSlmUnavlIndBwd   Unsigned32,
    tmnxOamPmStsLossSlmUndtAvlFwd    Unsigned32,
    tmnxOamPmStsLossSlmUndtUnavlFwd  Unsigned32,
    tmnxOamPmStsLossSlmUndtAvlBwd    Unsigned32,
    tmnxOamPmStsLossSlmUndtUnavlBwd  Unsigned32,
    tmnxOamPmStsLossSlmHliFwd        Unsigned32,
    tmnxOamPmStsLossSlmHliBwd        Unsigned32,
    tmnxOamPmStsLossSlmChliFwd       Unsigned32,
    tmnxOamPmStsLossSlmChliBwd       Unsigned32,
    tmnxOamPmStsLossSlmMinFlrFwd     Unsigned32,
    tmnxOamPmStsLossSlmMaxFlrFwd     Unsigned32,
    tmnxOamPmStsLossSlmAvgFlrFwd     Unsigned32,
    tmnxOamPmStsLossSlmMinFlrBwd     Unsigned32,
    tmnxOamPmStsLossSlmMaxFlrBwd     Unsigned32,
    tmnxOamPmStsLossSlmAvgFlrBwd     Unsigned32
}

tmnxOamPmStsLossSlmTxFwd         OBJECT-TYPE
    SYNTAX      Unsigned32
    UNITS       "SLM frames"
    MAX-ACCESS  read-only
    STATUS      current
    DESCRIPTION
        "The value of tmnxOamPmStsLossSlmTxFwd indicates the number of SLM
         request frames transmitted in the forward direction for the specified
         measurement interval data set.

         A frame is counted as transmitted if the SLM Availability state is
         Available at transmit time (as specified in MEF-35 Section 9.2.5).
         Otherwise, the frame is not counted.

         A simple count of the frames transmitted for the test is available in
         tmnxOamPmStsBaseTestFramesTx."
    REFERENCE
        "MEF-35, 'Service OAM Performance Monitoring Implementation Agreement',
         Metro Ethernet Forum, April 2012, Section 9.2.5, 'Measurement Behavior
         During Periods of Unavailability and Maintenance Intervals'"
    ::= { tmnxOamPmStsLossSlmEntry 1 }

tmnxOamPmStsLossSlmRxFwd         OBJECT-TYPE
    SYNTAX      Unsigned32
    UNITS       "SLM frames"
    MAX-ACCESS  read-only
    STATUS      current
    DESCRIPTION
        "The value of tmnxOamPmStsLossSlmRxFwd indicates the number of SLM
         request frames received in the forward direction for the specified
         measurement interval data set.

         A frame is counted as received if the SLM Availability state is
         Available at receive time (as specified in MEF-35 Section 9.2.5).
         Otherwise, the frame is not counted.

         A simple count of the frames received for the test is available in
         tmnxOamPmStsBaseTestFramesRx."
    REFERENCE
        "MEF-35, 'Service OAM Performance Monitoring Implementation Agreement',
         Metro Ethernet Forum, April 2012, Section 9.2.5, 'Measurement Behavior
         During Periods of Unavailability and Maintenance Intervals'"
    ::= { tmnxOamPmStsLossSlmEntry 2 }

tmnxOamPmStsLossSlmTxBwd         OBJECT-TYPE
    SYNTAX      Unsigned32
    UNITS       "SLR frames"
    MAX-ACCESS  read-only
    STATUS      current
    DESCRIPTION
        "The value of tmnxOamPmStsLossSlmTxBwd indicates the number of SLR reply
         frames transmitted in the backward direction for the specified
         measurement interval data set.

         A frame is counted as transmitted if the SLM Availability state is
         Available at transmit time (as specified in MEF-35 Section 9.2.5).
         Otherwise, the frame is not counted.

         A simple count of the frames transmitted for the test is available in
         tmnxOamPmStsBaseTestFramesTx."
    REFERENCE
        "MEF-35, 'Service OAM Performance Monitoring Implementation Agreement',
         Metro Ethernet Forum, April 2012, Section 9.2.5, 'Measurement Behavior
         During Periods of Unavailability and Maintenance Intervals'"
    ::= { tmnxOamPmStsLossSlmEntry 3 }

tmnxOamPmStsLossSlmRxBwd         OBJECT-TYPE
    SYNTAX      Unsigned32
    UNITS       "SLR frames"
    MAX-ACCESS  read-only
    STATUS      current
    DESCRIPTION
        "The value of tmnxOamPmStsLossSlmRxBwd indicates the number of SLR reply
         frames received in the backward direction for the specified measurement
         interval data set.

         A frame is counted as received if the SLM Availability state is
         Available at receive time (as specified in MEF-35 Section 6.3).
         Otherwise, the frame is not counted.

         A simple count of the frames received for the test is available in
         tmnxOamPmStsBaseTestFramesRx."
    REFERENCE
        "MEF-35, 'Service OAM Performance Monitoring Implementation Agreement',
         Metro Ethernet Forum, April 2012, Section 6.3, 'Measurement Behavior
         During Periods of Unavailability and Maintenance Intervals'"
    ::= { tmnxOamPmStsLossSlmEntry 4 }

tmnxOamPmStsLossSlmAvailIndFwd   OBJECT-TYPE
    SYNTAX      Unsigned32
    MAX-ACCESS  read-only
    STATUS      current
    DESCRIPTION
        "The value of tmnxOamPmStsLossSlmAvailIndFwd indicates the number of
         availability indicators evaluated as Available in the forward direction
         for the specified measurement interval data set."
    ::= { tmnxOamPmStsLossSlmEntry 5 }

tmnxOamPmStsLossSlmAvailIndBwd   OBJECT-TYPE
    SYNTAX      Unsigned32
    MAX-ACCESS  read-only
    STATUS      current
    DESCRIPTION
        "The value of tmnxOamPmStsLossSlmAvailIndBwd indicates the number of
         availability indicators evaluated as Available in the backward
         direction for the specified measurement interval data set."
    ::= { tmnxOamPmStsLossSlmEntry 6 }

tmnxOamPmStsLossSlmUnavlIndFwd   OBJECT-TYPE
    SYNTAX      Unsigned32
    MAX-ACCESS  read-only
    STATUS      current
    DESCRIPTION
        "The value of tmnxOamPmStsLossSlmUnavlIndFwd indicates the number of
         availability indicators evaluated as Unavailable in the forward
         direction for the specified measurement interval data set."
    ::= { tmnxOamPmStsLossSlmEntry 7 }

tmnxOamPmStsLossSlmUnavlIndBwd   OBJECT-TYPE
    SYNTAX      Unsigned32
    MAX-ACCESS  read-only
    STATUS      current
    DESCRIPTION
        "The value of tmnxOamPmStsLossSlmUnavlIndBwd indicates the number of
         availability indicators evaluated as Unavailable in the backward
         direction for the specified measurement interval data set."
    ::= { tmnxOamPmStsLossSlmEntry 8 }

tmnxOamPmStsLossSlmUndtAvlFwd    OBJECT-TYPE
    SYNTAX      Unsigned32
    MAX-ACCESS  read-only
    STATUS      current
    DESCRIPTION
        "The value of tmnxOamPmStsLossSlmUndtAvlFwd indicates the number of
         availability indicators evaluated as Available in the forward direction
         based on extrapolation from the previous state.

         For example, this counter will be incremented when:
         1.  It is time to calculate an availability indicator, and
         2.  All the probe requests used to calculate the availability indicator
         have timed out, and
         3.  The most recently declared availability indicator in the forward
         direction was Available.

         In that case, the result is considered undetermined because no
         information is available to indicate if the problem is in the forward
         direction or the backward direction."
    ::= { tmnxOamPmStsLossSlmEntry 9 }

tmnxOamPmStsLossSlmUndtUnavlFwd  OBJECT-TYPE
    SYNTAX      Unsigned32
    MAX-ACCESS  read-only
    STATUS      current
    DESCRIPTION
        "The value of tmnxOamPmStsLossSlmUndtUnavlFwd indicates the number of
         availability indicators evaluated as Unavailable in the forward
         direction based on extrapolation from the previous state.

         For example, this counter will be incremented when:
         1.  It is time to calculate an availability indicator, and
         2.  All the probe requests used to calculate the availability indicator
         have timed out, and
         3.  The most recently declared availability indicator in the forward
         direction was Unavailable.

         In that case, the result is considered undetermined because no
         information is available to indicate if the problem is in the forward
         direction or the backward direction."
    ::= { tmnxOamPmStsLossSlmEntry 10 }

tmnxOamPmStsLossSlmUndtAvlBwd    OBJECT-TYPE
    SYNTAX      Unsigned32
    MAX-ACCESS  read-only
    STATUS      current
    DESCRIPTION
        "The value of tmnxOamPmStsLossSlmUndtAvlBwd indicates the number of
         availability indicators evaluated as Available in the backward
         direction based on extrapolation from the previous state.

         For example, this counter will be incremented when:
         1.  It is time to calculate an availability indicator, and
         2.  All the probe requests used to calculate the availability indicator
         have timed out, and
         3.  The most recently declared availability indicator in the backward
         direction was Available.

         In that case, the result is considered undetermined because no
         information is available to indicate if the problem is in the forward
         direction or the backward direction."
    ::= { tmnxOamPmStsLossSlmEntry 11 }

tmnxOamPmStsLossSlmUndtUnavlBwd  OBJECT-TYPE
    SYNTAX      Unsigned32
    MAX-ACCESS  read-only
    STATUS      current
    DESCRIPTION
        "The value of tmnxOamPmStsLossSlmUndtUnavlBwd indicates the number of
         availability indicators evaluated as Unavailable in the backward
         direction based on extrapolation from the previous state.

         For example, this counter will be incremented when:
         1.  It is time to calculate an availability indicator, and
         2.  All the probe requests used to calculate the availability indicator
         have timed out, and
         3.  The most recently declared availability indicator in the backward
         direction was Unavailable.

         In that case, the result is considered undetermined because no
         information is available to indicate if the problem is in the forward
         direction or the backward direction."
    ::= { tmnxOamPmStsLossSlmEntry 12 }

tmnxOamPmStsLossSlmHliFwd        OBJECT-TYPE
    SYNTAX      Unsigned32
    MAX-ACCESS  read-only
    STATUS      current
    DESCRIPTION
        "The value of tmnxOamPmStsLossSlmHliFwd indicates the number of HLIs
         (High Loss Intervals) in the forward direction for the specified
         measurement interval data set."
    ::= { tmnxOamPmStsLossSlmEntry 13 }

tmnxOamPmStsLossSlmHliBwd        OBJECT-TYPE
    SYNTAX      Unsigned32
    MAX-ACCESS  read-only
    STATUS      current
    DESCRIPTION
        "The value of tmnxOamPmStsLossSlmHliBwd indicates the number of HLIs
         (High Loss Intervals) in the backward direction for the specified
         measurement interval data set."
    ::= { tmnxOamPmStsLossSlmEntry 14 }

tmnxOamPmStsLossSlmChliFwd       OBJECT-TYPE
    SYNTAX      Unsigned32
    MAX-ACCESS  read-only
    STATUS      current
    DESCRIPTION
        "The value of tmnxOamPmStsLossSlmChliFwd indicates the number of CHLIs
         (Consecutive High Loss Intervals) in the forward direction for the
         specified measurement interval data set."
    ::= { tmnxOamPmStsLossSlmEntry 15 }

tmnxOamPmStsLossSlmChliBwd       OBJECT-TYPE
    SYNTAX      Unsigned32
    MAX-ACCESS  read-only
    STATUS      current
    DESCRIPTION
        "The value of tmnxOamPmStsLossSlmChliBwd indicates the number of CHLIs
         (Consecutive High Loss Intervals) in the backward direction for the
         specified measurement interval data set."
    ::= { tmnxOamPmStsLossSlmEntry 16 }

tmnxOamPmStsLossSlmMinFlrFwd     OBJECT-TYPE
    SYNTAX      Unsigned32 (0..100000)
    UNITS       "milli-percent"
    MAX-ACCESS  read-only
    STATUS      current
    DESCRIPTION
        "The value of tmnxOamPmStsLossSlmMinFlrFwd indicates the minimum FLR
         (Frame Loss Ratio) in the forward direction for the specified
         measurement interval data set."
    ::= { tmnxOamPmStsLossSlmEntry 17 }

tmnxOamPmStsLossSlmMaxFlrFwd     OBJECT-TYPE
    SYNTAX      Unsigned32 (0..100000)
    UNITS       "milli-percent"
    MAX-ACCESS  read-only
    STATUS      current
    DESCRIPTION
        "The value of tmnxOamPmStsLossSlmMaxFlrFwd indicates the maximum FLR
         (Frame Loss Ratio) in the forward direction for the specified
         measurement interval data set."
    ::= { tmnxOamPmStsLossSlmEntry 18 }

tmnxOamPmStsLossSlmAvgFlrFwd     OBJECT-TYPE
    SYNTAX      Unsigned32 (0..100000)
    UNITS       "milli-percent"
    MAX-ACCESS  read-only
    STATUS      current
    DESCRIPTION
        "The value of tmnxOamPmStsLossSlmAvgFlrFwd indicates the average FLR
         (Frame Loss Ratio) in the forward direction for the specified
         measurement interval data set."
    ::= { tmnxOamPmStsLossSlmEntry 19 }

tmnxOamPmStsLossSlmMinFlrBwd     OBJECT-TYPE
    SYNTAX      Unsigned32 (0..100000)
    UNITS       "milli-percent"
    MAX-ACCESS  read-only
    STATUS      current
    DESCRIPTION
        "The value of tmnxOamPmStsLossSlmMinFlrBwd indicates the minimum FLR
         (Frame Loss Ratio) in the backward direction for the specified
         measurement interval data set."
    ::= { tmnxOamPmStsLossSlmEntry 20 }

tmnxOamPmStsLossSlmMaxFlrBwd     OBJECT-TYPE
    SYNTAX      Unsigned32 (0..100000)
    UNITS       "milli-percent"
    MAX-ACCESS  read-only
    STATUS      current
    DESCRIPTION
        "The value of tmnxOamPmStsLossSlmMaxFlrBwd indicates the maximum FLR
         (Frame Loss Ratio) in the backward direction for the specified
         measurement interval data set."
    ::= { tmnxOamPmStsLossSlmEntry 21 }

tmnxOamPmStsLossSlmAvgFlrBwd     OBJECT-TYPE
    SYNTAX      Unsigned32 (0..100000)
    UNITS       "milli-percent"
    MAX-ACCESS  read-only
    STATUS      current
    DESCRIPTION
        "The value of tmnxOamPmStsLossSlmAvgFlrBwd indicates the average FLR
         (Frame Loss Ratio) in the backward direction for the specified
         measurement interval data set."
    ::= { tmnxOamPmStsLossSlmEntry 22 }

--
-- OAM Performance Monitoring Statistics DMM Table
--

tmnxOamPmStsDelayDmmTable        OBJECT-TYPE
    SYNTAX      SEQUENCE OF TmnxOamPmStsDelayDmmEntry
    MAX-ACCESS  not-accessible
    STATUS      current
    DESCRIPTION
        "tmnxOamPmStsDelayDmmTable contains the summarized DMM (Delay
         Measurement Message) statistics for OAM Performance Monitoring
         Measurement Interval Data Sets."
    REFERENCE
        "MEF-35, 'Service OAM Performance Monitoring Implementation Agreement',
         Metro Ethernet Forum, April 2012, Section 10.1, 'Single-Ended Delay
         Function for Delay, Frame Delay Range, and Inter Delay Variation'."
    ::= { tmnxOamPmStatsTableObjs 4 }

tmnxOamPmStsDelayDmmEntry        OBJECT-TYPE
    SYNTAX      TmnxOamPmStsDelayDmmEntry
    MAX-ACCESS  not-accessible
    STATUS      current
    DESCRIPTION
        "tmnxOamPmStsDelayDmmEntry contains the summarized DMM (Delay
         Measurement Message) statistics for one OAM Performance Monitoring
         Measurement Interval Data Set.

         When a row is created in tmnxOamPmStsBaseTable with
         tmnxOamPmStsBaseTestType = 'dmm(1)', three rows are created in this
         table.  The three rows have the following values in the
         tmnxOamPmCfgBinType index column:  'fd(1)', 'fdr(2)', and 'ifdv(3)'.

         Rows are destroyed in this table when the corresponding
         tmnxOamPmStsBaseTable row is destroyed.

         When a test is running, the DMM statistics for a test's raw (i.e.
         'miRaw(1)') measurement interval duration can be cleared using
         TIMETRA-CLEAR-MIB::tmnxClearAction.  A successful clear operation
         zeros all the statistics in the specified rows."
    INDEX {
        tmnxOamPmCfgSessName,
        tmnxOamPmStsMeasIntvlDuration,
        tmnxOamPmStsIntvlNum,
        tmnxOamPmCfgBinType
    }
    ::= { tmnxOamPmStsDelayDmmTable 1 }

TmnxOamPmStsDelayDmmEntry        ::= SEQUENCE {
    tmnxOamPmStsDelayDmmFwdMin       Unsigned32,
    tmnxOamPmStsDelayDmmFwdMax       Unsigned32,
    tmnxOamPmStsDelayDmmFwdAvg       Unsigned32,
    tmnxOamPmStsDelayDmmBwdMin       Unsigned32,
    tmnxOamPmStsDelayDmmBwdMax       Unsigned32,
    tmnxOamPmStsDelayDmmBwdAvg       Unsigned32,
    tmnxOamPmStsDelayDmm2wyMin       Unsigned32,
    tmnxOamPmStsDelayDmm2wyMax       Unsigned32,
    tmnxOamPmStsDelayDmm2wyAvg       Unsigned32
}

tmnxOamPmStsDelayDmmFwdMin       OBJECT-TYPE
    SYNTAX      Unsigned32
    UNITS       "microseconds"
    MAX-ACCESS  read-only
    STATUS      current
    DESCRIPTION
        "The value of tmnxOamPmStsDelayDmmFwdMin indicates the minimum delay in
         the forward direction for the specified session, interval duration
         (e.g. 'mi15Minutes(2)'), interval number, and bin type (e.g. 'fd(1)')."
    ::= { tmnxOamPmStsDelayDmmEntry 1 }

tmnxOamPmStsDelayDmmFwdMax       OBJECT-TYPE
    SYNTAX      Unsigned32
    UNITS       "microseconds"
    MAX-ACCESS  read-only
    STATUS      current
    DESCRIPTION
        "The value of tmnxOamPmStsDelayDmmFwdMax indicates the maximum delay in
         the forward direction for the specified session, interval duration
         (e.g. 'mi15Minutes(2)'), interval number, and bin type (e.g. 'fd(1)')."
    ::= { tmnxOamPmStsDelayDmmEntry 2 }

tmnxOamPmStsDelayDmmFwdAvg       OBJECT-TYPE
    SYNTAX      Unsigned32
    UNITS       "microseconds"
    MAX-ACCESS  read-only
    STATUS      current
    DESCRIPTION
        "The value of tmnxOamPmStsDelayDmmFwdAvg indicates the average delay in
         the forward direction for the specified session, interval duration
         (e.g. 'mi15Minutes(2)'), interval number, and bin type (e.g. 'fd(1)')."
    ::= { tmnxOamPmStsDelayDmmEntry 3 }

tmnxOamPmStsDelayDmmBwdMin       OBJECT-TYPE
    SYNTAX      Unsigned32
    UNITS       "microseconds"
    MAX-ACCESS  read-only
    STATUS      current
    DESCRIPTION
        "The value of tmnxOamPmStsDelayDmmBwdMin indicates the minimum delay in
         the backward direction for the specified session, interval duration
         (e.g. 'mi15Minutes(2)'), interval number, and bin type (e.g. 'fd(1)')."
    ::= { tmnxOamPmStsDelayDmmEntry 4 }

tmnxOamPmStsDelayDmmBwdMax       OBJECT-TYPE
    SYNTAX      Unsigned32
    UNITS       "microseconds"
    MAX-ACCESS  read-only
    STATUS      current
    DESCRIPTION
        "The value of tmnxOamPmStsDelayDmmBwdMax indicates the maximum delay in
         the backward direction for the specified session, interval duration
         (e.g. 'mi15Minutes(2)'), interval number, and bin type (e.g. 'fd(1)')."
    ::= { tmnxOamPmStsDelayDmmEntry 5 }

tmnxOamPmStsDelayDmmBwdAvg       OBJECT-TYPE
    SYNTAX      Unsigned32
    UNITS       "microseconds"
    MAX-ACCESS  read-only
    STATUS      current
    DESCRIPTION
        "The value of tmnxOamPmStsDelayDmmBwdAvg indicates the average delay in
         the backward direction for the specified session, interval duration
         (e.g. 'mi15Minutes(2)'), interval number, and bin type (e.g. 'fd(1)')."
    ::= { tmnxOamPmStsDelayDmmEntry 6 }

tmnxOamPmStsDelayDmm2wyMin       OBJECT-TYPE
    SYNTAX      Unsigned32
    UNITS       "microseconds"
    MAX-ACCESS  read-only
    STATUS      current
    DESCRIPTION
        "The value of tmnxOamPmStsDelayDmm2wyMin indicates the minimum two-way
         delay for the specified session, interval duration (e.g.
         'mi15Minutes(2)'), interval number, and bin type (e.g. 'fd(1)')."
    ::= { tmnxOamPmStsDelayDmmEntry 7 }

tmnxOamPmStsDelayDmm2wyMax       OBJECT-TYPE
    SYNTAX      Unsigned32
    UNITS       "microseconds"
    MAX-ACCESS  read-only
    STATUS      current
    DESCRIPTION
        "The value of tmnxOamPmStsDelayDmm2wyMax indicates the maximum two-way
         delay for the specified session, interval duration (e.g.
         'mi15Minutes(2)'), interval number, and bin type (e.g. 'fd(1)')."
    ::= { tmnxOamPmStsDelayDmmEntry 8 }

tmnxOamPmStsDelayDmm2wyAvg       OBJECT-TYPE
    SYNTAX      Unsigned32
    UNITS       "microseconds"
    MAX-ACCESS  read-only
    STATUS      current
    DESCRIPTION
        "The value of tmnxOamPmStsDelayDmm2wyAvg indicates the average two-way
         delay for the specified session, interval duration (e.g.
         'mi15Minutes(2)'), interval number, and bin type (e.g. 'fd(1)')."
    ::= { tmnxOamPmStsDelayDmmEntry 9 }

--
-- OAM Performance Monitoring Statistics DMM Bin Table
--

tmnxOamPmStsDelayDmmBinTable     OBJECT-TYPE
    SYNTAX      SEQUENCE OF TmnxOamPmStsDelayDmmBinEntry
    MAX-ACCESS  not-accessible
    STATUS      current
    DESCRIPTION
        "tmnxOamPmStsDelayDmmBinTable contains the per-bin DMM (Delay
         Measurement Message) statistics for OAM Performance Monitoring
         Measurement Interval Data Sets."
    REFERENCE
        "MEF-35, 'Service OAM Performance Monitoring Implementation Agreement',
         Metro Ethernet Forum, April 2012, Section 10.1, 'Single-Ended Delay
         Function for Delay, Frame Delay Range, and Inter Delay Variation'."
    ::= { tmnxOamPmStatsTableObjs 5 }

tmnxOamPmStsDelayDmmBinEntry     OBJECT-TYPE
    SYNTAX      TmnxOamPmStsDelayDmmBinEntry
    MAX-ACCESS  not-accessible
    STATUS      current
    DESCRIPTION
        "tmnxOamPmStsDelayDmmBinEntry contains the per-bin DMM (Delay
         Measurement Message) statistics for one OAM Performance Monitoring
         Measurement Interval Data Set.

         Rows are created in this table when a corresponding row is created in
         tmnxOamPmStsDelayDmmTable.  If the tmnxOamPmStsDelayDmmTable row is
         created with the index value tmnxOamPmCfgBinType = 'fd(1)', then the
         the number of rows created in this table is
         tmnxOamPmCfgBinGroupFdBinCount.  Similarly, 'fdr(2)' and 'ifdv(3)'.

         Rows are destroyed in this table when the corresponding
         tmnxOamPmStsDelayDmmTable row is destroyed.

         When a test is running, the DMM statistics for a test's raw (i.e.
         'miRaw(1)') measurement interval duration can be cleared using
         TIMETRA-CLEAR-MIB::tmnxClearAction.  A successful clear operation
         zeros all the statistics in the specified rows."
    INDEX {
        tmnxOamPmCfgSessName,
        tmnxOamPmStsMeasIntvlDuration,
        tmnxOamPmStsIntvlNum,
        tmnxOamPmCfgBinType,
        tmnxOamPmStsDelayDmmBinNum
    }
    ::= { tmnxOamPmStsDelayDmmBinTable 1 }

TmnxOamPmStsDelayDmmBinEntry     ::= SEQUENCE {
    tmnxOamPmStsDelayDmmBinNum       Unsigned32,
    tmnxOamPmStsDelayDmmBinFwdCount  Unsigned32,
    tmnxOamPmStsDelayDmmBinBwdCount  Unsigned32,
    tmnxOamPmStsDelayDmmBin2wyCount  Unsigned32
}

tmnxOamPmStsDelayDmmBinNum       OBJECT-TYPE
    SYNTAX      Unsigned32 (0..9)
    MAX-ACCESS  not-accessible
    STATUS      current
    DESCRIPTION
        "The value of tmnxOamPmStsDelayDmmBinNum specifies the bin number of the
         statistics to be read."
    ::= { tmnxOamPmStsDelayDmmBinEntry 1 }

tmnxOamPmStsDelayDmmBinFwdCount  OBJECT-TYPE
    SYNTAX      Unsigned32
    MAX-ACCESS  read-only
    STATUS      current
    DESCRIPTION
        "The value of tmnxOamPmStsDelayDmmBinFwdCount indicates the number of
         measurements in the forward direction that fall within the configured
         range (in microseconds) of the specified bin.

         For example, suppose the index values for this object are as follows
         (where the index names are abbreviated, and index columns are
         underlined with octothorpes).

         _SessName   _IntvlDuration    _IntvlNum  _BinType  _BinNum
         ##########  ################  #########  ########  #######
         'dmmSess1'  'mi15Minutes(2)'          1  'fd(1)'         9

         Then, the value of this object indicates the number of DMM measurements
         (in microseconds) in the forward direction in the first interval of
         'dmmSess1' that fit in the highest configured delay range (as
         configured using tmnxOamPmCfgBinLowerBound)."
    ::= { tmnxOamPmStsDelayDmmBinEntry 2 }

tmnxOamPmStsDelayDmmBinBwdCount  OBJECT-TYPE
    SYNTAX      Unsigned32
    MAX-ACCESS  read-only
    STATUS      current
    DESCRIPTION
        "The value of tmnxOamPmStsDelayDmmBinBwdCount indicates the number of
         measurements in the backward direction that fall within the configured
         range (in microseconds) of the specified bin.

         For example, suppose the index values for this object are as follows
         (where the index names are abbreviated, and index columns are
         underlined with octothorpes).

         _SessName   _IntvlDuration    _IntvlNum  _BinType  _BinNum
         ##########  ################  #########  ########  #######
         'dmmSess1'  'mi15Minutes(2)'          1  'fd(1)'         0

         Then, the value of this object indicates the number of DMM measurements
         (in microseconds) in the backward direction in the first interval of
         'dmmSess1' that fit in the lowest configured delay range (as configured
         using tmnxOamPmCfgBinLowerBound)."
    ::= { tmnxOamPmStsDelayDmmBinEntry 3 }

tmnxOamPmStsDelayDmmBin2wyCount  OBJECT-TYPE
    SYNTAX      Unsigned32
    MAX-ACCESS  read-only
    STATUS      current
    DESCRIPTION
        "The value of tmnxOamPmStsDelayDmmBin2wyCount indicates the number of
         two-way measurements that fall within the configured range (in
         microseconds) of the specified bin.

         For example, suppose the index values for this object are as follows
         (where the index names are abbreviated, and index columns are
         underlined with octothorpes).

         _SessName   _IntvlDuration    _IntvlNum  _BinType  _BinNum
         ##########  ################  #########  ########  #######
         'dmmSess1'  'mi15Minutes(2)'          1  'fd(1)'         0

         Then, the value of this object indicates the number of two-way DMM
         measurements (in microseconds) in the first interval of 'dmmSess1' that
         fit in the lowest configured delay range (as configured using
         tmnxOamPmCfgBinLowerBound)."
    ::= { tmnxOamPmStsDelayDmmBinEntry 4 }

--
-- OAM Performance Monitoring Statistics TWAMP-Light Reflector Table
--

tmnxOamPmStsTwlRflTable          OBJECT-TYPE
    SYNTAX      SEQUENCE OF TmnxOamPmStsTwlRflEntry
    MAX-ACCESS  not-accessible
    STATUS      current
    DESCRIPTION
        "tmnxOamPmStsTwlRflTable contains the statistics for OAM Performance
         Monitoring TWAMP-Light reflectors."
    ::= { tmnxOamPmStatsTableObjs 6 }

tmnxOamPmStsTwlRflEntry          OBJECT-TYPE
    SYNTAX      TmnxOamPmStsTwlRflEntry
    MAX-ACCESS  not-accessible
    STATUS      current
    DESCRIPTION
        "tmnxOamPmStsTwlRflEntry contains the statistics for the specified OAM
         Performance Monitoring TWAMP-Light reflector.

         SROS creates a row in this table when a corresponding row is created in
         tmnxOamPmCfgTwlRflTable.

         SROS destroys a row in this table when a corresponding row is destroyed
         in tmnxOamPmCfgTwlRflTable.

         The encoding of the index is explained in the DESCRIPTION clause for
         tmnxOamPmCfgTwlRflEntry."
    AUGMENTS { tmnxOamPmCfgTwlRflEntry }
    ::= { tmnxOamPmStsTwlRflTable 1 }

TmnxOamPmStsTwlRflEntry          ::= SEQUENCE {
    tmnxOamPmStsTwlRflUpTime         Unsigned32,
    tmnxOamPmStsTwlRflFramesRx       Unsigned32,
    tmnxOamPmStsTwlRflFramesTx       Unsigned32
}

tmnxOamPmStsTwlRflUpTime         OBJECT-TYPE
    SYNTAX      Unsigned32
    UNITS       "seconds"
    MAX-ACCESS  read-only
    STATUS      current
    DESCRIPTION
        "The value of tmnxOamPmStsTwlRflUpTime indicates the time elapsed since
         the most recent transition of the reflector's administrative status to
         'enabled(1)'.

         Zero is returned if the reflector's administrative status is
         'disabled(2)'."
    ::= { tmnxOamPmStsTwlRflEntry 1 }

tmnxOamPmStsTwlRflFramesRx       OBJECT-TYPE
    SYNTAX      Unsigned32
    MAX-ACCESS  read-only
    STATUS      current
    DESCRIPTION
        "The value of tmnxOamPmStsTwlRflFramesRx indicates the number of
         TWAMP-Test frames received by the specified reflector."
    ::= { tmnxOamPmStsTwlRflEntry 2 }

tmnxOamPmStsTwlRflFramesTx       OBJECT-TYPE
    SYNTAX      Unsigned32
    MAX-ACCESS  read-only
    STATUS      current
    DESCRIPTION
        "The value of tmnxOamPmStsTwlRflFramesTx indicates the number of
         TWAMP-Test frames transmitted by the specified reflector."
    ::= { tmnxOamPmStsTwlRflEntry 3 }

--
-- OAM Performance Monitoring Statistics TWAMP-Light Delay Table
--

tmnxOamPmStsDelayTwlTable        OBJECT-TYPE
    SYNTAX      SEQUENCE OF TmnxOamPmStsDelayTwlEntry
    MAX-ACCESS  not-accessible
    STATUS      current
    DESCRIPTION
        "tmnxOamPmStsDelayTwlTable contains TWAMP-Light (Two-Way Active
         Measurement Protocol, Light) frame delay summary statistics.  The frame
         delay summary statistics kept for TWAMP-Light tests are the same as the
         frame delay summary statistics specified for Ethernet DMM (Delay
         Measurement Message) tests in MEF-35 requirement R66."
    REFERENCE
        "MEF-35, 'Service OAM Performance Monitoring Implementation Agreement',
         Metro Ethernet Forum, April 2012, Section 10.1, 'Single-Ended Delay
         Function for Delay, Frame Delay Range, and Inter Delay Variation',
         requirement R66.
         RFC 5357, 'A Two-Way Active Measurement Protocol (TWAMP)', Appendix I,
         'TWAMP Light'."
    ::= { tmnxOamPmStatsTableObjs 7 }

tmnxOamPmStsDelayTwlEntry        OBJECT-TYPE
    SYNTAX      TmnxOamPmStsDelayTwlEntry
    MAX-ACCESS  not-accessible
    STATUS      current
    DESCRIPTION
        "tmnxOamPmStsDelayTwlEntry contains the TWAMP-Light frame delay summary
         statistics for one OAM Performance Monitoring Measurement Interval Data
         Set.

         When a row is created in tmnxOamPmStsBaseTable with
         tmnxOamPmStsBaseTestType = 'twampLight(3)', three rows are created in
         this table.  The three rows have the following values in the
         tmnxOamPmCfgBinType index column:  'fd(1)', 'fdr(2)', and 'ifdv(3)'.

         Rows are destroyed in this table when the corresponding
         tmnxOamPmStsBaseTable row is destroyed.

         When a test is running, the TWAMP-Light statistics for a test's raw
         (i.e.  'miRaw(1)') measurement interval duration can be cleared using
         TIMETRA-CLEAR-MIB::tmnxClearAction.  A successful clear operation zeros
         all the statistics in the specified rows in this table."
    REFERENCE
        "MEF-35, 'Service OAM Performance Monitoring Implementation Agreement',
         Metro Ethernet Forum, April 2012, Section 9.2.1 'Measurement Interval
         Data Sets'."
    INDEX {
        tmnxOamPmCfgSessName,
        tmnxOamPmStsMeasIntvlDuration,
        tmnxOamPmStsIntvlNum,
        tmnxOamPmCfgBinType
    }
    ::= { tmnxOamPmStsDelayTwlTable 1 }

TmnxOamPmStsDelayTwlEntry        ::= SEQUENCE {
    tmnxOamPmStsDelayTwlFwdMin       Unsigned32,
    tmnxOamPmStsDelayTwlFwdMax       Unsigned32,
    tmnxOamPmStsDelayTwlFwdAvg       Unsigned32,
    tmnxOamPmStsDelayTwlBwdMin       Unsigned32,
    tmnxOamPmStsDelayTwlBwdMax       Unsigned32,
    tmnxOamPmStsDelayTwlBwdAvg       Unsigned32,
    tmnxOamPmStsDelayTwl2wyMin       Unsigned32,
    tmnxOamPmStsDelayTwl2wyMax       Unsigned32,
    tmnxOamPmStsDelayTwl2wyAvg       Unsigned32
}

tmnxOamPmStsDelayTwlFwdMin       OBJECT-TYPE
    SYNTAX      Unsigned32
    UNITS       "microseconds"
    MAX-ACCESS  read-only
    STATUS      current
    DESCRIPTION
        "The value of tmnxOamPmStsDelayTwlFwdMin indicates the minimum delay in
         the forward direction for the specified session, interval duration
         (e.g. 'mi15Minutes(2)'), interval number, and bin type (e.g. 'fd(1)')."
    ::= { tmnxOamPmStsDelayTwlEntry 1 }

tmnxOamPmStsDelayTwlFwdMax       OBJECT-TYPE
    SYNTAX      Unsigned32
    UNITS       "microseconds"
    MAX-ACCESS  read-only
    STATUS      current
    DESCRIPTION
        "The value of tmnxOamPmStsDelayTwlFwdMax indicates the maximum delay in
         the forward direction for the specified session, interval duration
         (e.g. 'mi15Minutes(2)'), interval number, and bin type (e.g. 'fd(1)')."
    ::= { tmnxOamPmStsDelayTwlEntry 2 }

tmnxOamPmStsDelayTwlFwdAvg       OBJECT-TYPE
    SYNTAX      Unsigned32
    UNITS       "microseconds"
    MAX-ACCESS  read-only
    STATUS      current
    DESCRIPTION
        "The value of tmnxOamPmStsDelayTwlFwdAvg indicates the average delay in
         the forward direction for the specified session, interval duration
         (e.g. 'mi15Minutes(2)'), interval number, and bin type (e.g. 'fd(1)')."
    ::= { tmnxOamPmStsDelayTwlEntry 3 }

tmnxOamPmStsDelayTwlBwdMin       OBJECT-TYPE
    SYNTAX      Unsigned32
    UNITS       "microseconds"
    MAX-ACCESS  read-only
    STATUS      current
    DESCRIPTION
        "The value of tmnxOamPmStsDelayTwlBwdMin indicates the minimum delay in
         the backward direction for the specified session, interval duration
         (e.g. 'mi15Minutes(2)'), interval number, and bin type (e.g. 'fd(1)')."
    ::= { tmnxOamPmStsDelayTwlEntry 4 }

tmnxOamPmStsDelayTwlBwdMax       OBJECT-TYPE
    SYNTAX      Unsigned32
    UNITS       "microseconds"
    MAX-ACCESS  read-only
    STATUS      current
    DESCRIPTION
        "The value of tmnxOamPmStsDelayTwlBwdMax indicates the maximum delay in
         the backward direction for the specified session, interval duration
         (e.g. 'mi15Minutes(2)'), interval number, and bin type (e.g. 'fd(1)')."
    ::= { tmnxOamPmStsDelayTwlEntry 5 }

tmnxOamPmStsDelayTwlBwdAvg       OBJECT-TYPE
    SYNTAX      Unsigned32
    UNITS       "microseconds"
    MAX-ACCESS  read-only
    STATUS      current
    DESCRIPTION
        "The value of tmnxOamPmStsDelayTwlBwdAvg indicates the average delay in
         the backward direction for the specified session, interval duration
         (e.g. 'mi15Minutes(2)'), interval number, and bin type (e.g. 'fd(1)')."
    ::= { tmnxOamPmStsDelayTwlEntry 6 }

tmnxOamPmStsDelayTwl2wyMin       OBJECT-TYPE
    SYNTAX      Unsigned32
    UNITS       "microseconds"
    MAX-ACCESS  read-only
    STATUS      current
    DESCRIPTION
        "The value of tmnxOamPmStsDelayTwl2wyMin indicates the minimum two-way
         delay for the specified session, interval duration (e.g.
         'mi15Minutes(2)'), interval number, and bin type (e.g. 'fd(1)')."
    ::= { tmnxOamPmStsDelayTwlEntry 7 }

tmnxOamPmStsDelayTwl2wyMax       OBJECT-TYPE
    SYNTAX      Unsigned32
    UNITS       "microseconds"
    MAX-ACCESS  read-only
    STATUS      current
    DESCRIPTION
        "The value of tmnxOamPmStsDelayTwl2wyMax indicates the maximum two-way
         delay for the specified session, interval duration (e.g.
         'mi15Minutes(2)'), interval number, and bin type (e.g. 'fd(1)')."
    ::= { tmnxOamPmStsDelayTwlEntry 8 }

tmnxOamPmStsDelayTwl2wyAvg       OBJECT-TYPE
    SYNTAX      Unsigned32
    UNITS       "microseconds"
    MAX-ACCESS  read-only
    STATUS      current
    DESCRIPTION
        "The value of tmnxOamPmStsDelayTwl2wyAvg indicates the average two-way
         delay for the specified session, interval duration (e.g.
         'mi15Minutes(2)'), interval number, and bin type (e.g. 'fd(1)')."
    ::= { tmnxOamPmStsDelayTwlEntry 9 }

--
-- OAM Performance Monitoring Statistics TWAMP-Light Delay Bin Table
--

tmnxOamPmStsDelayTwlBinTable     OBJECT-TYPE
    SYNTAX      SEQUENCE OF TmnxOamPmStsDelayTwlBinEntry
    MAX-ACCESS  not-accessible
    STATUS      current
    DESCRIPTION
        "tmnxOamPmStsDelayTwlBinTable contains TWAMP-Light (Two-Way Active
         Measurement Protocol, Light) frame delay per-bin statistics.  The frame
         delay per-bin statistics kept for TWAMP-Light tests are the same as the
         frame delay per-bin statistics specified for Ethernet DMM (Delay
         Measurement Message) tests in MEF-35 requirement R66."
    REFERENCE
        "MEF-35, 'Service OAM Performance Monitoring Implementation Agreement',
         Metro Ethernet Forum, April 2012, Section 10.1, 'Single-Ended Delay
         Function for Delay, Frame Delay Range, and Inter Delay Variation',
         requirement R66.
         RFC 5357, 'A Two-Way Active Measurement Protocol (TWAMP)', Appendix I,
         'TWAMP Light'."
    ::= { tmnxOamPmStatsTableObjs 8 }

tmnxOamPmStsDelayTwlBinEntry     OBJECT-TYPE
    SYNTAX      TmnxOamPmStsDelayTwlBinEntry
    MAX-ACCESS  not-accessible
    STATUS      current
    DESCRIPTION
        "tmnxOamPmStsDelayTwlBinEntry contains the TWAMP-Light frame delay
         per-bin statistics for one OAM Performance Monitoring Measurement
         Interval Data Set.

         Rows are created in this table when a corresponding row is created in
         tmnxOamPmStsDelayTwlTable.  If the tmnxOamPmStsDelayTwlTable row is
         created with the index value tmnxOamPmCfgBinType = 'fd(1)', then the
         the number of rows created in this table is
         tmnxOamPmCfgBinGroupFdBinCount.  Similarly, 'fdr(2)' and 'ifdv(3)'.

         Rows are destroyed in this table when the corresponding
         tmnxOamPmStsDelayTwlTable row is destroyed.

         When a test is running, the TWAMP-Light statistics for a test's raw
         (i.e.  'miRaw(1)') measurement interval duration can be cleared using
         TIMETRA-CLEAR-MIB::tmnxClearAction.  A successful clear operation zeros
         all the statistics in the specified rows in this table."
    REFERENCE
        "MEF-35, 'Service OAM Performance Monitoring Implementation Agreement',
         Metro Ethernet Forum, April 2012, Section 9.2.1 'Measurement Interval
         Data Sets'."
    INDEX {
        tmnxOamPmCfgSessName,
        tmnxOamPmStsMeasIntvlDuration,
        tmnxOamPmStsIntvlNum,
        tmnxOamPmCfgBinType,
        tmnxOamPmStsDelayTwlBinNum
    }
    ::= { tmnxOamPmStsDelayTwlBinTable 1 }

TmnxOamPmStsDelayTwlBinEntry     ::= SEQUENCE {
    tmnxOamPmStsDelayTwlBinNum       Unsigned32,
    tmnxOamPmStsDelayTwlBinFwdCount  Unsigned32,
    tmnxOamPmStsDelayTwlBinBwdCount  Unsigned32,
    tmnxOamPmStsDelayTwlBin2wyCount  Unsigned32
}

tmnxOamPmStsDelayTwlBinNum       OBJECT-TYPE
    SYNTAX      Unsigned32 (0..9)
    MAX-ACCESS  not-accessible
    STATUS      current
    DESCRIPTION
        "The value of tmnxOamPmStsDelayTwlBinNum specifies the bin number of the
         statistics to be read."
    ::= { tmnxOamPmStsDelayTwlBinEntry 1 }

tmnxOamPmStsDelayTwlBinFwdCount  OBJECT-TYPE
    SYNTAX      Unsigned32
    MAX-ACCESS  read-only
    STATUS      current
    DESCRIPTION
        "The value of tmnxOamPmStsDelayTwlBinFwdCount indicates the number of
         TWAMP-Light frame delay measurements in the forward direction that fall
         within the configured range (in microseconds) of the specified bin.

         For example, suppose the index values for this object are as follows
         (where the index names are abbreviated, and index columns are
         underlined with octothorpes).

         _SessName   _IntvlDuration    _IntvlNum  _BinType  _BinNum
         ##########  ################  #########  ########  #######
         'twlSess1'  'mi15Minutes(2)'          1  'fd(1)'         9

         Then, the value of this object indicates the number of TWAMP-Light
         frame delay measurements (in microseconds) in the forward direction in
         the first interval of 'twlSess1' that fit in the highest configured
         delay range (as configured using tmnxOamPmCfgBinLowerBound)."
    ::= { tmnxOamPmStsDelayTwlBinEntry 2 }

tmnxOamPmStsDelayTwlBinBwdCount  OBJECT-TYPE
    SYNTAX      Unsigned32
    MAX-ACCESS  read-only
    STATUS      current
    DESCRIPTION
        "The value of tmnxOamPmStsDelayTwlBinBwdCount indicates the number of
         TWAMP-Light frame delay measurements in the backward direction that
         fall within the configured range (in microseconds) of the specified
         bin.

         For example, suppose the index values for this object are as follows
         (where the index names are abbreviated, and index columns are
         underlined with octothorpes).

         _SessName   _IntvlDuration    _IntvlNum  _BinType  _BinNum
         ##########  ################  #########  ########  #######
         'twlSess1'  'mi15Minutes(2)'          1  'fd(1)'         0

         Then, the value of this object indicates the number of TWAMP-Light
         frame delay measurements (in microseconds) in the backward direction in
         the first interval of 'twlSess1' that fit in the lowest configured
         delay range (as configured using tmnxOamPmCfgBinLowerBound)."
    ::= { tmnxOamPmStsDelayTwlBinEntry 3 }

tmnxOamPmStsDelayTwlBin2wyCount  OBJECT-TYPE
    SYNTAX      Unsigned32
    MAX-ACCESS  read-only
    STATUS      current
    DESCRIPTION
        "The value of tmnxOamPmStsDelayTwlBin2wyCount indicates the number of
         TWAMP-Light two-way frame delay measurements that fall within the
         configured range (in microseconds) of the specified bin.

         For example, suppose the index values for this object are as follows
         (where the index names are abbreviated, and index columns are
         underlined with octothorpes).

         _SessName   _IntvlDuration    _IntvlNum  _BinType  _BinNum
         ##########  ################  #########  ########  #######
         'twlSess1'  'mi15Minutes(2)'          1  'fd(1)'         0

         Then, the value of this object indicates the number of TWAMP-Light
         two-way frame delay measurements (in microseconds) in the first
         interval of 'twlSess1' that fit in the lowest configured delay range
         (as configured using tmnxOamPmCfgBinLowerBound)."
    ::= { tmnxOamPmStsDelayTwlBinEntry 4 }

--
-- OAM Performance Monitoring Statistics Frame Loss LMM Table
--

tmnxOamPmStsLossLmmTable         OBJECT-TYPE
    SYNTAX      SEQUENCE OF TmnxOamPmStsLossLmmEntry
    MAX-ACCESS  not-accessible
    STATUS      current
    DESCRIPTION
        "tmnxOamPmStsLossLmmTable contains the frame loss statistics for OAM
         Performance Monitoring LMM (Loss Measurement Message) tests."
    REFERENCE
        "ITU-T G.8013/Y.1731, 'OAM functions and mechanisms for Ethernet based
         networks', 07/2011, Section 8.1 'Frame loss measurement (ETH-LM)'.
         MEF-35, 'Service OAM Performance Monitoring Implementation Agreement',
         Metro Ethernet Forum, April 2012, Section 12.1 'Single-Ended Service
         Loss Function'."
    ::= { tmnxOamPmStatsTableObjs 9 }

tmnxOamPmStsLossLmmEntry         OBJECT-TYPE
    SYNTAX      TmnxOamPmStsLossLmmEntry
    MAX-ACCESS  not-accessible
    STATUS      current
    DESCRIPTION
        "tmnxOamPmStsLossLmmEntry contains the LMM test statistics for one OAM
         Performance Monitoring Measurement Interval Data Set.

         A row is created in this table when a tmnxOamPmStsBaseTable row is
         created with tmnxOamPmStsBaseTestType = 'lmm(4)'.

         A row is destroyed in this table when the corresponding
         tmnxOamPmCfgMeasIntvlTable row is destroyed.

         When a test is running, the LMM statistics for a test's raw (i.e.
         'miRaw(1)') measurement interval duration can be cleared using
         TIMETRA-CLEAR-MIB::tmnxClearAction.  A successful clear operation
         zeros all the statistics in the specified row."
    INDEX {
        tmnxOamPmCfgSessName,
        tmnxOamPmStsMeasIntvlDuration,
        tmnxOamPmStsIntvlNum
    }
    ::= { tmnxOamPmStsLossLmmTable 1 }

TmnxOamPmStsLossLmmEntry         ::= SEQUENCE {
    tmnxOamPmStsLossLmmTxFwd         Counter64,
    tmnxOamPmStsLossLmmRxFwd         Counter64,
    tmnxOamPmStsLossLmmTxBwd         Counter64,
    tmnxOamPmStsLossLmmRxBwd         Counter64,
    tmnxOamPmStsLossLmmMinFlrFwd     Unsigned32,
    tmnxOamPmStsLossLmmMaxFlrFwd     Unsigned32,
    tmnxOamPmStsLossLmmAvgFlrFwd     Unsigned32,
    tmnxOamPmStsLossLmmMinFlrBwd     Unsigned32,
    tmnxOamPmStsLossLmmMaxFlrBwd     Unsigned32,
    tmnxOamPmStsLossLmmAvgFlrBwd     Unsigned32
}

tmnxOamPmStsLossLmmTxFwd         OBJECT-TYPE
    SYNTAX      Counter64
    UNITS       "frames"
    MAX-ACCESS  read-only
    STATUS      current
    DESCRIPTION
        "The value of tmnxOamPmStsLossLmmTxFwd indicates the number of service
         frames transmitted in the forward direction for the specified
         measurement interval data set.

         This counter is computed using the procedures in Y.1731 Section 8.1."
    REFERENCE
        "ITU-T G.8013/Y.1731, 'OAM functions and mechanisms for Ethernet based
         networks', 07/2011, Section 8.1 'Frame loss measurement (ETH-LM)'.
         MEF-35, 'Service OAM Performance Monitoring Implementation Agreement',
         Metro Ethernet Forum, April 2012, Section 12.1 'Single-Ended Service
         Loss Function', R112."
    ::= { tmnxOamPmStsLossLmmEntry 1 }

tmnxOamPmStsLossLmmRxFwd         OBJECT-TYPE
    SYNTAX      Counter64
    UNITS       "frames"
    MAX-ACCESS  read-only
    STATUS      current
    DESCRIPTION
        "The value of tmnxOamPmStsLossLmmRxFwd indicates the number of service
         frames received in the forward direction for the specified measurement
         interval data set.

         This counter is computed using the procedures in Y.1731 Section 8.1."
    REFERENCE
        "ITU-T G.8013/Y.1731, 'OAM functions and mechanisms for Ethernet based
         networks', 07/2011, Section 8.1 'Frame loss measurement (ETH-LM)'.
         MEF-35, 'Service OAM Performance Monitoring Implementation Agreement',
         Metro Ethernet Forum, April 2012, Section 12.1 'Single-Ended Service
         Loss Function', R112."
    ::= { tmnxOamPmStsLossLmmEntry 2 }

tmnxOamPmStsLossLmmTxBwd         OBJECT-TYPE
    SYNTAX      Counter64
    UNITS       "frames"
    MAX-ACCESS  read-only
    STATUS      current
    DESCRIPTION
        "The value of tmnxOamPmStsLossLmmTxBwd indicates the number of service
         frames transmitted in the backward direction for the specified
         measurement interval data set.

         This counter is computed using the procedures in Y.1731 Section 8.1."
    REFERENCE
        "ITU-T G.8013/Y.1731, 'OAM functions and mechanisms for Ethernet based
         networks', 07/2011, Section 8.1 'Frame loss measurement (ETH-LM)'.
         MEF-35, 'Service OAM Performance Monitoring Implementation Agreement',
         Metro Ethernet Forum, April 2012, Section 12.1 'Single-Ended Service
         Loss Function', R112."
    ::= { tmnxOamPmStsLossLmmEntry 3 }

tmnxOamPmStsLossLmmRxBwd         OBJECT-TYPE
    SYNTAX      Counter64
    UNITS       "frames"
    MAX-ACCESS  read-only
    STATUS      current
    DESCRIPTION
        "The value of tmnxOamPmStsLossLmmRxBwd indicates the number of service
         frames received in the backward direction for the specified measurement
         interval data set.

         This counter is computed using the procedures in Y.1731 Section 8.1."
    REFERENCE
        "ITU-T G.8013/Y.1731, 'OAM functions and mechanisms for Ethernet based
         networks', 07/2011, Section 8.1 'Frame loss measurement (ETH-LM)'.
         MEF-35, 'Service OAM Performance Monitoring Implementation Agreement',
         Metro Ethernet Forum, April 2012, Section 12.1 'Single-Ended Service
         Loss Function', R112."
    ::= { tmnxOamPmStsLossLmmEntry 4 }

tmnxOamPmStsLossLmmMinFlrFwd     OBJECT-TYPE
    SYNTAX      Unsigned32 (0..100000)
    UNITS       "milli-percent"
    MAX-ACCESS  read-only
    STATUS      current
    DESCRIPTION
        "The value of tmnxOamPmStsLossLmmMinFlrFwd indicates the minimum FLR
         (Frame Loss Ratio) in the forward direction for the specified
         measurement interval data set.

         This value is computed using the procedures in Y.1731 Section 8.1."
    REFERENCE
        "ITU-T G.8013/Y.1731, 'OAM functions and mechanisms for Ethernet based
         networks', 07/2011, Section 8.1 'Frame loss measurement (ETH-LM)'."
    ::= { tmnxOamPmStsLossLmmEntry 5 }

tmnxOamPmStsLossLmmMaxFlrFwd     OBJECT-TYPE
    SYNTAX      Unsigned32 (0..100000)
    UNITS       "milli-percent"
    MAX-ACCESS  read-only
    STATUS      current
    DESCRIPTION
        "The value of tmnxOamPmStsLossLmmMaxFlrFwd indicates the maximum FLR
         (Frame Loss Ratio) in the forward direction for the specified
         measurement interval data set.

         This value is computed using the procedures in Y.1731 Section 8.1."
    REFERENCE
        "ITU-T G.8013/Y.1731, 'OAM functions and mechanisms for Ethernet based
         networks', 07/2011, Section 8.1 'Frame loss measurement (ETH-LM)'."
    ::= { tmnxOamPmStsLossLmmEntry 6 }

tmnxOamPmStsLossLmmAvgFlrFwd     OBJECT-TYPE
    SYNTAX      Unsigned32 (0..100000)
    UNITS       "milli-percent"
    MAX-ACCESS  read-only
    STATUS      current
    DESCRIPTION
        "The value of tmnxOamPmStsLossLmmAvgFlrFwd indicates the average FLR
         (Frame Loss Ratio) in the forward direction for the specified
         measurement interval data set.

         This value is computed using the procedures in Y.1731 Section 8.1."
    REFERENCE
        "ITU-T G.8013/Y.1731, 'OAM functions and mechanisms for Ethernet based
         networks', 07/2011, Section 8.1 'Frame loss measurement (ETH-LM)'."
    ::= { tmnxOamPmStsLossLmmEntry 7 }

tmnxOamPmStsLossLmmMinFlrBwd     OBJECT-TYPE
    SYNTAX      Unsigned32 (0..100000)
    UNITS       "milli-percent"
    MAX-ACCESS  read-only
    STATUS      current
    DESCRIPTION
        "The value of tmnxOamPmStsLossLmmMinFlrBwd indicates the minimum FLR
         (Frame Loss Ratio) in the backward direction for the specified
         measurement interval data set.

         This value is computed using the procedures in Y.1731 Section 8.1."
    REFERENCE
        "ITU-T G.8013/Y.1731, 'OAM functions and mechanisms for Ethernet based
         networks', 07/2011, Section 8.1 'Frame loss measurement (ETH-LM)'."
    ::= { tmnxOamPmStsLossLmmEntry 8 }

tmnxOamPmStsLossLmmMaxFlrBwd     OBJECT-TYPE
    SYNTAX      Unsigned32 (0..100000)
    UNITS       "milli-percent"
    MAX-ACCESS  read-only
    STATUS      current
    DESCRIPTION
        "The value of tmnxOamPmStsLossLmmMaxFlrBwd indicates the maximum FLR
         (Frame Loss Ratio) in the backward direction for the specified
         measurement interval data set.

         This value is computed using the procedures in Y.1731 Section 8.1."
    REFERENCE
        "ITU-T G.8013/Y.1731, 'OAM functions and mechanisms for Ethernet based
         networks', 07/2011, Section 8.1 'Frame loss measurement (ETH-LM)'."
    ::= { tmnxOamPmStsLossLmmEntry 9 }

tmnxOamPmStsLossLmmAvgFlrBwd     OBJECT-TYPE
    SYNTAX      Unsigned32 (0..100000)
    UNITS       "milli-percent"
    MAX-ACCESS  read-only
    STATUS      current
    DESCRIPTION
        "The value of tmnxOamPmStsLossLmmAvgFlrBwd indicates the average FLR
         (Frame Loss Ratio) in the backward direction for the specified
         measurement interval data set.

         This value is computed using the procedures in Y.1731 Section 8.1."
    REFERENCE
        "ITU-T G.8013/Y.1731, 'OAM functions and mechanisms for Ethernet based
         networks', 07/2011, Section 8.1 'Frame loss measurement (ETH-LM)'."
    ::= { tmnxOamPmStsLossLmmEntry 10 }

-- #############################################################################
-- accessible-for-notify Objects
-- #############################################################################

-- #############################################################################
-- Notifications
-- #############################################################################

-- #############################################################################
-- Module Compliance Statements
-- #############################################################################

tmnxOamPmV12v0Compliance         MODULE-COMPLIANCE
    STATUS      current
    DESCRIPTION
        "The compliance statement for management of OAM Performance Management
         on Alcatel-Lucent SROS series systems, release 12.0."
    MODULE  -- this module
        MANDATORY-GROUPS {
            tmnxOamPmV12v0ObjGroup
        }
    ::= { tmnxOamPmCompliances 1 }

-- #############################################################################
-- Object Group Statements
-- #############################################################################

tmnxOamPmV12v0ObjGroup           OBJECT-GROUP
    OBJECTS { -- sorted alphabetically
        tmnxOamPmCfgBinGroupAdminStatus,
        tmnxOamPmCfgBinGroupDescription,
        tmnxOamPmCfgBinGroupFdBinCount,
        tmnxOamPmCfgBinGroupFdrBinCount,
        tmnxOamPmCfgBinGroupIfdvBinCount,
        tmnxOamPmCfgBinGroupRowStatus,
        tmnxOamPmCfgBinGroupTableLastChg,
        tmnxOamPmCfgBinLowerBound,
        tmnxOamPmCfgBinTableLastChg,
        tmnxOamPmCfgDelayDmmAdminStatus,
        tmnxOamPmCfgDelayDmmDataTlvSize,
        tmnxOamPmCfgDelayDmmInterval,
        tmnxOamPmCfgDelayDmmOnDmndStatus,
        tmnxOamPmCfgDelayDmmRowStatus,
        tmnxOamPmCfgDelayDmmRunTimeLeft,
        tmnxOamPmCfgDelayDmmTableLastChg,
        tmnxOamPmCfgDelayDmmTestDuration,
        tmnxOamPmCfgDelayDmmTestId,
        tmnxOamPmCfgLossSlmAdminStatus,
        tmnxOamPmCfgLossSlmChliThreshold,
        tmnxOamPmCfgLossSlmConsecDeltaTs,
        tmnxOamPmCfgLossSlmDataTlvSize,
        tmnxOamPmCfgLossSlmFlrThreshold,
        tmnxOamPmCfgLossSlmInterval,
        tmnxOamPmCfgLossSlmOnDmndStatus,
        tmnxOamPmCfgLossSlmRowStatus,
        tmnxOamPmCfgLossSlmRunTimeLeft,
        tmnxOamPmCfgLossSlmTableLastChg,
        tmnxOamPmCfgLossSlmTestDuration,
        tmnxOamPmCfgLossSlmTestId,
        tmnxOamPmCfgLossSlmTxFrmsPerDelT,
        tmnxOamPmCfgMeasIntvlAccntPolicy,
        tmnxOamPmCfgMeasIntvlBoundaryTyp,
        tmnxOamPmCfgMeasIntvlClockOffset,
        tmnxOamPmCfgMeasIntvlRowStatus,
        tmnxOamPmCfgMeasIntvlTableLstChg,
        tmnxOamPmCfgMeasIntvlsStored,
        tmnxOamPmCfgSessBinGroupId,
        tmnxOamPmCfgSessDescription,
        tmnxOamPmCfgSessEthDestMacAddr,
        tmnxOamPmCfgSessEthPriority,
        tmnxOamPmCfgSessEthSrcMaIndex,
        tmnxOamPmCfgSessEthSrcMdIndex,
        tmnxOamPmCfgSessEthSrcMepId,
        tmnxOamPmCfgSessEthTableLastChg,
        tmnxOamPmCfgSessRowStatus,
        tmnxOamPmCfgSessTableLastChg,
        tmnxOamPmCfgSessTestFamily,
        tmnxOamPmCfgSessType,
        tmnxOamPmStsBaseElapsedTime,
        tmnxOamPmStsBaseOperStatus,
        tmnxOamPmStsBaseStartTime,
        tmnxOamPmStsBaseSuspect,
        tmnxOamPmStsBaseTestFramesRx,
        tmnxOamPmStsBaseTestFramesTx,
        tmnxOamPmStsDelayDmm2wyAvg,
        tmnxOamPmStsDelayDmm2wyMax,
        tmnxOamPmStsDelayDmm2wyMin,
        tmnxOamPmStsDelayDmmBin2wyCount,
        tmnxOamPmStsDelayDmmBinBwdCount,
        tmnxOamPmStsDelayDmmBinFwdCount,
        tmnxOamPmStsDelayDmmBwdAvg,
        tmnxOamPmStsDelayDmmBwdMax,
        tmnxOamPmStsDelayDmmBwdMin,
        tmnxOamPmStsDelayDmmFwdAvg,
        tmnxOamPmStsDelayDmmFwdMax,
        tmnxOamPmStsDelayDmmFwdMin,
        tmnxOamPmStsLossSlmAvailIndBwd,
        tmnxOamPmStsLossSlmAvailIndFwd,
        tmnxOamPmStsLossSlmAvgFlrBwd,
        tmnxOamPmStsLossSlmAvgFlrFwd,
        tmnxOamPmStsLossSlmChliBwd,
        tmnxOamPmStsLossSlmChliFwd,
        tmnxOamPmStsLossSlmHliBwd,
        tmnxOamPmStsLossSlmHliFwd,
        tmnxOamPmStsLossSlmMaxFlrBwd,
        tmnxOamPmStsLossSlmMaxFlrFwd,
        tmnxOamPmStsLossSlmMinFlrBwd,
        tmnxOamPmStsLossSlmMinFlrFwd,
        tmnxOamPmStsLossSlmRxBwd,
        tmnxOamPmStsLossSlmRxFwd,
        tmnxOamPmStsLossSlmTxBwd,
        tmnxOamPmStsLossSlmTxFwd,
        tmnxOamPmStsLossSlmUnavlIndBwd,
        tmnxOamPmStsLossSlmUnavlIndFwd,
        tmnxOamPmStsLossSlmUndtAvlBwd,
        tmnxOamPmStsLossSlmUndtAvlFwd,
        tmnxOamPmStsLossSlmUndtUnavlBwd,
        tmnxOamPmStsLossSlmUndtUnavlFwd,
        tmnxOamPmStsMeasIntvlIndexNewest,
        tmnxOamPmCfgSessIpBypassRouting,
        tmnxOamPmCfgSessIpDstAddress,
        tmnxOamPmCfgSessIpDstAddressType,
        tmnxOamPmCfgSessIpDstUdpPort,
        tmnxOamPmCfgSessIpEgressIfName,
        tmnxOamPmCfgSessIpForwardClass,
        tmnxOamPmCfgSessIpNhAddress,
        tmnxOamPmCfgSessIpNhAddressType,
        tmnxOamPmCfgSessIpProfile,
        tmnxOamPmCfgSessIpServiceId,
        tmnxOamPmCfgSessIpSrcAddress,
        tmnxOamPmCfgSessIpSrcAddressType,
        tmnxOamPmCfgSessIpTableLastChg,
        tmnxOamPmCfgSessIpTtl,
        tmnxOamPmCfgTwampLtAdminStatus,
        tmnxOamPmCfgTwampLtInterval,
        tmnxOamPmCfgTwampLtOnDmndStatus,
        tmnxOamPmCfgTwampLtPadSize,
        tmnxOamPmCfgTwampLtRowStatus,
        tmnxOamPmCfgTwampLtRunTimeLeft,
        tmnxOamPmCfgTwampLtTableLastChg,
        tmnxOamPmCfgTwampLtTestDuration,
        tmnxOamPmCfgTwampLtTestId,
        tmnxOamPmCfgTwlRflAdminStatus,
        tmnxOamPmCfgTwlRflDescription,
        tmnxOamPmCfgTwlRflInactTimer,
        tmnxOamPmCfgTwlRflListenUdpPort,
        tmnxOamPmCfgTwlRflPfxDescription,
        tmnxOamPmCfgTwlRflPfxRowStatus,
        tmnxOamPmCfgTwlRflPfxTableLstChg,
        tmnxOamPmCfgTwlRflRowStatus,
        tmnxOamPmCfgTwlRflTableLastChg,
        tmnxOamPmStsDelayTwl2wyAvg,
        tmnxOamPmStsDelayTwl2wyMax,
        tmnxOamPmStsDelayTwl2wyMin,
        tmnxOamPmStsDelayTwlBin2wyCount,
        tmnxOamPmStsDelayTwlBinBwdCount,
        tmnxOamPmStsDelayTwlBinFwdCount,
        tmnxOamPmStsDelayTwlBwdAvg,
        tmnxOamPmStsDelayTwlBwdMax,
        tmnxOamPmStsDelayTwlBwdMin,
        tmnxOamPmStsDelayTwlFwdAvg,
        tmnxOamPmStsDelayTwlFwdMax,
        tmnxOamPmStsDelayTwlFwdMin,
        tmnxOamPmStsTwlRflFramesRx,
        tmnxOamPmStsTwlRflFramesTx,
        tmnxOamPmStsTwlRflUpTime,
        tmnxOamPmCfgLossLmmAdminStatus,
        tmnxOamPmCfgLossLmmInterval,
        tmnxOamPmCfgLossLmmOnDmndStatus,
        tmnxOamPmCfgLossLmmRowStatus,
        tmnxOamPmCfgLossLmmRunTimeLeft,
        tmnxOamPmCfgLossLmmTableLastChg,
        tmnxOamPmCfgLossLmmTestDuration,
        tmnxOamPmCfgLossLmmTestId,
        tmnxOamPmStsLossLmmAvgFlrBwd,
        tmnxOamPmStsLossLmmAvgFlrFwd,
        tmnxOamPmStsLossLmmMaxFlrBwd,
        tmnxOamPmStsLossLmmMaxFlrFwd,
        tmnxOamPmStsLossLmmMinFlrBwd,
        tmnxOamPmStsLossLmmMinFlrFwd,
        tmnxOamPmStsLossLmmRxBwd,
        tmnxOamPmStsLossLmmRxFwd,
        tmnxOamPmStsLossLmmTxBwd,
        tmnxOamPmStsLossLmmTxFwd
    }
    STATUS      current
    DESCRIPTION
        "The group of objects supporting management of the OAM Performance
         Management functionality on Alcatel-Lucent SROS Release 12.0."
    ::= { tmnxOamPmV12v0ObjGroups 1 }

-- #############################################################################
-- Notification Group Statements
-- #############################################################################

END
