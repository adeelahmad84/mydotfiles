TIMETRA-OSPF-NG-MIB DEFINITIONS ::= BEGIN 

IMPORTS 
    MODULE-IDENTITY, OBJECT-TYPE, NOTIFICATION-TYPE, 
    Counter32, Gauge32, Integer32, Unsigned32 
        FROM SNMPv2-SMI 

    TEXTUAL-CONVENTION, TruthValue, StorageType, RowStatus,
    TimeStamp, TimeInterval, DateAndTime, DisplayString 
        FROM SNMPv2-TC 

    MODULE-COMPLIANCE, OBJECT-GROUP, NOTIFICATION-GROUP 
        FROM SNMPv2-CONF 

    InterfaceIndex,InterfaceIndexOrZero
        FROM IF-MIB 
    
    InetAddressType, InetAddress, InetAddressPrefixLength 
        FROM INET-ADDRESS-MIB 

    Metric, BigMetric, Status,  
    HelloRange, DesignatedRouterPriority 
        FROM OSPF-MIB
       
    TNamedItemOrEmpty, TmnxOspfInstance, TmnxOperState, TmnxEnabledDisabled,
    TmnxReferenceBandwidth
        FROM TIMETRA-TC-MIB
        
    vRtrID, TmnxInetCidrNextHopOwner
        FROM TIMETRA-VRTR-MIB 

    timetraSRMIBModules, tmnxSRObjs, 
    tmnxSRNotifyPrefix, tmnxSRConfs                              
        FROM TIMETRA-GLOBAL-MIB;
             
timetraOspfNgMIBModule MODULE-IDENTITY
        LAST-UPDATED "201401010000Z"
        ORGANIZATION "Alcatel-Lucent"
        CONTACT-INFO
            "Alcatel-Lucent SROS Support
             Web: http://support.alcatel-lucent.com"
    DESCRIPTION
        "This document is the SNMP MIB module to manage and provision
         OSPF protocol for the Alcatel-Lucent SROS device.
       
         Copyright 2003-2014 Alcatel-Lucent.  All rights reserved.
         Reproduction of this document is authorized on the condition that
         the foregoing copyright notice is included.
       
         This SNMP MIB module (Specification) embodies Alcatel-Lucent's
         proprietary intellectual property.  Alcatel-Lucent retains 
         all title and ownership in the Specification, including any 
         revisions.
       
         Alcatel-Lucent grants all interested parties a non-exclusive 
         license to use and distribute an unmodified copy of this 
         Specification in connection with management of Alcatel-Lucent 
         products, and without fee, provided this copyright notice and 
         license appear on all copies.
       
         This Specification is supplied 'as is', and Alcatel-Lucent 
         makes no warranty, either express or implied, as to the use, 
         operation, condition, or performance of the Specification."
--
--  Revision History
--
        REVISION        "201401010000Z"
        DESCRIPTION     "Rev 12.0               1 Jan 2014 00:00
                         12.0 release of the TIMETRA-OSPF-NG-MIB."

        REVISION        "201102010000Z"
        DESCRIPTION     "Rev 9.0                1 Feb 2011 00:00
                         9.0 release of the TIMETRA-OSPF-NG-MIB."

        REVISION        "200902280000Z"
        DESCRIPTION     "Rev 7.0                28 Feb 2009 00:00
                         7.0 release of the TIMETRA-OSPF-NG-MIB."

        REVISION        "200807010000Z"
        DESCRIPTION     "Rev 6.1                01 Jul 2008 00:00
                         6.1 release of the TIMETRA-OSPF-NG-MIB."

        REVISION        "200801010000Z"
        DESCRIPTION     "Rev 6.0                01 Jan 2008 00:00
                         6.0 release of the TIMETRA-OSPF-NG-MIB."

        REVISION        "200701010000Z"
        DESCRIPTION     "Rev 5.0                01 Jan 2007 00:00
                         5.0 release of the TIMETRA-OSPF-NG-MIB."

        REVISION        "200603270000Z"   
        DESCRIPTION     "Rev 0.1                27 Mar 2006 00:00
                         Initial version of the TIMETRA-OSPF-NG-MIB."
        ::= { timetraSRMIBModules 36 }
 
--
--
tmnxOspfObjects         OBJECT IDENTIFIER ::= { tmnxSRObjs 36 }
tmnxOspfNotifyPrefix   OBJECT IDENTIFIER ::= { tmnxSRNotifyPrefix 36 }
    tmnxOspfNotifications   OBJECT IDENTIFIER ::= { tmnxOspfNotifyPrefix 0 }
tmnxOspfConformance     OBJECT IDENTIFIER ::= { tmnxSRConfs 36 }

 --
 -- Textual Conventions
 --
TmnxOspfUpToRefreshIntervalTc ::= TEXTUAL-CONVENTION 
    DISPLAY-HINT "d" 
    STATUS        current 
    DESCRIPTION 
        "The value of TmnxOspfUpToRefreshIntervalTc provides values one 
         might be able to configure for variables bounded by the Refresh 
         Interval." 
    SYNTAX      Integer32 (0..1800) 
 
TmnxOspfDeadIntRangeTc ::= TEXTUAL-CONVENTION 
    DISPLAY-HINT "d" 
    STATUS        current 
    DESCRIPTION 
        "The value of TmnxOspfDeadIntRangeTc provides the range, in seconds, 
         of the dead interval value." 
    SYNTAX      Integer32 (1..'FFFF'h) 
    
TmnxOspfRouterIdTc ::= TEXTUAL-CONVENTION 
    DISPLAY-HINT "d" 
    STATUS      current 
    DESCRIPTION 
        "The value of TmnxOspfRouterIdTc provides a 32-bit, unsigned integer 
         uniquely identifying the router in the Autonomous System. To ensure 
         uniqueness, this may default to the value of one of the router's 
         IPv4 host addresses if IPv4 is configured on the router." 
    SYNTAX      Unsigned32 (0..'FFFFFFFF'h) 
 
TmnxOspfAreaIdTc ::= TEXTUAL-CONVENTION 
    DISPLAY-HINT "d" 
    STATUS      current 
    DESCRIPTION 
        "The value of TmnxOspfAreaIdTc provides an OSPF Area Identifier." 
    SYNTAX      Unsigned32 (0..'FFFFFFFF'h) 
 
TmnxOspfIfInstIdTc ::= TEXTUAL-CONVENTION 
    DISPLAY-HINT "d" 
    STATUS      current 
    DESCRIPTION 
        "The value of TmnxOspfIfInstIdTc provides an OSPF interface 
         instance ID." 
    SYNTAX      Integer32 (0..255) 

TmnxOspfPreference ::= TEXTUAL-CONVENTION
    STATUS current
    DESCRIPTION
        "The value of TmnxOspfPreference provides a route preference value. 
         This value will be used during the route selection algorithm."
    SYNTAX INTEGER (1..255)
 
TmnxOspfAuthenticationType ::= TEXTUAL-CONVENTION 
    STATUS      current 
    DESCRIPTION 
        "The value TmnxOspfAuthenticationType provides the authentication 
         type.  This type of authentication is only applied to interfaces with 
         tmnxOspfVersion equal to 'version2'." 
    SYNTAX      INTEGER { 
                    none (0), 
                    simplePassword (1), 
                    md5 (2) 
                } 

TmnxOspfIfMD5KeyId      ::= TEXTUAL-CONVENTION
    STATUS      current
    DESCRIPTION
        "The value of TmnxOspfIfMD5KeyId provides a unique identifier 
         for a key to be used for authentication on a specific OSPFv2
         IP address.
         The value of 0 means that no keys are configured."
    SYNTAX      Integer32 (0..255)

TmnxOspfRestartReasonTc ::= TEXTUAL-CONVENTION
    STATUS      current
    DESCRIPTION "The TmnxOspfRestartReasonTc data 
                 type is an enumerated integer that 
                 describes the values used to identify
                 OSPF graceful restart reason."
    SYNTAX      INTEGER { unknown (0),       -- not attempted 
                          swRestart (1),     -- software restart 
                          swReload (2),      -- software reload/upgrade 
                          switchRed (3) -- switch to redundant control processor 
                        } 

TmnxOspfIfTypeTc ::= TEXTUAL-CONVENTION
    STATUS      current
    DESCRIPTION "The TmnxOspfIfTypeTc data type is an
                 enumerated integer that describes the
                 OSPF interface type."
    SYNTAX      INTEGER { 
                    unspecified (0),
                    broadcast (1), 
                    nbma (2), 
                    pointToPoint (3), 
                    pointToMultipoint (5),
                    secondary (6)
                } 

TmnxOspfShamIfMetricTc ::= TEXTUAL-CONVENTION
     STATUS       current
     DESCRIPTION  "The TmnxOspfShamIfMetricTc data type provides 
                   a metric value for sham-link"
     SYNTAX       Integer32 (1..'FFFF'h)

TmnxOspfLsaFilterOutTc ::= TEXTUAL-CONVENTION
    STATUS      current
    DESCRIPTION "The TmnxOspfLsaFilterOutTc data type is an enumerated
                 integer that describes the OSPF LSA Flooding Reduction type."
    SYNTAX      INTEGER { 
                    none (0),
                    all (1), 
                    exceptOwnRtrLsa (2), 
                    exceptOwnRtrLsaAndDefaults (3)
                } 

-- These parameters apply globally to all OSPF protocol instances. 
tmnxOspfScalars         OBJECT IDENTIFIER ::= { tmnxOspfObjects 1 }

tmnxOspfGeneralEntries     OBJECT-TYPE
    SYNTAX      Gauge32
    MAX-ACCESS  read-only
    STATUS      current
    DESCRIPTION
        "The value of tmnxOspfGeneralEntries indicates the number of row
         entries in the tmnxOspfGeneralTable.  This is the number of
         OSPF instances currently configured."
    ::= { tmnxOspfScalars 1 }
 

-- OSPF General Table 
-- 
-- These parameters apply globally to an OSPF protocol instance. 

 
tmnxOspfGeneralTable OBJECT-TYPE 
    SYNTAX          SEQUENCE OF TmnxOspfGeneralEntry 
    MAX-ACCESS      not-accessible 
    STATUS          current 
    DESCRIPTION 
        "The tmnxOspfGeneralTable contains information describing the 
         configured parameters and cumulative statistics of an OSPF 
         instance's attached areas." 
    ::= { tmnxOspfObjects 2 } 
 
tmnxOspfGeneralEntry OBJECT-TYPE 
    SYNTAX          TmnxOspfGeneralEntry 
    MAX-ACCESS      not-accessible 
    STATUS          current 
    DESCRIPTION 
        "The tmnxOspfGeneralEntry contains information describing the 
         configured parameters and cumulative statistics of one of an 
         OSPF instance's attached areas.  An OSPF row entry is created 
         or deleted in this table by setting the tmnxOspfRowStatus object." 
        INDEX       {   vRtrID, 
                        tmnxOspfVersion, 
                        tmnxOspfInstance
                    } 
    ::= { tmnxOspfGeneralTable 1 } 
 
TmnxOspfGeneralEntry ::= SEQUENCE {
        tmnxOspfVersion                 INTEGER,
        tmnxOspfInstance                TmnxOspfInstance,
        tmnxOspfGeneralLastChanged      TimeStamp,
        tmnxOspfRouterId                TmnxOspfRouterIdTc,
        tmnxOspfAdminState              Status, 
        tmnxOspfASBdrRtrStatus          TruthValue, 
        tmnxOspfRFC1583Compatibility    TruthValue,
        tmnxOspfExtLsdbLimit            Integer32,
        tmnxOspfMulticastExtensions     BITS, 
        tmnxOspfExitOverflowInterval    Unsigned32, 
        tmnxOspfDemandExtensions        TruthValue, 
        tmnxOspfReferenceBandwidth      TmnxReferenceBandwidth,  
        tmnxOspfStrictLsaChecking       TruthValue, 
        tmnxOspfRestartSupport          INTEGER, 
        tmnxOspfRestartInterval         TmnxOspfUpToRefreshIntervalTc, 
        tmnxOspfPreference              TmnxOspfPreference,
        tmnxOspfExternalPreference      TmnxOspfPreference,
        tmnxOspfExportPolicy1           TNamedItemOrEmpty,
        tmnxOspfExportPolicy2           TNamedItemOrEmpty,
        tmnxOspfExportPolicy3           TNamedItemOrEmpty,
        tmnxOspfExportPolicy4           TNamedItemOrEmpty,
        tmnxOspfExportPolicy5           TNamedItemOrEmpty,
        tmnxOspfManualSpfTrigger        INTEGER,
        tmnxOspfOverloadAdmState        Status,
        tmnxOspfOverloadInterval        Unsigned32,
        tmnxOspfBootOverloadAdmState    INTEGER,
        tmnxOspfBootOverloadInterval    Unsigned32,
        tmnxOspfOverloadStubs           TruthValue,
        tmnxOspfSpfMaxWait              Unsigned32,
        tmnxOspfSpfInitialWait          Unsigned32,
        tmnxOspfSpfSecondWait           Unsigned32,
        tmnxOspfLsaGenMaxWait           Unsigned32,
        tmnxOspfLsaGenInitialWait       Unsigned32,
        tmnxOspfLsaGenSecondWait        Unsigned32,
        tmnxOspfLsaArrivalWait          Unsigned32,
        tmnxOspfTESupport               TruthValue,
        tmnxOspfUnicastImport           TruthValue,
        tmnxOspfMulticastImport         TruthValue,
        tmnxOspfGREnable                TruthValue,
        tmnxOspfGRHelperMode            TruthValue,
        tmnxOspfRowStatus               RowStatus,
        tmnxOspfAsbrDomainId            Integer32,
        tmnxOspfIgnoreDNBit             TruthValue,
        tmnxOspfSuppressDNBit           TruthValue,
        tmnxOspfLdpSyncAdminState       Status,
        tmnxOspfVpnDomainType           INTEGER,
        tmnxOspfVpnDomainId             OCTET STRING,
        tmnxOspfVpnTag                  Unsigned32,
        tmnxOspfSuperBackBone           TruthValue,
        tmnxOspfLdpOverRsvp             TmnxEnabledDisabled,
        tmnxOspfExportLimit             Unsigned32,
        tmnxOspfExportLimitLogPercent   Unsigned32,
        tmnxOspfRsvpShortcut            TruthValue,
        tmnxOspfAdvertiseTunnelLink     TruthValue,
        tmnxOspfImportPolicy1           TNamedItemOrEmpty,
        tmnxOspfImportPolicy2           TNamedItemOrEmpty,
        tmnxOspfImportPolicy3           TNamedItemOrEmpty,
        tmnxOspfImportPolicy4           TNamedItemOrEmpty,
        tmnxOspfImportPolicy5           TNamedItemOrEmpty,
        tmnxOspfLoopfreeAlternate       TruthValue,
        tmnxOspfLsaAccumulate           Unsigned32,
        tmnxOspfRedistDelay             Unsigned32,
        tmnxOspfIncrSpfWait             Unsigned32,
        tmnxOspfOverloadInclExt2        TruthValue
    } 

tmnxOspfVersion OBJECT-TYPE 
    SYNTAX      INTEGER {
                    version2 (2), 
                    version3 (3)
                } 
    MAX-ACCESS  not-accessible 
    STATUS      current 
    DESCRIPTION 
        "The value of tmnxOspfVersion specifies the version number of OSPF 
         supported by this OSPF instance.  The version number of OSPF for 
         IPv6 is 3." 
    ::= { tmnxOspfGeneralEntry 1 } 
 
tmnxOspfInstance OBJECT-TYPE 
    SYNTAX      TmnxOspfInstance 
    MAX-ACCESS  not-accessible 
    STATUS      current 
    DESCRIPTION 
        "The value of tmnxOspfInstance is a unique integer that
         identifies a specific instance of a version of the
         OSPF protocol running in the router instance specified
         by the vRtrID index." 
    ::= { tmnxOspfGeneralEntry 2 } 
 
tmnxOspfGeneralLastChanged  OBJECT-TYPE
    SYNTAX      TimeStamp
    MAX-ACCESS  read-only
    STATUS      current
    DESCRIPTION
        "The value of tmnxOspfGeneralLastChanged indicates the sysUpTime
         when a configurable object in this row was last modified."
    ::= { tmnxOspfGeneralEntry 4 } 

tmnxOspfRouterId OBJECT-TYPE 
    SYNTAX      TmnxOspfRouterIdTc 
    MAX-ACCESS  read-create 
    STATUS      current 
    DESCRIPTION 
        "The value of tmnxOspfRouterId specifies a 32-bit integer uniquely
         identifying the router in the Autonomous System.  By convention 
         to ensure uniqueness, this may default to the value of one of the 
         router's IPv4 host addresses, represented as a 32-bit unsigned 
         integer, if IPv4 is configured on the router." 
    ::= { tmnxOspfGeneralEntry 5 } 
 
tmnxOspfAdminState     OBJECT-TYPE 
    SYNTAX      Status 
    MAX-ACCESS  read-create 
    STATUS      current 
    DESCRIPTION 
        "The value of tmnxOspfAdminState specifies the desired 
         administrative status of this instance of OSPF in the router. 
         The value 'enabled' activates this instance of the OSPF protocol.  
         The value' disabled' stops it."
    ::= { tmnxOspfGeneralEntry 6 } 
 
tmnxOspfASBdrRtrStatus OBJECT-TYPE 
    SYNTAX      TruthValue 
    MAX-ACCESS  read-create 
    STATUS      current 
    DESCRIPTION 
        "The value of tmnxOspfASBdrRtrStatus specifies whether this router
         is configured as an Autonomous System border router."
    REFERENCE 
        "OSPF Version 2, Section 3.3 Classification of routers" 
    ::= { tmnxOspfGeneralEntry 7 } 
 
tmnxOspfRFC1583Compatibility  OBJECT-TYPE 
    SYNTAX       TruthValue 
    MAX-ACCESS   read-create 
    STATUS       current 
    DESCRIPTION 
        "The value of tmnxOspfRFC1583Compatibility indicates the
         metrics used to choose among multiple AS-external-LSAs. 
         When tmnxOspfRFC1583Compatibility is set to 'true', only cost
         will be used when choosing among multiple AS-external-LSAs 
         advertising the same destination. When tmnxOspfRFC1583Compatibility 
         is set to 'false', preference will be driven first by the 
         type of path using cost only to break ties. 
        
         This object is valid only when tmnxOspfVersion is 'version2'." 
    REFERENCE 
        "OSPF Version 2, Section 16.4.1 External path preferences" 
    ::= { tmnxOspfGeneralEntry 8 } 
  
tmnxOspfExtLsdbLimit OBJECT-TYPE 
    SYNTAX      Integer32 (-1..'7FFFFFFF'h) 
    MAX-ACCESS  read-create 
    STATUS      current 
    DESCRIPTION 
        "The value of tmnxOspfExtLsdbLimit specifies the maximum 
         number of non-default AS-external-LSAs entries that can be 
         stored in the link-state database. If the value is -1, then 
         there is no limit. 
  
         When the number of non-default AS-external-LSAs in a router's 
         link-state database reaches tmnxOspfExtLsdbLimit, the 
         router enters Overflow state. The router never holds more than 
         tmnxOspfExtLsdbLimit non-default AS-external-LSAs in its 
         database.  tmnxOspfExtLsdbLimit MUST be set identically in 
         all routers attached to the OSPF backbone and/or any regular 
         OSPF area. (i.e., OSPF stub areas and NSSAs are excluded)."  
    ::= { tmnxOspfGeneralEntry 9 } 
 
tmnxOspfMulticastExtensions OBJECT-TYPE 
    SYNTAX      BITS { 
                    intraAreaMulticast(0), 
                    interAreaMulticast(1), 
                    interAsMulticast(2) 
                } 
    MAX-ACCESS  read-create 
    STATUS      current 
    DESCRIPTION 
        "The value of tmnxOspfMulticastExtensions specifies a Bit Mask 
         indicating whether the router is forwarding IPv6 multicast
         datagrams based on the algorithms defined in the Multicast 
         Extensions to OSPF. 
 
         When the intraAreaMulticast bit is set, it indicates that the 
         router can forward IPv6 multicast datagrams in the router's 
         directly attached areas (called intra-area multicast routing). 
 
         When the interAreaMulticast bit is set, it indicates that the 
         router can forward IPv6 multicast datagrams between OSPFv3 
         areas (called inter-area multicast routing). 
 
         When the interAsMulticast bit is set, it indicates that the 
         router can forward IPv6 multicast datagrams between Autonomous 
         Systems (called inter-AS multicast routing). 
 
         Only certain combinations of bit settings are allowed, namely: 
            - All bits cleared (no multicasting) 
            - intraAreaMulticast only, 
            - intraAreaMulticast and interAreaMulticast, 
            - intraAreaMulticast and interAsMulticast 
            - intraAreaMulticast, interAreaMulticast and interAsMulticast 
         By default, all bits are cleared."
    DEFVAL { {} } 
    ::= { tmnxOspfGeneralEntry 10 } 
 
tmnxOspfExitOverflowInterval OBJECT-TYPE 
    SYNTAX      Unsigned32 
    UNITS       "seconds" 
    MAX-ACCESS  read-create 
    STATUS      current 
    DESCRIPTION 
        "The value of tmnxOspfExitOverflowInterval specifies the number of 
         seconds that, after entering Overflow State, a router will attempt
         to leave Overflow State. This allows the router to again originate
         non-default  AS-external-LSAs. When set to 0, the router will not
         leave Overflow state until restarted."
    DEFVAL { 0 } 
    ::= { tmnxOspfGeneralEntry 11 } 
 
tmnxOspfDemandExtensions OBJECT-TYPE 
    SYNTAX      TruthValue 
    MAX-ACCESS  read-create 
    STATUS      current 
    DESCRIPTION 
        "The value of tmnxOspfDemandExtensions specifies the router's support
         for demand routing."
    REFERENCE 
        "OSPF Version 2, Appendix on Demand Routing" 
    ::= { tmnxOspfGeneralEntry 12 } 
 
tmnxOspfReferenceBandwidth OBJECT-TYPE  
    SYNTAX      TmnxReferenceBandwidth (1..4000000000)
    UNITS       "1000 bits per second"
    MAX-ACCESS  read-create
    STATUS      current
    DESCRIPTION
        "The value of tmnxOspfReferenceBandwidth specifies default
         metrics to any OSPF interface.  The cost metric is calculated
         by dividing the value of tmnxOspfReferenceBandwidth by the bandwidth
         of the interface.  The default value of 100,000,000 Kbps or
         100 Gps provides a 10-Mbs link with a cost of 10000, a 100-Mbs
         link with a cost of 1000, a 1-Gbs link with a cost of 100 and
         10-Gbs link with a cost of 10.  To override this default cost
         on a particular interface, set tmnxOspfIfCfgMetric for that
         interface.
         The maximum value of 4,000,000,000 Kbps amounts to 
         4 Terabit per second."
    DEFVAL { 100000000 }
    ::= { tmnxOspfGeneralEntry 13 } 
 
tmnxOspfStrictLsaChecking OBJECT-TYPE 
    SYNTAX       TruthValue 
    MAX-ACCESS   read-create 
    STATUS       current 
    DESCRIPTION 
        "The value of tmnxOspfStrictLsaChecking indicates if strict 
         LSA checking is enabled for graceful restart. 
        
         This object is persistent and when written the entity SHOULD 
         save the change to non-volatile storage." 
    ::= { tmnxOspfGeneralEntry 14 } 
     
tmnxOspfRestartSupport OBJECT-TYPE  
    SYNTAX      INTEGER { 
                    none (1),  
                    plannedOnly (2),  
                    plannedAndUnplanned (3)  
                } 
    MAX-ACCESS  read-create  
    STATUS      current  
    DESCRIPTION  
        "The value of tmnxOspfRestartSupport specifies the router's support
         for OSPF graceful restart.  Options include: no restart support, 
         only planned restarts or both planned and unplanned restarts."
    ::= { tmnxOspfGeneralEntry 15 }  
        
tmnxOspfRestartInterval OBJECT-TYPE  
    SYNTAX      TmnxOspfUpToRefreshIntervalTc 
    UNITS       "seconds"  
    MAX-ACCESS  read-create  
    STATUS      current  
    DESCRIPTION  
        "The value of tmnxOspfRestartInterval specifies the configured
         OSPF graceful restart timeout interval."
    ::= { tmnxOspfGeneralEntry 16 }  
        
tmnxOspfPreference OBJECT-TYPE
    SYNTAX      TmnxOspfPreference
    MAX-ACCESS  read-create
    STATUS      current
    DESCRIPTION
        "The value of tmnxOspfPreference specifies the
         route preference for OSPF internal routes."
    DEFVAL { 10 }
    ::= { tmnxOspfGeneralEntry 17 }

tmnxOspfExternalPreference OBJECT-TYPE
    SYNTAX      TmnxOspfPreference
    MAX-ACCESS  read-create
    STATUS      current
    DESCRIPTION
        "The value of tmnxOspfExternalPreference specifies the
         route preference for OSPF external routes."
    DEFVAL { 150 }
    ::= { tmnxOspfGeneralEntry 18 }

tmnxOspfExportPolicy1 OBJECT-TYPE
    SYNTAX      TNamedItemOrEmpty
    MAX-ACCESS  read-create
    STATUS      current
    DESCRIPTION
        "The value of tmnxOspfExportPolicy1 specifies the name of
         1st Export policy to be used to be used for determining which
         routes are exported from  the routing table to OSPF."
    DEFVAL { ''H }   -- the empty string
    ::= { tmnxOspfGeneralEntry 19 }

tmnxOspfExportPolicy2 OBJECT-TYPE
    SYNTAX      TNamedItemOrEmpty
    MAX-ACCESS  read-create
    STATUS      current
    DESCRIPTION
        "The value of tmnxOspfExportPolicy2 specifies the name of 2nd
         Export policy to be used to be used for determining which routes
         are exported from the routing table to OSPF."
    DEFVAL { ''H }   -- the empty string
    ::= { tmnxOspfGeneralEntry 20 }

tmnxOspfExportPolicy3 OBJECT-TYPE
    SYNTAX      TNamedItemOrEmpty
    MAX-ACCESS  read-create
    STATUS      current
    DESCRIPTION
        "The value of tmnxOspfExportPolicy3 specifies the name of 3rd
         Export policy to be used to be used for determining which routes
         are exported from the routing table to OSPF."
    DEFVAL { ''H }   -- the empty string
    ::= { tmnxOspfGeneralEntry 21 }

tmnxOspfExportPolicy4 OBJECT-TYPE
    SYNTAX      TNamedItemOrEmpty
    MAX-ACCESS  read-create
    STATUS      current
    DESCRIPTION
        "The value of tmnxOspfExportPolicy4 specifies the name of 4rd
         Export policy to be used to be used for determining which routes
         are exported from the routing table to OSPF."
    DEFVAL { ''H }   -- the empty string
    ::= { tmnxOspfGeneralEntry 22 }

tmnxOspfExportPolicy5 OBJECT-TYPE
    SYNTAX      TNamedItemOrEmpty
    MAX-ACCESS  read-create
    STATUS      current
    DESCRIPTION
        "The value of tmnxOspfExportPolicy5 specifies the name of 5th
         Export policy to be used to be used for determining which routes
         are exported from  the routing table to OSPF."
    DEFVAL { ''H }   -- the empty string
    ::= { tmnxOspfGeneralEntry 23 }

tmnxOspfManualSpfTrigger OBJECT-TYPE
    SYNTAX      INTEGER {
                    noAction(1),
                    runTotalSpf(2),
                    runExternalsSpf(3)
                }
    MAX-ACCESS  read-create
    STATUS      current
    DESCRIPTION
        "The value of tmnxOspfManualSpfTrigger specifies a manual Dijkstra
         SPF calculation trigger.

         When tmnxOspfManualSpfTrigger is set to 'runTotalSpf' a normal
         Dijkstra SPF calculation is performed.

         When tmnxOspfManualSpfTrigger is set to 'runExternalsSpf',
         only the AS External LSAs are recalculated.
         
         GETs and GETNEXTs on this variable return 'noAction'."
    DEFVAL { noAction }
    ::= { tmnxOspfGeneralEntry 24 }
     
tmnxOspfOverloadAdmState OBJECT-TYPE
    SYNTAX      Status
    MAX-ACCESS  read-create
    STATUS      current
    DESCRIPTION
        "The value of tmnxOspfOverloadAdmState specifies a command
         used to manually make the system go in or out of overload
         state. Whenever this value is set, tmnxOspfOverloadInterval 
         is reset to back to default."
    DEFVAL { disabled }
    ::= { tmnxOspfGeneralEntry 25 }

tmnxOspfOverloadInterval OBJECT-TYPE
    SYNTAX      Unsigned32 (0..1800)
    UNITS       "seconds" 
    MAX-ACCESS  read-create
    STATUS      current
    DESCRIPTION
        "The value of tmnxOspfOverloadInterval specifies how long
         (in seconds) OSPF should remain in overload state. This is
         reset to default when tmnxOspfOverloadAdmState is modified.
         The value of 0 implies that the system is indefinitely in
         overload."
    DEFVAL { 0 }
    ::= { tmnxOspfGeneralEntry 26 }

tmnxOspfBootOverloadAdmState OBJECT-TYPE
    SYNTAX      INTEGER {
                    disabled(1),
                    enabled(2),
                    enabledWaitForBgp(3)
                }
    MAX-ACCESS  read-create
    STATUS      current
    DESCRIPTION
        "The value of tmnxOspfBootOverloadAdmState specifies the
         desired overload state that should be aplied after boot
         Whenever this value is set, tmnxOspfBootOverloadInterval 
         is reset to back to default."
    DEFVAL { disabled }
    ::= { tmnxOspfGeneralEntry 27 }

tmnxOspfBootOverloadInterval OBJECT-TYPE
    SYNTAX      Unsigned32 (0..1800)
    UNITS       "seconds" 
    MAX-ACCESS  read-create
    STATUS      current
    DESCRIPTION
        "The value of tmnxOspfBootOverloadInterval specifies the configured
         value for OSPF for which it should remain in overload state on
         boot-up. This is reset to default when tmnxOspfBootOverloadAdmState
         is modified.  The value of 0 implies that the system is
         indefinitely in overload."
    DEFVAL { 0 }
    ::= { tmnxOspfGeneralEntry 28 }

tmnxOspfOverloadStubs OBJECT-TYPE
    SYNTAX      TruthValue
    MAX-ACCESS  read-create
    STATUS      current
    DESCRIPTION
        "The value of tmnxOspfOverloadStubs specifies if the OSPF
         stub networks should be advertised with a maximum metric value
         when the system goes into overload state for any reason.
         If the value is 'true', the system uses the maximum metric
         value."
    DEFVAL { false }
    ::= { tmnxOspfGeneralEntry 29 }

tmnxOspfSpfMaxWait OBJECT-TYPE
    SYNTAX      Unsigned32 (10..120000)
    UNITS       "milliseconds"
    MAX-ACCESS  read-create
    STATUS      current
    DESCRIPTION
        "The value of tmnxOspfSpfMaxWait defines the maximum
         interval between two consecutive full SPF calculations."
    DEFVAL { 10000 }
    ::= { tmnxOspfGeneralEntry 30 }

tmnxOspfSpfInitialWait OBJECT-TYPE
    SYNTAX      Unsigned32 (10..100000)
    UNITS       "milliseconds"
    MAX-ACCESS  read-create
    STATUS      current
    DESCRIPTION
        "The value of tmnxOspfSpfInitialWait defines the holddown
         time before a full SPF calculation delay after a topology
         change."
    DEFVAL { 1000 }
    ::= { tmnxOspfGeneralEntry 31 }

tmnxOspfSpfSecondWait OBJECT-TYPE
    SYNTAX      Unsigned32 (10..100000)
    UNITS       "milliseconds"
    MAX-ACCESS  read-create
    STATUS      current
    DESCRIPTION
        "The value of tmnxOspfSpfSecondWait defines the hold time
         between the first and second SPF calculation. Subsequent SPF 
         runs will occur at exponentially increasing intervals of the 
         tmnxOspfSpfSecondWait value i.e., if tmnxOspfSpfSecondWait 
         is 1000, then the next SPF triggered by an event during this 
         interval will run after 2000 msec, and the subsequent one at 
         4000 msec, etc. until it is capped off at tmnxOspfSpfMaxWait 
         value. If this is configured as zero, there will be no 
         exponential backoff.

         The SPF interval will stay at tmnxOspfSpfMaxWait value until
         there are no more SPF runs scheduled in that interval. After
         a full interval without any SPF runs, the SPF interval will
         drop back to tmnxOspfSpfInitialWait."
    DEFVAL { 1000 }
    ::= { tmnxOspfGeneralEntry 32 }

tmnxOspfLsaGenMaxWait OBJECT-TYPE
    SYNTAX      Unsigned32 (10..600000)
    UNITS       "milliseconds"
    MAX-ACCESS  read-create
    STATUS      current
    DESCRIPTION
        "The value of tmnxOspfLsaGenMaxWait defines the maximum interval
         between two consecutive updates of a self generated LSA due to
         any event. This is a way to manipulate the 'MinLSInterval'."
    DEFVAL { 5000 }
    ::= { tmnxOspfGeneralEntry 33 }

tmnxOspfLsaGenInitialWait OBJECT-TYPE
    SYNTAX      Unsigned32 (10..600000)
    UNITS       "milliseconds"
    MAX-ACCESS  read-create
    STATUS      current
    DESCRIPTION
        "The value of tmnxOspfLsaGenInitialWait defines the initial LSA
         generation delay after an event that causes the LSA generation or
         update."
    DEFVAL { 5000 }
    ::= { tmnxOspfGeneralEntry 34 }

tmnxOspfLsaGenSecondWait OBJECT-TYPE
    SYNTAX      Unsigned32 (10..600000)
    UNITS       "milliseconds"
    MAX-ACCESS  read-create
    STATUS      current
    DESCRIPTION
        "The value of tmnxOspfLsaGenSecondWait defines the hold time
         between the first and second LSA generation.

         Subsequent updates of that LSA will occur at exponentially
         increasing intervals of tmnxOspfLsaGenSecondWait value i.e.,
         if tmnxOspfLsaGenSecondWait is 1000, then the next LS update
         triggered during this interval will be processed after 2000
         msec, and the subsequent one at 4000 msec, etc. until it is
         capped off at tmnxOspfLsaGenMaxWait. If this is configured
         as zero, there will be no exponential backoff.

         The LSA generate interval will stay at tmnxOspfLsaGenMaxWait
         value until there are no more updates of that LSA triggered
         in that interval. After a full interval without any updates
         of that LSA, the LSA generate interval will be reset back to
         tmnxOspfLsaGenInitialWait."
    DEFVAL { 5000 }
    ::= { tmnxOspfGeneralEntry 35 }

tmnxOspfLsaArrivalWait  OBJECT-TYPE
    SYNTAX      Unsigned32 (0..600000)
    UNITS       "milliseconds"
    MAX-ACCESS  read-create
    STATUS      current
    DESCRIPTION
        "The value of tmnxOspfLsaArrivalWait defines the minimum
         interval between two consecutive updates of an LSA received
         from any neighbor. Any LSA update received before that is
         discarded. This is a way to manipulate the 'MinLSArrival'."
    DEFVAL { 1000 }
    ::= { tmnxOspfGeneralEntry 36 }

tmnxOspfTESupport       OBJECT-TYPE
    SYNTAX      TruthValue
    MAX-ACCESS  read-create
    STATUS      current
    DESCRIPTION
        "The value of tmnxOspfTESupport indicates whether or not TEs
         are supported by this instance of OSPF.  When it has a value
         of 'true', TEs are supported."
    DEFVAL { false }
    ::= { tmnxOspfGeneralEntry 37 }

tmnxOspfUnicastImport        OBJECT-TYPE
    SYNTAX      TruthValue
    MAX-ACCESS  read-create
    STATUS      current
    DESCRIPTION
        "The value of tmnxOspfUnicastImport specifies whether OSPF protocol
         will submit routes into the unicast Route Table Manage(RTM).
         
         When tmnxOspfUnicastImport has a value of 'true', the OSPF protocol
         submits routes into the unicast RTM, and when it has a value of 
         'false', it does not."
    DEFVAL { true }
    ::= { tmnxOspfGeneralEntry 38 }

tmnxOspfMulticastImport      OBJECT-TYPE
    SYNTAX      TruthValue
    MAX-ACCESS  read-create
    STATUS      current
    DESCRIPTION
        "The value of tmnxOspfMulticastImport specifies whether OSPF 
         protocol will submit routes into the multicast Reverse Path 
         Forwarding(RPF) Route Table Manage(RTM).
         
         When tmnxOspfMulticastImport has a value of 'true', OSPF protocol 
         submits routes into the multicast RPF RTM and when it has a 
         value of 'false', it does not."
    DEFVAL { false }
    ::= { tmnxOspfGeneralEntry 39 }

tmnxOspfGREnable      OBJECT-TYPE
    SYNTAX      TruthValue
    MAX-ACCESS  read-create
    STATUS      current
    DESCRIPTION
        "The value of tmnxOspfGREnable specifies whether the graceful
         restart is enabled or disabled for this instance of OSPF 
         on the router.
         
         When tmnxOspfGREnable has a value of 'true' graceful
         restart capabilities are enabled.  When it has a value
         of 'false' the graceful restart is disabled."
    DEFVAL { false }
    ::= { tmnxOspfGeneralEntry 40 }

tmnxOspfGRHelperMode      OBJECT-TYPE
    SYNTAX      TruthValue
    MAX-ACCESS  read-create
    STATUS      current
    DESCRIPTION
        "The value of tmnxOspfGRHelperMode specifies whether the 
         graceful restart helper mode is enabled or disabled for this 
         instance of OSPF on the router.
         tmnxOspfGRHelperMode is valid only if the value of 
         tmnxOspfGREnable is 'true'.
         
         When tmnxOspfGRHelperMode has a value of 'true' graceful
         restart helper capabilities are enabled.  When it has a value
         of 'false' the graceful restart helper capabilities are disabled."
    DEFVAL { true }
    ::= { tmnxOspfGeneralEntry 41 }

tmnxOspfRowStatus      OBJECT-TYPE
    SYNTAX      RowStatus
    MAX-ACCESS  read-create
    STATUS      current
    DESCRIPTION
        "The tmnxOspfRowStatus variable is used for creation and deletion 
         of tmnxOspfGeneralTable row entries."
    ::= { tmnxOspfGeneralEntry 42 }

tmnxOspfAsbrDomainId OBJECT-TYPE
    SYNTAX      Integer32 (-1 | 0..31)
    MAX-ACCESS  read-create
    STATUS      current
    DESCRIPTION
        "The value of tmnxOspfAsbrDomainId specifies the domain-id associated
         with this instance of OSPF on the router.
         
         If no value is specified for tmnxOspfAsbrDomainId, it is set to -1."
    DEFVAL { -1 }
    ::= { tmnxOspfGeneralEntry 43 }

tmnxOspfIgnoreDNBit OBJECT-TYPE
    SYNTAX      TruthValue
    MAX-ACCESS  read-create
    STATUS      current
    DESCRIPTION
        "The value of tmnxOspfIgnoreDNBit specifies whether to ignore the
         DN bit for OSPF LSA packets for this instance of OSPF on the router.

         When tmnxOspfIgnoreDNBit has a value of 'true' the DN bit for
         OSPF LSA packets will be ignored. When it has a value of 'false'
         the DN bit will not be ignored for OSPF LSA packets."
    DEFVAL { false }
    ::= { tmnxOspfGeneralEntry 44 }

tmnxOspfSuppressDNBit OBJECT-TYPE
    SYNTAX      TruthValue
    MAX-ACCESS  read-create
    STATUS      current
    DESCRIPTION
        "The value of tmnxOspfSuppressDNBit specifies whether to suppress the
         setting of the DN bit for OSPF LSA packets generated by this instance
         of OSPF on the router.

         When tmnxOspfSuppressDNBit has a value of 'true' the DN bit for
         OSPF LSA packets generated by this instance of the OSPF router 
         will not be set. When it has a value of 'false' this instance of
         the OSPF router will follow the normal proceedure to determine
         whether to set the DN bit."
    DEFVAL { false }
    ::= { tmnxOspfGeneralEntry 45 }

tmnxOspfLdpSyncAdminState     OBJECT-TYPE 
    SYNTAX      Status 
    MAX-ACCESS  read-create 
    STATUS      current 
    DESCRIPTION
        "The value of tmnxOspfLdpSyncAdminState specifies whether the IGP-LDP 
         synchronization feature is enabled or disabled on all interfaces 
         participating in the OSPF routing protocol. 
    
         When the value is set to 'disabled', IGP immediately advertises the 
         actual value of the link cost for all interfaces which have the IGP-LDP 
         synchronization enabled if the currently advertized cost is different. 
         IGP-LDP synchronization for all interfaces is then disabled."
    DEFVAL { enabled }
    ::= { tmnxOspfGeneralEntry 46 } 

tmnxOspfVpnDomainType    OBJECT-TYPE
    SYNTAX      INTEGER {
                    type0000 (0),
                    type0005 (5),
                    type0105 (261),
                    type0205 (517),
                    type8005 (32773)
                }
    MAX-ACCESS  read-create
    STATUS      current
    DESCRIPTION
        "The value of tmnxOspfVpnDomainType specifies type of the extended
         community attribute exchanged using BGP to carry the OSPF VPN 
         Domain ID. This object applies to VPRN instances of OSPF only. An 
         attempt to modify the value of this object will result in an 
         'inconsistentValue' error when the vRtrID index for this row entry 
         is not a VPRN instance.

         When the value is set to 'type0000', vpn-domain functionality is 
         disabled."
    DEFVAL { type0000 }
    ::= { tmnxOspfGeneralEntry 47 }

tmnxOspfVpnDomainId    OBJECT-TYPE
    SYNTAX      OCTET STRING (SIZE (0..6))
    MAX-ACCESS  read-create
    STATUS      current
    DESCRIPTION
        "The value of tmnxOspfVpnDomainId specifies the OSPF VPN Domain.
         This is exchanged using BGP in the extended community attribute
         associated with a prefix. This object applies to VPRN instances
         of OSPF only. An attempt to modify the value of this object will 
         result in an 'inconsistentValue' error when the vRtrID index for 
         this row entry is not a VPRN instance."
    DEFVAL { '000000000000'H }
    ::= { tmnxOspfGeneralEntry 48 }

tmnxOspfVpnTag  OBJECT-TYPE
    SYNTAX      Unsigned32 (0..4294967295)
    MAX-ACCESS  read-create
    STATUS      current
    DESCRIPTION
        "The value of tmnxOspfVpnTag specifies the route tag for an OSPF VPN
         on a PE router. This field is set in the tag field of the OSPF external
         LSAs generated by the PE. This is mainly used to prevent routing loops.
         This object applies to VPRN instances of OSPF only. An attempt to 
         modify the value of this object will result in an 'inconsistentValue' 
         error when the vRtrID index for this row entry is not a VPRN instance."
    DEFVAL { 0 }
    ::= { tmnxOspfGeneralEntry 49 }

tmnxOspfSuperBackBone OBJECT-TYPE
    SYNTAX      TruthValue
    MAX-ACCESS  read-create
    STATUS      current
    DESCRIPTION
        "The value of tmnxOspfSuperBackBone specifies whether CE-PE 
         functionality is required or not. tmnxOspfSuperBackBone indicates the 
         type of the LSA generated as a result of routes redistributed into 
         OSPF.

         When the value is set to 'true' the redistributed routes are injected 
         as summary, external or NSSA LSAs.
         
         When the value is set to 'false' the redistributed routes are injected 
         as either external or NSSA LSAs only."
    DEFVAL { false }
    ::= { tmnxOspfGeneralEntry 50 }

tmnxOspfLdpOverRsvp  OBJECT-TYPE
    SYNTAX      TmnxEnabledDisabled
    MAX-ACCESS  read-create
    STATUS      current
    DESCRIPTION
        "The value of tmnxOspfLdpOverRsvp specifies whether LDP-over-RSVP 
         feature is enabled or disabled for a specific OSPF instance.

         When tmnxOspfLdpOverRsvp is enabled, OSPF will select the endpoint 
         that is closest to the destination for further selection of 
         LDP-over-RSVP tunnels to that endpoint."
    DEFVAL { disabled }
    ::= { tmnxOspfGeneralEntry 51 }

tmnxOspfExportLimit         OBJECT-TYPE
    SYNTAX      Unsigned32
    MAX-ACCESS  read-create
    STATUS      current
    DESCRIPTION
        "The value of tmnxOspfExportLimit specifies the maximum number of 
        routes or prefixes that can be exported into OSPF or OSPF3 from the 
        route table.

        A value of 0 indicates that the export limit for routes or prefixes has
        been disabled."
    DEFVAL { 0 }
    ::= { tmnxOspfGeneralEntry 52 }

tmnxOspfExportLimitLogPercent       OBJECT-TYPE
    SYNTAX      Unsigned32  (0..100)
    UNITS       "percentage"
    MAX-ACCESS  read-create
    STATUS      current
    DESCRIPTION
        "The value of tmnxOspfExportLimitLogPercent specifies the percentage
        of the export-limit, at which a warning log message and SNMP 
        notification would be sent. This would only be a warning and additional 
        routes will be learned up to 100% of tmnxOspfExportLimit.

        A value of 0 indicates that tmnxOspfExportLimitLogPercent is disabled
        and no log message or SNMP notification would be sent."
    DEFVAL { 0 }
    ::= { tmnxOspfGeneralEntry 53 }

tmnxOspfRsvpShortcut         OBJECT-TYPE
    SYNTAX      TruthValue
    MAX-ACCESS  read-create
    STATUS      current
    DESCRIPTION
        "The value of tmnxOspfRsvpShortcut indicates whether RSVP-TE shortcut
         for resolving IGP routes has been enabled or disabled for OSPF.

         When the value of tmnxOspfRsvpShortcut is set to true RSVP-TE shortcut 
         is enabled and when tmnxOspfRsvpShortcut is set to false RSVP-TE shortcut
         is disabled for OSPF."
    DEFVAL { false }     
    ::= { tmnxOspfGeneralEntry 54 }

tmnxOspfAdvertiseTunnelLink         OBJECT-TYPE
    SYNTAX      TruthValue
    MAX-ACCESS  read-create
    STATUS      current
    DESCRIPTION
        "The value of tmnxOspfAdvertiseTunnelLink indicates whether advertisement
         of LSP shortcuts into IGP has been enabled or disabled for OSPF.

         When the value of tmnxOspfAdvertiseTunnelLink is set to true LSP  shortcut 
         advertisement into IGP is enabled and when tmnxOspfAdvertiseTunnelLink is 
         set to false LSP shortcut advertisement into IGP is disabled."
    DEFVAL { false }     
    ::= { tmnxOspfGeneralEntry 55 }

tmnxOspfImportPolicy1 OBJECT-TYPE
    SYNTAX      TNamedItemOrEmpty
    MAX-ACCESS  read-create
    STATUS      current
    DESCRIPTION
        "The value of tmnxOspfImportPolicy1 specifies the name of
         1st import policy to be used to be used for determining which
         routes are exported from  the routing table to OSPF."
    DEFVAL { ''H }   -- the empty string
    ::= { tmnxOspfGeneralEntry 56 }

tmnxOspfImportPolicy2 OBJECT-TYPE
    SYNTAX      TNamedItemOrEmpty
    MAX-ACCESS  read-create
    STATUS      current
    DESCRIPTION
        "The value of tmnxOspfImportPolicy2 specifies the name of 2nd
         import policy to be used to be used for determining which routes
         are imported from OSPF to the routing table."
    DEFVAL { ''H }   -- the empty string
    ::= { tmnxOspfGeneralEntry 57 }

tmnxOspfImportPolicy3 OBJECT-TYPE
    SYNTAX      TNamedItemOrEmpty
    MAX-ACCESS  read-create
    STATUS      current
    DESCRIPTION
        "The value of tmnxOspfImportPolicy3 specifies the name of 3rd
         import policy to be used to be used for determining which routes
         are imported from OSPF to the routing table."
    DEFVAL { ''H }   -- the empty string
    ::= { tmnxOspfGeneralEntry 58 }

tmnxOspfImportPolicy4 OBJECT-TYPE
    SYNTAX      TNamedItemOrEmpty
    MAX-ACCESS  read-create
    STATUS      current
    DESCRIPTION
        "The value of tmnxOspfImportPolicy4 specifies the name of 4rd
         import policy to be used to be used for determining which routes
         are imported from OSPF to the routing table."
    DEFVAL { ''H }   -- the empty string
    ::= { tmnxOspfGeneralEntry 59 }

tmnxOspfImportPolicy5 OBJECT-TYPE
    SYNTAX      TNamedItemOrEmpty
    MAX-ACCESS  read-create
    STATUS      current
    DESCRIPTION
        "The value of tmnxOspfImportPolicy5 specifies the name of 5th
         import policy to be used to be used for determining which routes
         are imported from OSPF to the routing table."
    DEFVAL { ''H }   -- the empty string
    ::= { tmnxOspfGeneralEntry 60 }

tmnxOspfLoopfreeAlternate    OBJECT-TYPE
    SYNTAX      TruthValue
    MAX-ACCESS  read-create
    STATUS      current
    DESCRIPTION
        "The value of tmnxOspfLoopfreeAlternate specifies whether to enable or
         disable IP fast re-route capability for OSPF.

         When the value of tmnxOspfLoopfreeAlternate is set to 'true' IP fast 
         re-route capability for OSPF is enabled and when 
         tmnxOspfLoopfreeAlternate is set to 'false' IP fast re-route capability 
         for OSPF is disabled."
    DEFVAL { false } 
    ::= { tmnxOspfGeneralEntry 61 }

tmnxOspfLsaAccumulate  OBJECT-TYPE
    SYNTAX      Unsigned32 (0..1000)
    UNITS       "milliseconds"
    MAX-ACCESS  read-create
    STATUS      current
    DESCRIPTION
        "The value of tmnxOspfLsaAccumulate defines the accumulation delay for
         multiple LSA's, so OSPF messages can be sent as efficiently as
         possible.
         
         Shorting this delay can speed up the advertisement of LSA's to OSPF
         neighbors but may increase the number of OSPF messages sent."
    DEFVAL { 1000 }
    ::= { tmnxOspfGeneralEntry 62 }

tmnxOspfRedistDelay  OBJECT-TYPE
    SYNTAX      Unsigned32 (0..1000)
    UNITS       "milliseconds"
    MAX-ACCESS  read-create
    STATUS      current
    DESCRIPTION
        "The value of tmnxOspfRedistDelay defines the internal OSPF hold down
         timer for external routes being redistributed into OSPF.
         
         Shorting this delay can speed up the advertisement of external routes
         into OSPF but can result in additional OSPF messages if that source 
         route is not yet stable."
    DEFVAL { 1000 }
    ::= { tmnxOspfGeneralEntry 63 }

tmnxOspfIncrSpfWait  OBJECT-TYPE
    SYNTAX      Unsigned32 (0..1000)
    UNITS       "milliseconds"
    MAX-ACCESS  read-create
    STATUS      current
    DESCRIPTION
        "The value of tmnxOspfIncrSpfWait defines the internal OSPF delay
         before an incremental SPF calculation is performed."
    DEFVAL { 1000 }
    ::= { tmnxOspfGeneralEntry 64 }

tmnxOspfOverloadInclExt2 OBJECT-TYPE
    SYNTAX      TruthValue
    MAX-ACCESS  read-create
    STATUS      current
    DESCRIPTION
        "The value of tmnxOspfOverloadInclExt2 specifies if the OSPF external
         prefixes with metric-type 2, should be advertised with a maximum
         metric value when the system goes into overload state for any reason.
         If the value is 'true', the system uses the maximum metric value."
    DEFVAL { false }
    ::= { tmnxOspfGeneralEntry 65 }

    
-- 
--  Augmentation of the tmnxOspfGeneralTable.
--  Use of AUGMENTS clause implies a one-to-one dependent relationship between
--  the base table, tmnxOspfGeneralTable, and the augmenting table, 
--  tmnxOspfStatusTable.
--  This in effect extends the tmnxOspfGeneralTable with additional columns.  
--  Creation (or deletion) of a row in the tmnxOspfGeneralTable results in 
--  the same fate for the row in the tmnxOspfStatusTable.
-- 
tmnxOspfStatusTable OBJECT-TYPE
    SYNTAX      SEQUENCE OF TmnxOspfStatusEntry
    MAX-ACCESS  not-accessible
    STATUS      current
    DESCRIPTION
        "The tmnxOspfStatusTable provides an extension of the 
         tmnxOspfGeneralTable for OSPF process statuses."
    ::= { tmnxOspfObjects 3 }

tmnxOspfStatusEntry OBJECT-TYPE
    SYNTAX      TmnxOspfStatusEntry
    MAX-ACCESS  not-accessible
    STATUS      current
    DESCRIPTION
        "Each row entry in the tmnxOspfStatusTable represents additional 
         columns for status objects for an OSPF instance."
    AUGMENTS { tmnxOspfGeneralEntry }
   ::= { tmnxOspfStatusTable 1 }

TmnxOspfStatusEntry ::=
    SEQUENCE {
        tmnxOspfAreaBdrRtrStatus        TruthValue, 
        tmnxOspfBackBoneRouter          TruthValue,
        tmnxOspfStubRouterSupport       TruthValue,
        tmnxOspfAsScopeLsaCount         Gauge32,
        tmnxOspfAsScopeLsaCksumSum      Integer32,
        tmnxOspfAsScopeUnkLsaCount      Gauge32,
        tmnxOspfAsScopeUnkLsaCksumSum   Integer32,
        tmnxOspfExternLsaCount          Gauge32, 
        tmnxOspfExternLsaCksumSum       Integer32,
        tmnxOspfOpaqueLsaSupport        TruthValue,
        tmnxOspfRestartStatus           INTEGER,  
        tmnxOspfRestartAge              TmnxOspfUpToRefreshIntervalTc, 
        tmnxOspfRestartExitRc           INTEGER,  
        tmnxOspfDiscontinuityTime       TimeStamp,
        tmnxOspfLastEnabledTime         TimeStamp,
        tmnxOspfLastOvrflwEnteredTime   TimeStamp,
        tmnxOspfLastOverflowExitTime    TimeStamp,
        tmnxOspfInOverflowState         TruthValue,
        tmnxOspfOverloadOperState       INTEGER,
        tmnxOspfOverloadRemInterval     TimeInterval,
        tmnxOspfLastOverloadEntrdTime   TimeStamp,
        tmnxOspfLastOverloadExitTime    TimeStamp,
        tmnxOspfLastOverloadEnterCode   INTEGER,
        tmnxOspfLastOverloadExitCode    INTEGER,
        tmnxOspfLastExtSpfRunTime       TimeStamp,
        tmnxOspfLastFullSpfRunTime      TimeStamp,
        tmnxOspfLastFullSpfInterval     TimeInterval,
        tmnxOspfMaxSpfRunInterval       TimeInterval,
        tmnxOspfMinSpfRunInterval       TimeInterval,
        tmnxOspfAvgSpfRunInterval       TimeInterval,
        tmnxOspfExtSpfRunInterval       TimeInterval,
        tmnxOspfRoutesSubmitted         Gauge32,
        tmnxOspfOperRouterId            TmnxOspfRouterIdTc,
        tmnxOspfTotalExportedRoutes     Gauge32,
        tmnxOspfLastLfaSpfRunTime       TimeStamp
    }

tmnxOspfAreaBdrRtrStatus OBJECT-TYPE 
    SYNTAX      TruthValue 
    MAX-ACCESS  read-only 
    STATUS      current 
    DESCRIPTION 
        "The value of tmnxOspfAreaBdrRtrStatus indicates whether this router
         is an area border router." 
    REFERENCE 
        "OSPF Version 2, Section 3 Splitting the AS into Areas" 
    ::= { tmnxOspfStatusEntry 1 } 
 
tmnxOspfBackBoneRouter OBJECT-TYPE
    SYNTAX      TruthValue
    MAX-ACCESS  read-only
    STATUS      current
    DESCRIPTION
        "The value of tmnxOspfBackBoneRouter indicates whether or not
         this router is configured as an OSPF back bone router."
    ::= { tmnxOspfStatusEntry 2 }

tmnxOspfStubRouterSupport OBJECT-TYPE 
    SYNTAX       TruthValue 
    MAX-ACCESS   read-only 
    STATUS       current 
    DESCRIPTION 
        "The value of tmnxOspfStubRouterSupport indicates the router's 
         support for stub router functionality." 
    REFERENCE 
        "OSPF Stub Router Advertisement" 
    ::= { tmnxOspfStatusEntry 3 }  
      
tmnxOspfAsScopeLsaCount OBJECT-TYPE 
    SYNTAX      Gauge32 
    MAX-ACCESS  read-only 
    STATUS      current 
    DESCRIPTION 
        "The value of tmnxOspfAsScopeLsaCount specifies the number of 
         AS-Scope (e.g. AS-External) link state advertisements in the 
         link-state database." 
    ::= { tmnxOspfStatusEntry 4 } 
 
tmnxOspfAsScopeLsaCksumSum OBJECT-TYPE 
    SYNTAX      Integer32 
    MAX-ACCESS  read-only 
    STATUS      current 
    DESCRIPTION 
        "The value of tmnxOspfAsScopeLsaCksumSum indicates the 32-bit 
         unsigned sum of the LS checksums of the AS-scoped link-state 
         advertisements contained in the link-state database.  This sum 
         can be used to determine if there has been a change in a router's 
         link-state database, and to compare the link-state database of two 
         routers." 
    ::= { tmnxOspfStatusEntry 5 } 

tmnxOspfAsScopeUnkLsaCount OBJECT-TYPE 
    SYNTAX      Gauge32 
    MAX-ACCESS  read-only 
    STATUS      current 
    DESCRIPTION 
        "The value of tmnxOspfAsScopeUnkLsaCount specifies the number of 
         unknown AS-Scope (e.g. AS-External) link-state advertisements in 
         the link-state database." 
    ::= { tmnxOspfStatusEntry 6 } 
 
tmnxOspfAsScopeUnkLsaCksumSum OBJECT-TYPE 
    SYNTAX      Integer32 
    MAX-ACCESS  read-only 
    STATUS      current 
    DESCRIPTION 
        "The value of tmnxOspfAsScopeUnkLsaCksumSum indicates the 32-bit 
         unsigned sum of the LS checksums of the unknown AS-scoped link-state 
         advertisements contained in the link-state database. This sum can 
         be used to determine if there has been a change in a router's 
         link-state database, and to compare the link-state database of two 
         routers." 
    ::= { tmnxOspfStatusEntry 7 } 

tmnxOspfExternLsaCount OBJECT-TYPE 
    SYNTAX      Gauge32 
    MAX-ACCESS  read-only 
    STATUS      current 
    DESCRIPTION 
        "The value of tmnxOspfExternLsaCount indicates the number of 
         External LSAs (LS type 0x4005) in the link-state database" 
    ::= { tmnxOspfStatusEntry 8 } 
 
tmnxOspfExternLsaCksumSum OBJECT-TYPE 
    SYNTAX       Integer32 
    MAX-ACCESS   read-only 
    STATUS       current 
    DESCRIPTION 
         "The value of tmnxOspfExternLsaCksumSum indicates the 32-bit 
          unsigned sum of the LS checksums of the external link-state 
          advertisements contained in the link-state database. This sum 
          can be used to determine if there has been a change in a router's 
          link state  database, and to compare the link-state database of 
          two routers." 
    ::= { tmnxOspfStatusEntry 9 } 

tmnxOspfOpaqueLsaSupport  OBJECT-TYPE 
    SYNTAX       TruthValue 
    MAX-ACCESS   read-only 
    STATUS       current 
    DESCRIPTION 
        "The value of tmnxOspfOpaqueLsaSupport indicates the router's 
         support for Opaque LSA types. 
  
         This object is valid only when tmnxOspfVersion is 'version2'." 
    REFERENCE 
        "The OSPF Opaque LSA Option" 
    ::= { tmnxOspfStatusEntry 10 } 
     
tmnxOspfRestartStatus OBJECT-TYPE  
    SYNTAX      INTEGER { 
                    notRestarting (1),  
                    plannedRestart (2),  
                    unplannedRestart (3)  
                }  
    MAX-ACCESS  read-only  
    STATUS      current  
    DESCRIPTION  
        "The value of tmnxOspfRestartStatus indicates the current status of
         OSPF graceful restart capability." 
    ::= { tmnxOspfStatusEntry 11 }  
        
tmnxOspfRestartAge OBJECT-TYPE  
    SYNTAX      TmnxOspfUpToRefreshIntervalTc 
    UNITS       "seconds"  
    MAX-ACCESS  read-only  
    STATUS      current  
    DESCRIPTION  
        "The value of tmnxOspfRestartAge indicates the remaining time in 
         the current OSPF graceful restart interval." 
    ::= { tmnxOspfStatusEntry 12 }  
        
tmnxOspfRestartExitRc OBJECT-TYPE  
    SYNTAX      INTEGER { 
                    none (1),  
                    inProgress (2),  
                    completed (3), 
                    timedOut (4), 
                    topologyChanged (5) 
                }  
    MAX-ACCESS  read-only  
    STATUS      current  
    DESCRIPTION  
        "The value of tmnxOspfRestartExitRc indicates the outcome of 
         the last attempt at a Graceful restart. 
     
              none (1)              no restart has yet been attempted. 
              inProgress (2)        a restart attempt is currently underway. 
              completed (3)         the last restart completed successfully. 
              timedOut (4)          the last restart timed out. 
              topologyChanged (5)   the last restart was aborted due to 
                                    a topology change."  
    ::= { tmnxOspfStatusEntry 13 } 
 
tmnxOspfDiscontinuityTime OBJECT-TYPE 
    SYNTAX      TimeStamp 
    MAX-ACCESS  read-only 
    STATUS      current 
    DESCRIPTION 
        "The value of sysUpTime on the most recent occasion at which any 
         one of this MIB's counters suffered a discontinuity. 
     
         If no such discontinuities have occurred since the last 
         reinitialization of the local management subsystem, then this 
         object contains a zero value." 
    ::= { tmnxOspfStatusEntry 14 } 
     
tmnxOspfLastEnabledTime OBJECT-TYPE
    SYNTAX      TimeStamp
    MAX-ACCESS  read-only
    STATUS      current
    DESCRIPTION
        "The value of tmnxOspfLastEnabledTime indicates the value of
         sysUpTime when tmnxOspfAdminState was last set to 'enabled'.
         When tmnxOspfAdminState is set to 'disabled', the OSPF counters
         are stopped; when tmnxOspfAdminState is reset to 'enabled', the
         counters are reset to zero."
    ::= { tmnxOspfStatusEntry 15 }

tmnxOspfLastOvrflwEnteredTime OBJECT-TYPE
    SYNTAX      TimeStamp
    MAX-ACCESS  read-only
    STATUS      current
    DESCRIPTION
        "The value of tmnxOspfLastOvrflwEnteredTime indicates
         the value of sysUpTime the last time we entered overflow state.
         This overflow state occurs when the number of non-default
         AS-external-LSAs entries exceed the link-state database
         capability."
    ::= { tmnxOspfStatusEntry 16 }

tmnxOspfLastOverflowExitTime OBJECT-TYPE
    SYNTAX      TimeStamp
    MAX-ACCESS  read-only
    STATUS      current
    DESCRIPTION
        "The value of tmnxOspfLastOverflowExitTime indicates the
         value of sysUpTime the last time we exited overflow state.
         This overflow state occurs when the number of
         non-default AS-external-LSAs entries exceed the link-state
         database capability."
    ::= { tmnxOspfStatusEntry 17 }

tmnxOspfInOverflowState OBJECT-TYPE
    SYNTAX      TruthValue
    MAX-ACCESS  read-only
    STATUS      current
    DESCRIPTION
        "The value of tmnxOspfInOverflowState indicates the current
         overflow state (true/False). This overflow state
         occurs when the number of non-default AS-external-LSAs entries
         exceed the link-state database capability."
    ::= { tmnxOspfStatusEntry 18 }

tmnxOspfOverloadOperState OBJECT-TYPE
    SYNTAX      INTEGER {
                    overload(1),
                    noOverload(2)
                }
    MAX-ACCESS  read-only
    STATUS      current
    DESCRIPTION
        "The value of tmnxOspfOverloadOperState indicates whether
         or not the OSPF application is presently in overload
         state or not."
    ::= { tmnxOspfStatusEntry 19 }

tmnxOspfOverloadRemInterval OBJECT-TYPE
    SYNTAX      TimeInterval (0..65535)
    MAX-ACCESS  read-only
    STATUS      current
    DESCRIPTION
        "The value of tmnxOspfOverloadRemInterval indicates the time
         for which the system will be in overload state if OSPF is in
         overload state.

         The value of 0 implies that the system is indefinitely in
         overload state."
    ::= { tmnxOspfStatusEntry 20 }

tmnxOspfLastOverloadEntrdTime OBJECT-TYPE
    SYNTAX      TimeStamp
    MAX-ACCESS  read-only
    STATUS      current
    DESCRIPTION
        "The value of tmnxOspfLastOverloadEntrdTime indicates the
         time at which the system last went into overload state."
    ::= { tmnxOspfStatusEntry 21 }

tmnxOspfLastOverloadExitTime OBJECT-TYPE
    SYNTAX      TimeStamp
    MAX-ACCESS  read-only
    STATUS      current
    DESCRIPTION
        "The value of tmnxOspfLastOverloadExitTime indicates the
         time at which the system last came out of overload state."
    ::= { tmnxOspfStatusEntry 22 }

tmnxOspfLastOverloadEnterCode OBJECT-TYPE
    SYNTAX      INTEGER {
                    none (1),
                    spfFailed (2),
                    bootOverload (3),
                    manualOverload (4),
                    singleSfm (5)
                }
    MAX-ACCESS  read-only
    STATUS      current
    DESCRIPTION
        "The value of tmnxOspfLastOverloadEnterCode indicates the
         condition which caused OSPF to get into overload."
    ::= { tmnxOspfStatusEntry 23 }

tmnxOspfLastOverloadExitCode OBJECT-TYPE
    SYNTAX      INTEGER {
                    none (1),
                    bgpSigRecv (2),
                    timerExpired (3),
                    manualExit (4),
                    singleSfm (5)
                }
    MAX-ACCESS  read-only
    STATUS      current
    DESCRIPTION
        "The value of tmnxOspfLastOverloadExitCode indicates
         the reason why OSPF came out of overload state the last
         time, since reset."
    ::= { tmnxOspfStatusEntry 24 }

tmnxOspfLastExtSpfRunTime OBJECT-TYPE
    SYNTAX      TimeStamp
    MAX-ACCESS  read-only
    STATUS      current
    DESCRIPTION
        "The value of tmnxOspfLastExtSpfRunTime indicates the value of
         sysUpTime when the external OSPF Dijkstra (SPF) was last run."
    ::= { tmnxOspfStatusEntry 25 }

tmnxOspfLastFullSpfRunTime OBJECT-TYPE
    SYNTAX      TimeStamp
    MAX-ACCESS  read-only
    STATUS      current
    DESCRIPTION
        "The value of tmnxOspfLastFullSpfRunTime indicates the
         time at which the system last performed a full Dijkstra (SPF) run."
    ::= { tmnxOspfStatusEntry 26 }

tmnxOspfLastFullSpfInterval OBJECT-TYPE
    SYNTAX      TimeInterval
    MAX-ACCESS  read-only
    STATUS      current
    DESCRIPTION
        "The value of tmnxOspfLastFullSpfInterval indicates the time,
         in hundredths of seconds, used to perform the most recent
         total SPF calculation."
    ::= { tmnxOspfStatusEntry 27 }

tmnxOspfMaxSpfRunInterval OBJECT-TYPE
    SYNTAX      TimeInterval
    MAX-ACCESS  read-only
    STATUS      current
    DESCRIPTION
        "The value of tmnxOspfMaxSpfRunInterval indicates the maximum
         time, in hundredths of seconds, used to perform a total
         SPF calculation."
    ::= { tmnxOspfStatusEntry 28 }

tmnxOspfMinSpfRunInterval OBJECT-TYPE
    SYNTAX      TimeInterval
    MAX-ACCESS  read-only
    STATUS      current
    DESCRIPTION
        "The value of tmnxOspfMinSpfRunInterval indicates the minimum
         time, in hundredths of seconds, used to perform a total
         SPF calculation."
    ::= { tmnxOspfStatusEntry 29 }

tmnxOspfAvgSpfRunInterval OBJECT-TYPE
    SYNTAX      TimeInterval
    MAX-ACCESS  read-only
    STATUS      current
    DESCRIPTION
        "The value of tmnxOspfAvgSpfRunInterval indicates the average
         time, in hundredths of seconds, of all the total SPF
         calculations performed by this OSPF router."
    ::= { tmnxOspfStatusEntry 30 }

tmnxOspfExtSpfRunInterval OBJECT-TYPE
    SYNTAX      TimeInterval
    MAX-ACCESS  read-only
    STATUS      current
    DESCRIPTION
        "The value of tmnxOspfExtSpfRunInterval indicates the time,
         in hundredths of seconds, used to perform the most recent
         total external (not incremental) SPF calculation."
    ::= { tmnxOspfStatusEntry 31 }

tmnxOspfRoutesSubmitted     OBJECT-TYPE
    SYNTAX      Gauge32
    MAX-ACCESS  read-only
    STATUS      current
    DESCRIPTION
        "The value of tmnxOspfRoutesSubmitted indicates the number
         of routes submitted to the Route Table Manager (RTM) by this 
         instance of OSPF."
    ::= { tmnxOspfStatusEntry 32 }

tmnxOspfOperRouterId OBJECT-TYPE
    SYNTAX      TmnxOspfRouterIdTc
    MAX-ACCESS  read-only
    STATUS      current
    DESCRIPTION
        "The value of tmnxOspfOperRouterId specifies the 32-bit integer
         used to uniquely identify the router in the Autonomous System. 
         The default OSPF instance will use the value specified by 
         tmnxOspfRouterId or the one derived from the IP layer.  For 
         the non-default instances of OSPF, this is the same value as 
         tmnxOspfRouterId, which must be specified before the OSPF 
         instance can become operational."
    ::= { tmnxOspfStatusEntry 33 }

tmnxOspfTotalExportedRoutes         OBJECT-TYPE
    SYNTAX      Gauge32
    MAX-ACCESS  read-only
    STATUS      current
    DESCRIPTION
        "The value of tmnxOspfTotalExportedRoutes indicates the total number
         of routes exported into OSPF from the route table manager when an 
         export policy is configured.

         Value of tmnxOspfTotalExportedRoutes would be 0 when no export policy
         is configured."
    ::= { tmnxOspfStatusEntry 34 }

tmnxOspfLastLfaSpfRunTime OBJECT-TYPE
    SYNTAX      TimeStamp
    MAX-ACCESS  read-only
    STATUS      current
    DESCRIPTION
        "The value of tmnxOspfLastLfaSpfRunTime indicates the
         time at which the system last performed a Dijkstra (LFA SPF) run."
    ::= { tmnxOspfStatusEntry 35 }

-- 
--  Augmentation of the tmnxOspfGeneralTable.
--  Use of AUGMENTS clause implies a one-to-one dependent relationship between
--  the base table, tmnxOspfGeneralTable, and the augmenting table, 
--  tmnxOspfStatisticsTable.
--  This in effect extends the tmnxOspfGeneralTable with additional columns.  
--  Creation (or deletion) of a row in the tmnxOspfGeneralTable results in 
--  the same fate for the row in the tmnxOspfStatisticsTable.
-- 
tmnxOspfStatisticsTable OBJECT-TYPE
    SYNTAX      SEQUENCE OF TmnxOspfStatisticsEntry
    MAX-ACCESS  not-accessible
    STATUS      current
    DESCRIPTION
        "The tmnxOspfStatisticsTable provides an extension of the 
         tmnxOspfGeneralTable for statistics for an OSPF instance."
    ::= { tmnxOspfObjects 4 }

tmnxOspfStatisticsEntry OBJECT-TYPE
    SYNTAX      TmnxOspfStatisticsEntry
    MAX-ACCESS  not-accessible
    STATUS      current
    DESCRIPTION
        "Each row entry in the tmnxOspfStatisticsTable represents additional 
         columns for statistics for an OSPF instance."
    AUGMENTS { tmnxOspfGeneralEntry }
   ::= { tmnxOspfStatisticsTable 1 }

TmnxOspfStatisticsEntry ::=
    SEQUENCE {
        tmnxOspfOriginateNewLsas        Counter32, 
        tmnxOspfRxNewLsas               Counter32, 
        tmnxOspfFullSpfRuns             Counter32,
        tmnxOspfExtSpfRuns              Counter32,
        tmnxOspfIncremntlInterSpfRuns   Counter32,
        tmnxOspfIncrementalExtSpfRuns   Counter32,
        tmnxOspfSpfAttemptsFailed       Counter32,
        tmnxOspfNumTimesInOverload      Counter32,
        tmnxOspfNumTimesInOverflow      Counter32,
        tmnxOspfRoutesAddsFailed        Counter32,
        tmnxOspfRoutesDelsFailed        Counter32,
        tmnxOspfRoutesModsFailed        Counter32,
        tmnxOspfAreaEntries             Gauge32,
        tmnxOspfAreaLsaCountEntries     Gauge32,        
        tmnxOspfAsLsdbEntries           Gauge32,
        tmnxOspfAreaLsdbEntries         Gauge32,
        tmnxOspfLinkLsdbEntries         Gauge32,
        tmnxOspfHostEntries             Gauge32,
        tmnxOspfIfEntries               Gauge32,
        tmnxOspfVirtIfEntries           Gauge32,
        tmnxOspfNbrEntries              Gauge32,
        tmnxOspfCfgNbrEntries           Gauge32,
        tmnxOspfVirtNbrEntries          Gauge32,
        tmnxOspfAreaAggrEntries         Gauge32,
        tmnxOspfIfMD5KeyEntries         Gauge32,
        tmnxOspfVirtIfMD5KeyEntries     Gauge32,
        tmnxOspfCSPFRequests            Counter32,
        tmnxOspfCSPFDroppedRequests     Counter32,
        tmnxOspfCSPFPathsFound          Counter32,
        tmnxOspfCSPFPathsNotFound       Counter32,
        tmnxOspfShamIfEntries           Gauge32,
        tmnxOspfShamNbrEntries          Gauge32,
        tmnxOspfShamIfMD5KeyEntries     Gauge32,
        tmnxOspfLfaSpfRuns              Counter32
    }

tmnxOspfOriginateNewLsas OBJECT-TYPE 
    SYNTAX      Counter32 
    MAX-ACCESS  read-only 
    STATUS      current 
    DESCRIPTION 
        "The value of tmnxOspfOriginateNewLsas indicates the number of  
         new link-state advertisements that have been originated.  
         This number is incremented each time the router originates a new 
         LSA." 
    ::= { tmnxOspfStatisticsEntry 2 } 
 
tmnxOspfRxNewLsas OBJECT-TYPE 
    SYNTAX      Counter32 
    MAX-ACCESS  read-only 
    STATUS      current 
    DESCRIPTION 
        "The value of tmnxOspfRxNewLsas indicates the number of link-state
         advertisements received determined to be new instantiations. 
         This number does not include newer instantiations 
         of self-originated link-state advertisements." 
    ::= { tmnxOspfStatisticsEntry 3 } 
 
tmnxOspfFullSpfRuns OBJECT-TYPE
    SYNTAX      Counter32
    MAX-ACCESS  read-only
    STATUS      current
    DESCRIPTION
        "The value of tmnxOspfFullSpfRuns indicates the total number of
         times that complete SPF has been run on the router since OSPF
         was last enabled."
    ::= { tmnxOspfStatisticsEntry 5 }
                                 
tmnxOspfExtSpfRuns OBJECT-TYPE
    SYNTAX      Counter32
    MAX-ACCESS  read-only
    STATUS      current
    DESCRIPTION
        "The value of tmnxOspfExtSpfRuns indicates the total number of
         times that only the External portion of the SPF has been run
         since OSPF was last enabled."
    ::= { tmnxOspfStatisticsEntry 6 }

tmnxOspfIncremntlInterSpfRuns OBJECT-TYPE
    SYNTAX      Counter32
    MAX-ACCESS  read-only
    STATUS      current
    DESCRIPTION
        "The value of tmnxOspfIncremntlInterSpfRuns indicates the
         total number of incremental SPF runs triggered by new or
         updated inter-area prefix or inter-area router LSAs."
    ::= { tmnxOspfStatisticsEntry 7 }

tmnxOspfIncrementalExtSpfRuns OBJECT-TYPE
    SYNTAX      Counter32
    MAX-ACCESS  read-only
    STATUS      current
    DESCRIPTION
        "The value of tmnxOspfIncrementalExtSpfRuns indicates the total
         number of incremental SPF runs triggered by new or updated external
         LSAs."
    ::= { tmnxOspfStatisticsEntry 8 }

tmnxOspfSpfAttemptsFailed OBJECT-TYPE
    SYNTAX      Counter32
    MAX-ACCESS  read-only
    STATUS      current
    DESCRIPTION
        "The value of tmnxOspfSpfAttemptsFailed indicates the number
         of times an attempt to run SPF has failed because SPF runs
         have been stopped as a result of insufficient memory resources."
    ::= { tmnxOspfStatisticsEntry 9 }

tmnxOspfNumTimesInOverload OBJECT-TYPE
    SYNTAX      Counter32
    MAX-ACCESS  read-only
    STATUS      current
    DESCRIPTION
        "The value of tmnxOspfNumTimesInOverload indicates the count
         of the number of times the system was overloaded."
    ::= { tmnxOspfStatisticsEntry 10 }

tmnxOspfNumTimesInOverflow OBJECT-TYPE
    SYNTAX      Counter32
    MAX-ACCESS  read-only
    STATUS      current
    DESCRIPTION
        "The value of tmnxOspfNumTimesInOverflow indicates the count
         of the number of times the system was in the overflow state."
    ::= { tmnxOspfStatisticsEntry 11 }

tmnxOspfRoutesAddsFailed    OBJECT-TYPE
    SYNTAX      Counter32
    MAX-ACCESS  read-only
    STATUS      current
    DESCRIPTION
        "The value of tmnxOspfRoutesAddsFailed indicates the number of
         times an attempt to add a route to the Route Table Manager (RTM)
         failed for this OSPF instance."
    ::= { tmnxOspfStatisticsEntry 12 }

tmnxOspfRoutesDelsFailed    OBJECT-TYPE
    SYNTAX      Counter32
    MAX-ACCESS  read-only
    STATUS      current
    DESCRIPTION
        "The value of tmnxOspfRoutesDelsFailed indicates the number of
         times an attempt to delete a route from the Route Table Manager
         (RTM) failed for this instance of OSPF."
    ::= { tmnxOspfStatisticsEntry 13 }

tmnxOspfRoutesModsFailed    OBJECT-TYPE
    SYNTAX      Counter32
    MAX-ACCESS  read-only
    STATUS      current
    DESCRIPTION
        "The value of tmnxOspfRoutesModsFailed indicates the number of
         times an attempt to modify a route in the Route Table Manager (RTM)
         failed for this instance of OSPF."
    ::= { tmnxOspfStatisticsEntry 14 }
 
tmnxOspfAreaEntries     OBJECT-TYPE
    SYNTAX      Gauge32
    MAX-ACCESS  read-only
    STATUS      current
    DESCRIPTION
        "The value of tmnxOspfAreaEntries indicates the number of row
         entries in the tmnxOspfAreaTable."
    ::= { tmnxOspfStatisticsEntry 15 }

tmnxOspfAreaLsaCountEntries     OBJECT-TYPE
    SYNTAX      Gauge32
    MAX-ACCESS  read-only
    STATUS      current
    DESCRIPTION
        "The value of tmnxOspfAreaLsaCountEntries indicates the number of row
         entries in the tmnxOspfAreaLsaCountTable."
    ::= { tmnxOspfStatisticsEntry 16 }

tmnxOspfAsLsdbEntries     OBJECT-TYPE
    SYNTAX      Gauge32
    MAX-ACCESS  read-only
    STATUS      current
    DESCRIPTION
        "The value of tmnxOspfAsLsdbEntries indicates the number of row
         entries in the tmnxOspfAsLsdbTable."
    ::= { tmnxOspfStatisticsEntry 17 }

tmnxOspfAreaLsdbEntries     OBJECT-TYPE
    SYNTAX      Gauge32
    MAX-ACCESS  read-only
    STATUS      current
    DESCRIPTION
        "The value of tmnxOspfAreaLsdbEntries indicates the number of row
         entries in the tmnxOspfAreaLsdbTable."
    ::= { tmnxOspfStatisticsEntry 18 }

tmnxOspfLinkLsdbEntries     OBJECT-TYPE
    SYNTAX      Gauge32
    MAX-ACCESS  read-only
    STATUS      current
    DESCRIPTION
        "The value of tmnxOspfLinkLsdbEntries indicates the number of row
         entries in the tmnxOspfNgLinkLsdbTable."
    ::= { tmnxOspfStatisticsEntry 19 }

tmnxOspfHostEntries     OBJECT-TYPE
    SYNTAX      Gauge32
    MAX-ACCESS  read-only
    STATUS      current
    DESCRIPTION
        "The value of tmnxOspfHostEntries indicates the number of row
         entries in the tmnxOspfHostTable."
    ::= { tmnxOspfStatisticsEntry 20 }

tmnxOspfIfEntries     OBJECT-TYPE
    SYNTAX      Gauge32
    MAX-ACCESS  read-only
    STATUS      current
    DESCRIPTION
        "The value of tmnxOspfIfEntries indicates the number of row
         entries in the tmnxOspfNgIfTable."
    ::= { tmnxOspfStatisticsEntry 21 }

tmnxOspfVirtIfEntries     OBJECT-TYPE
    SYNTAX      Gauge32
    MAX-ACCESS  read-only
    STATUS      current
    DESCRIPTION
        "The value of tmnxOspfVirtIfEntries indicates the number of row
         entries in the tmnxOspfVirtIfTable."
    ::= { tmnxOspfStatisticsEntry 22 }

tmnxOspfNbrEntries     OBJECT-TYPE
    SYNTAX      Gauge32
    MAX-ACCESS  read-only
    STATUS      current
    DESCRIPTION
        "The value of tmnxOspfNbrEntries indicates the number of row
         entries in the tmnxOspfNgNbrTable."
    ::= { tmnxOspfStatisticsEntry 23 }

tmnxOspfCfgNbrEntries     OBJECT-TYPE
    SYNTAX      Gauge32
    MAX-ACCESS  read-only
    STATUS      current
    DESCRIPTION
        "The value of tmnxOspfCfgNbrEntries indicates the number of row
         entries in the tmnxOspfCfgNbrTable."
    ::= { tmnxOspfStatisticsEntry 24 }

tmnxOspfVirtNbrEntries     OBJECT-TYPE
    SYNTAX      Gauge32
    MAX-ACCESS  read-only
    STATUS      current
    DESCRIPTION
        "The value of tmnxOspfVirtNbrEntries indicates the number of row
         entries in the tmnxOspfVirtNbrTable."
    ::= { tmnxOspfStatisticsEntry 25 }

tmnxOspfAreaAggrEntries     OBJECT-TYPE
    SYNTAX      Gauge32
    MAX-ACCESS  read-only
    STATUS      current
    DESCRIPTION
        "The value of tmnxOspfAreaAggrEntries indicates the number of row
         entries in the tmnxOspfAreaAggrTable."
    ::= { tmnxOspfStatisticsEntry 26 }

tmnxOspfIfMD5KeyEntries     OBJECT-TYPE
    SYNTAX      Gauge32
    MAX-ACCESS  read-only
    STATUS      current
    DESCRIPTION
        "The value of tmnxOspfIfMD5KeyEntries indicates the number of row
         entries in the tmnxOspfNgIfMD5KeyTable."
    ::= { tmnxOspfStatisticsEntry 27 }

tmnxOspfVirtIfMD5KeyEntries     OBJECT-TYPE
    SYNTAX      Gauge32
    MAX-ACCESS  read-only
    STATUS      current
    DESCRIPTION
        "The value of tmnxOspfVirtIfMD5KeyEntries indicates the number of row
         entries in the tmnxOspfVirtIfMD5KeyTable."
    ::= { tmnxOspfStatisticsEntry 28 }

tmnxOspfCSPFRequests     OBJECT-TYPE
    SYNTAX      Counter32
    MAX-ACCESS  read-only
    STATUS      current
    DESCRIPTION
        "The value of tmnxOspfCSPFRequests indicates the 
         number of CSPF requests made to the OSPF protocol."
    ::= { tmnxOspfStatisticsEntry 29 }

tmnxOspfCSPFDroppedRequests     OBJECT-TYPE
    SYNTAX      Counter32
    MAX-ACCESS  read-only
    STATUS      current
    DESCRIPTION
        "The value of tmnxOspfCSPFDroppedRequests indicates the 
         number of dropped CSPF requests made by the OSPF protocol."
    ::= { tmnxOspfStatisticsEntry 30 }

tmnxOspfCSPFPathsFound            OBJECT-TYPE
    SYNTAX      Counter32
    MAX-ACCESS  read-only
    STATUS      current
    DESCRIPTION
        "The value of tmnxOspfCSPFPathsFound indicates the number of
         of paths found for the requests made to OSPF protocol."
    ::= { tmnxOspfStatisticsEntry 31 }

tmnxOspfCSPFPathsNotFound       OBJECT-TYPE
    SYNTAX      Counter32
    MAX-ACCESS  read-only
    STATUS      current
    DESCRIPTION
        "The value of tmnxOspfCSPFPathsNotFound indicates the number of
         of paths not found for the requests made to OSPF protocol."
    ::= { tmnxOspfStatisticsEntry 32 }

tmnxOspfShamIfEntries     OBJECT-TYPE
    SYNTAX      Gauge32
    MAX-ACCESS  read-only
    STATUS      current
    DESCRIPTION
        "The value of tmnxOspfShamIfEntries indicates the number of row
         entries in the tmnxOspfShamIfTable."
    ::= { tmnxOspfStatisticsEntry 33 }

tmnxOspfShamNbrEntries     OBJECT-TYPE
    SYNTAX      Gauge32
    MAX-ACCESS  read-only
    STATUS      current
    DESCRIPTION
        "The value of tmnxOspfShamNbrEntries indicates the number of row
         entries in the tmnxOspfShamNbrTable."
    ::= { tmnxOspfStatisticsEntry 34 }

tmnxOspfShamIfMD5KeyEntries     OBJECT-TYPE
    SYNTAX      Gauge32
    MAX-ACCESS  read-only
    STATUS      current
    DESCRIPTION
        "The value of tmnxOspfShamIfMD5KeyEntries indicates the number of row
         entries in the tmnxOspfShamIfMD5KeyTable."
    ::= { tmnxOspfStatisticsEntry 35 }

tmnxOspfLfaSpfRuns OBJECT-TYPE
    SYNTAX      Counter32
    MAX-ACCESS  read-only
    STATUS      current
    DESCRIPTION
        "The value of tmnxOspfLfaSpfRuns indicates the total number of
         times that complete LFA SPF has been run on the router since OSPF
         was last enabled."
    ::= { tmnxOspfStatisticsEntry 36 }

-- 
--  Augmentation of the tmnxOspfGeneralTable.
--  Use of AUGMENTS clause implies a one-to-one dependent relationship between
--  the base table, tmnxOspfGeneralTable, and the augmenting table, 
--  tmnxOspfChangedTable.
--  This in effect extends the tmnxOspfGeneralTable with additional columns.  
--  Creation (or deletion) of a row in the tmnxOspfGeneralTable results in 
--  the same fate for the row in the tmnxOspfChangedTable.
-- 
tmnxOspfChangedTable OBJECT-TYPE
    SYNTAX      SEQUENCE OF TmnxOspfChangedEntry
    MAX-ACCESS  not-accessible
    STATUS      current
    DESCRIPTION
        "The tmnxOspfChangedTable provides an extension of the 
         tmnxOspfGeneralTable for last changed timestamps for an
         OSPF instance."
    ::= { tmnxOspfObjects 5 }

tmnxOspfChangedEntry OBJECT-TYPE
    SYNTAX      TmnxOspfChangedEntry
    MAX-ACCESS  not-accessible
    STATUS      current
    DESCRIPTION
        "Each row entry in the tmnxOspfChangedTable represents additional 
         columns for last changed timestamps for an OSPF instance."
    AUGMENTS { tmnxOspfGeneralEntry }
   ::= { tmnxOspfChangedTable 1 }

TmnxOspfChangedEntry ::=
    SEQUENCE {
        tmnxOspfAreaTableChanged            TimeStamp,
        tmnxOspfHostTableChanged            TimeStamp,
        tmnxOspfIfTableChanged              TimeStamp,
        tmnxOspfVirtIfTableChanged          TimeStamp,
        tmnxOspfNbrTableChanged             TimeStamp,
        tmnxOspfCfgNbrTableChanged          TimeStamp,
        tmnxOspfVirtNbrTableChanged         TimeStamp,
        tmnxOspfAreaAggTableChanged         TimeStamp,
        tmnxOspfIfMD5KeyTableChanged        TimeStamp,
        tmnxOspfVirtIfMD5KeyTableChanged    TimeStamp,
        tmnxOspfShamIfTableChanged          TimeStamp,
        tmnxOspfShamNbrTableChanged         TimeStamp,
        tmnxOspfShamIfMD5KeyTableChanged    TimeStamp
    }

tmnxOspfAreaTableChanged  OBJECT-TYPE
    SYNTAX      TimeStamp
    MAX-ACCESS  read-only
    STATUS      current
    DESCRIPTION
        "The value of tmnxOspfAreaTableChanged indicates the sysUpTime
         when a configurable object in the tmnxOspfAreaTable was last
         modified for this OSPF instance.  If no modifications have been 
         made since this instance of OSPF was created, 
         tmnxOspfAreaTableChanged will have a 0 value."
    ::= { tmnxOspfChangedEntry 1 } 

tmnxOspfHostTableChanged  OBJECT-TYPE
    SYNTAX      TimeStamp
    MAX-ACCESS  read-only
    STATUS      current
    DESCRIPTION
        "The value of tmnxOspfHostTableChanged indicates the sysUpTime
         when a configurable object in the tmnxOspfHostTable was last
         modified for this OSPF instance.  If no modifications have been 
         made since this instance of OSPF was created, tmnxOspfHostTableChanged
         will have a 0 value."
    ::= { tmnxOspfChangedEntry 2 } 

tmnxOspfIfTableChanged  OBJECT-TYPE
    SYNTAX      TimeStamp
    MAX-ACCESS  read-only
    STATUS      current
    DESCRIPTION
        "The value of tmnxOspfIfTableChanged indicates the sysUpTime
         when a configurable object in the tmnxOspfNgIfTable was last
         modified for this OSPF instance.  If no modifications have been 
         made since this instance of OSPF was created, tmnxOspfIfTableChanged 
         will have a 0 value."
    ::= { tmnxOspfChangedEntry 3 } 

tmnxOspfVirtIfTableChanged  OBJECT-TYPE
    SYNTAX      TimeStamp
    MAX-ACCESS  read-only
    STATUS      current
    DESCRIPTION
        "The value of tmnxOspfVirtIfTableChanged indicates the sysUpTime
         when a configurable object in the tmnxOspfVirtIfTable was last
         modified for this OSPF instance.  If no modifications have been 
         made since this instance of OSPF was created, 
         tmnxOspfVirtIfTableChanged will have a 0 value."
    ::= { tmnxOspfChangedEntry 4 } 

tmnxOspfNbrTableChanged  OBJECT-TYPE
    SYNTAX      TimeStamp
    MAX-ACCESS  read-only
    STATUS      current
    DESCRIPTION
        "The value of tmnxOspfNbrTableChanged indicates the sysUpTime
         when a configurable object in the tmnxOspfNgNbrTable was last
         modified for this OSPF instance.  If no modifications have been 
         made since this instance of OSPF was created, 
         tmnxOspfNbrTableChanged will have a 0 value."
    ::= { tmnxOspfChangedEntry 5 } 

tmnxOspfCfgNbrTableChanged  OBJECT-TYPE
    SYNTAX      TimeStamp
    MAX-ACCESS  read-only
    STATUS      current
    DESCRIPTION
        "The value of tmnxOspfCfgNbrTableChanged indicates the sysUpTime
         when a configurable object in the tmnxOspfCfgNbrTable was last
         modified for this OSPF instance.  If no modifications have been 
         made since this instance of OSPF was created, 
         tmnxOspfCfgNbrTableChanged will have a 0 value."
    ::= { tmnxOspfChangedEntry 6 } 

tmnxOspfVirtNbrTableChanged  OBJECT-TYPE
    SYNTAX      TimeStamp
    MAX-ACCESS  read-only
    STATUS      current
    DESCRIPTION
        "The value of tmnxOspfVirtNbrTableChanged indicates the sysUpTime
         when a configurable object in the tmnxOspfVirtNbrTable was last
         modified for this OSPF instance.  If no modifications have been 
         made since this instance of OSPF was created, 
         tmnxOspfVirtNbrTableChanged will have a 0 value."
    ::= { tmnxOspfChangedEntry 7 } 

tmnxOspfAreaAggTableChanged  OBJECT-TYPE
    SYNTAX      TimeStamp
    MAX-ACCESS  read-only
    STATUS      current
    DESCRIPTION
        "The value of tmnxOspfAreaAggTableChanged indicates the sysUpTime
         when a configurable object in the tmnxOspfAreaAggrTable was last
         modified for this OSPF instance.  If no modifications have been 
         made since this instance of OSPF was created, 
         tmnxOspfAreaAggTableChanged will have a 0 value."
    ::= { tmnxOspfChangedEntry 8 } 

tmnxOspfIfMD5KeyTableChanged  OBJECT-TYPE
    SYNTAX      TimeStamp
    MAX-ACCESS  read-only
    STATUS      current
    DESCRIPTION
        "The value of tmnxOspfIfMD5KeyTableChanged indicates the sysUpTime
         when a configurable object in the tmnxOspfNgIfMD5KeyTable was last
         modified for this OSPF instance.  If no modifications have been 
         made since this instance of OSPF was created, 
         tmnxOspfIfMD5KeyTableChanged will have a 0 value."
    ::= { tmnxOspfChangedEntry 9 } 

tmnxOspfVirtIfMD5KeyTableChanged  OBJECT-TYPE
    SYNTAX      TimeStamp
    MAX-ACCESS  read-only
    STATUS      current
    DESCRIPTION
        "The value of tmnxOspfVirtIfMD5KeyTableChanged indicates the sysUpTime
         when a configurable object in the tmnxOspfVirtIfMD5KeyTable was last
         modified for this OSPF instance.  If no modifications have been 
         made since this instance of OSPF was created, 
         tmnxOspfVirtIfMD5KeyTableChanged will have a 0 value."
    ::= { tmnxOspfChangedEntry 10 } 

tmnxOspfShamIfTableChanged  OBJECT-TYPE
    SYNTAX      TimeStamp
    MAX-ACCESS  read-only
    STATUS      current
    DESCRIPTION
        "The value of tmnxOspfShamIfTableChanged indicates the sysUpTime
         when a configurable object in the tmnxOspfShamIfTable was last
         modified for this OSPF instance.  If no modifications have been 
         made since this instance of OSPF was created, 
         tmnxOspfShamIfTableChanged will have a 0 value."
    ::= { tmnxOspfChangedEntry 11 } 

tmnxOspfShamNbrTableChanged  OBJECT-TYPE
    SYNTAX      TimeStamp
    MAX-ACCESS  read-only
    STATUS      current
    DESCRIPTION
        "The value of tmnxOspfShamNbrTableChanged indicates the sysUpTime
         when a configurable object in the tmnxOspfShamNbrTable was last
         modified for this OSPF instance.  If no modifications have been 
         made since this instance of OSPF was created, 
         tmnxOspfShamNbrTableChanged will have a 0 value."
    ::= { tmnxOspfChangedEntry 12 } 

tmnxOspfShamIfMD5KeyTableChanged  OBJECT-TYPE
    SYNTAX      TimeStamp
    MAX-ACCESS  read-only
    STATUS      current
    DESCRIPTION
        "The value of tmnxOspfShamIfMD5KeyTableChanged indicates the sysUpTime
         when a configurable object in the tmnxOspfShamIfMD5KeyTable was last
         modified for this OSPF instance.  If no modifications have been 
         made since this instance of OSPF was created, 
         tmnxOspfShamIfMD5KeyTableChanged will have a 0 value."
    ::= { tmnxOspfChangedEntry 13 } 


-- The OSPF Area Data Structure contains information 
-- regarding the various areas. The interfaces and 
-- virtual links are configured as part of these areas. 
-- Area 0, by definition, is the Backbone Area 
 
tmnxOspfAreaTable OBJECT-TYPE 
    SYNTAX      SEQUENCE OF TmnxOspfAreaEntry 
    MAX-ACCESS  not-accessible 
    STATUS      current 
    DESCRIPTION 
        "The tmnxOspfAreaTable contains information describing the 
         configured parameters and cumulative statistics of the router's 
         attached areas." 
    REFERENCE 
        "OSPF Version 2, Section 6 The Area Data Structure" 
    ::= { tmnxOspfObjects 6 } 
 
tmnxOspfAreaEntry OBJECT-TYPE 
    SYNTAX      TmnxOspfAreaEntry 
    MAX-ACCESS  not-accessible 
    STATUS      current 
    DESCRIPTION 
        "The tmnxOspfAreaEntry contains information describing the 
         configured parameters and cumulative statistics of one of the 
        router's attached areas." 
        INDEX   {   vRtrID,
                    tmnxOspfVersion,
                    tmnxOspfInstance, 
                    tmnxOspfAreaId 
                } 
    ::= { tmnxOspfAreaTable 1 } 
 
TmnxOspfAreaEntry ::= SEQUENCE { 
        tmnxOspfAreaId                      TmnxOspfAreaIdTc, 
        tmnxOspfAreaStatus                  RowStatus,
        tmnxOspfAreaLastChanged             TimeStamp, 
        tmnxOspfImportAsExtern              INTEGER, 
        tmnxOspfAreaSummary                 INTEGER, 
        tmnxOspfAreaRangeBlackhole          TruthValue,
        tmnxOspfStubMetric                  BigMetric, 
        tmnxOspfAreaStubMetricType          INTEGER, 
        tmnxOspfAreaOriginateDefault        INTEGER,
        tmnxOspfAreaNssaRedistribute        TruthValue,
        tmnxOspfAreaNssaTranslatorRole      INTEGER, 
        tmnxOspfAreaNssaTranslatorStabInt   Unsigned32, 
        tmnxOspfAreaBdrRtrCount             Gauge32, 
        tmnxOspfAreaAsBdrRtrCount           Gauge32, 
        tmnxOspfAreaScopeLsaCount           Gauge32, 
        tmnxOspfAreaScopeLsaCksumSum        Integer32, 
        tmnxOspfAreaScopeUnkLsaCount        Gauge32, 
        tmnxOspfAreaScopeUnkLsaCksumSum     Integer32, 
        tmnxOspfAreaNssaTranslatorState     INTEGER, 
        tmnxOspfAreaActiveInterfaces        Unsigned32,
        tmnxOspfAreaInterfaceCount          Unsigned32,
        tmnxOspfAreaVirtualLinkCount        Unsigned32,
        tmnxOspfAreaLastSpfRunTime          TimeStamp,
        tmnxOspfAreaSpfRuns                 Counter32, 
        tmnxOspfAreaNssaTranslatorEvents    Counter32,
        tmnxOspfAreaNeighborCount           Gauge32,
        tmnxOspfAreaShamLinkCount           Gauge32,
        tmnxOspfAreaKeyRolloverInterval     Unsigned32,
        tmnxOspfAreaLoopfreeAltExclude      TruthValue,
        tmnxOspfAreaNssaAdjCheck            TruthValue,
        tmnxOspfAreaAdvRtrCapability        TruthValue
    } 
 
tmnxOspfAreaId OBJECT-TYPE 
    SYNTAX      TmnxOspfAreaIdTc 
    MAX-ACCESS  not-accessible 
    STATUS      current 
    DESCRIPTION 
        "The value of tmnxOspfAreaId specifies a 32-bit integer uniquely 
         identifying an area.  Area ID 0 is used for the OSPF backbone." 
    REFERENCE 
        "OSPF Version 2, Appendix C.2 Area parameters" 
    ::= { tmnxOspfAreaEntry 1 } 
 
tmnxOspfAreaStatus OBJECT-TYPE 
    SYNTAX      RowStatus 
    MAX-ACCESS  read-create 
    STATUS      current 
    DESCRIPTION 
        "The tmnxOspfAreaStatus variable is used for creation and deletion 
         of tmnxOspfAreaTable row entries." 
    ::= { tmnxOspfAreaEntry 2 } 

tmnxOspfAreaLastChanged  OBJECT-TYPE
    SYNTAX      TimeStamp
    MAX-ACCESS  read-only
    STATUS      current
    DESCRIPTION
        "The value of tmnxOspfAreaLastChanged indicates the sysUpTime
         when a configurable object in this row was last modified."
    ::= { tmnxOspfAreaEntry 3 } 

tmnxOspfImportAsExtern OBJECT-TYPE 
    SYNTAX      INTEGER { 
                    importExternal(1),   -- normal area 
                    importNoExternal(2), -- stub area 
                    importNssa(3)        -- not-so-stubby-area 
                } 
    MAX-ACCESS  read-create 
    STATUS      current 
    DESCRIPTION 
        "The value of tmnxOspfImportAsExtern specifies whether an area 
         is a Stub area, NSSA, or standard area. AS-scope LSAs are not 
         imported into Stub Areas or NSSAs. NSSAs import AS-External 
         data as NSSA LSAs which have Area-scope" 
    REFERENCE 
        "OSPF Version 2, Appendix C.2 Area parameters" 
    DEFVAL { importExternal } 
    ::= { tmnxOspfAreaEntry 4 } 
 
tmnxOspfAreaSummary OBJECT-TYPE 
    SYNTAX      INTEGER { 
                    noAreaSummary (1), 
                    sendAreaSummary (2) 
                } 
    MAX-ACCESS  read-create 
    STATUS      current 
    DESCRIPTION 
        "The value of tmnxOspfAreaSummary specifies how the Inter-Area 
         LSAs are imported into stub areas. It has no effect on other areas. 
 
         If it is 'noAreaSummary (1)', the router will neither originate 
         nor propagate Inter-Area LSAs into the stub area. It will rely 
         entirely on its default route. 
 
         If it is 'sendAreaSummary (2)', the router will both summarize 
         and propagate Inter-Area LSAs." 
    DEFVAL  { sendAreaSummary } 
    ::= { tmnxOspfAreaEntry 5 } 
 
tmnxOspfAreaRangeBlackhole OBJECT-TYPE
    SYNTAX      TruthValue
    MAX-ACCESS  read-create
    STATUS      current
    DESCRIPTION
        "The value of tmnxOspfAreaRangeBlackhole specifies whether or not
         a blackhole route needs to be installed for the aggregates
         configured in this area. If the value is 'true', a lowest
         priority backhole route is installed for advertised aggregates
         in this area.  Note that if the value is 'false', the blackhole
         route is not installed and there is a potential for a routing
         loop."
    DEFVAL { true }
    ::= { tmnxOspfAreaEntry 6 }

tmnxOspfStubMetric OBJECT-TYPE 
    SYNTAX      BigMetric 
    MAX-ACCESS  read-create 
    STATUS      current 
    DESCRIPTION 
        "The value of tmnxOspfStubMetric specifies the metric value 
         advertised for the default route into Stub and NSSA areas." 
    ::= { tmnxOspfAreaEntry 7 } 
 
tmnxOspfAreaStubMetricType OBJECT-TYPE 
    SYNTAX      INTEGER { 
                    ospfMetric     (1),  -- OSPF Metric 
                    comparableCost (2),  -- external type 1 
                    nonComparable  (3)   -- external type 2 
                } 
    MAX-ACCESS  read-create 
    STATUS      current 
    DESCRIPTION 
        "The value of tmnxOspfAreaStubMetricType specifies the type of metric 
         advertised as a default route." 
    DEFVAL { ospfMetric } 
    ::= { tmnxOspfAreaEntry 8 } 
    
tmnxOspfAreaOriginateDefault OBJECT-TYPE
    SYNTAX      INTEGER {
                    noOriginate (1),
                    originateType3 (2),
                    originateType7 (3)
                }
    MAX-ACCESS  read-create
    STATUS      current
    DESCRIPTION
        "The value of tmnxOspfAreaOriginateDefault indicates whether or not
         when configuring an NSSA with no summaries, the Area Border Router
         (ABR) will inject a type-7 LSA default route into the NSSA area.
         The default behavior is to inject a type-3 LSA default route, but
         some older implementations expect a type-7 LSA default route.

         When tmnxOspfAreaOriginateDefault has a value of 'originateType7',
         type-7 LSA default routes are injected into an NSSA configured
         with no summaries.

         When tmnxOspfAreaOriginateDefault has a value of 'originateType3',
         type-3 LSA default routes are injected into an NSSA configured
         with no summaries.

         When tmnxOspfAreaOriginateDefault has a value of 'noOriginate',
         no default routes are generated."
    DEFVAL { noOriginate }
    ::= { tmnxOspfAreaEntry 9 }

tmnxOspfAreaNssaRedistribute OBJECT-TYPE
    SYNTAX      TruthValue
    MAX-ACCESS  read-create
    STATUS      current
    DESCRIPTION
        "The value of tmnxOspfAreaNssaRedistribute specifies whether or
         not extenal routes are to be injected or redistributed into the NSSA
         area.
         Setting tmnxOspfAreaNssaRedistribute equal 'false' causes
         external routes to be not injected or redistributed
         into the NSSA area."
    DEFVAL { true }
    ::= { tmnxOspfAreaEntry 10 }

tmnxOspfAreaNssaTranslatorRole OBJECT-TYPE 
    SYNTAX      INTEGER { 
                    always (1), 
                    candidate (2)
                } 
    MAX-ACCESS  read-create 
    STATUS      current 
    DESCRIPTION 
        "The value of tmnxOspfAreaNssaTranslatorRole specifies an 
         NSSA Border router's ability to perform NSSA translation 
         of NSSA-LSAs into AS-External-LSAs." 
    DEFVAL { candidate } 
    ::= { tmnxOspfAreaEntry 11 } 
 
tmnxOspfAreaNssaTranslatorStabInt OBJECT-TYPE 
    SYNTAX      Unsigned32 
    UNITS       "seconds" 
    MAX-ACCESS  read-create 
    STATUS      current 
    DESCRIPTION 
        "The value of tmnxOspfAreaNssaTranslatorStabInt specifies the 
         number of seconds after an elected translator determines its 
         services are no longer required, that it should continue to 
         perform its translation duties." 
    DEFVAL { 40 } 
    ::= { tmnxOspfAreaEntry 12 } 
 
tmnxOspfAreaBdrRtrCount OBJECT-TYPE 
    SYNTAX      Gauge32 
    MAX-ACCESS  read-only 
    STATUS      current 
    DESCRIPTION 
        "The value of tmnxOspfAreaBdrRtrCount indicates the total 
         number of area border routers reachable within this area. 
         This is initially zero, and is calculated in each SPF pass." 
    ::= { tmnxOspfAreaEntry 13 } 
 
tmnxOspfAreaAsBdrRtrCount OBJECT-TYPE 
    SYNTAX      Gauge32 
    MAX-ACCESS  read-only 
    STATUS      current 
    DESCRIPTION 
        "The value of tmnxOspfAreaAsBdrRtrCount indicates the total 
         number of Autonomous System border routers reachable within 
         this area. This is initially zero, and is calculated in each 
         SPF pass." 
    ::= { tmnxOspfAreaEntry 14 } 
 
tmnxOspfAreaScopeLsaCount OBJECT-TYPE 
    SYNTAX      Gauge32 
    MAX-ACCESS  read-only 
    STATUS      current 
    DESCRIPTION 
        "The value of tmnxOspfAreaScopeLsaCount indicates the total 
         number of Area-Scope link state advertisements in this area's 
         link-state database." 
    ::= { tmnxOspfAreaEntry 15 } 
 
tmnxOspfAreaScopeLsaCksumSum OBJECT-TYPE 
    SYNTAX      Integer32 
    MAX-ACCESS  read-only 
    STATUS      current 
    DESCRIPTION 
        "The value of tmnxOspfAreaScopeLsaCksumSum indicates the 32-bit 
         unsigned sum of the Area-Scope link state advertisements' LS 
         checksums contained in this area's link-state database. The sum 
         can be used to determine if there has been a change in a router's 
         link-state database, and to compare the link-state database of 
         two routers." 
    ::= { tmnxOspfAreaEntry 16 } 
 
tmnxOspfAreaScopeUnkLsaCount OBJECT-TYPE 
    SYNTAX      Gauge32 
    MAX-ACCESS  read-only 
    STATUS      current 
    DESCRIPTION 
        "The value of tmnxOspfAreaScopeUnkLsaCount indicates the total 
         number of unknown Area-Scope link-state advertisements in this 
         area's link-state database." 
    ::= { tmnxOspfAreaEntry 17 } 
 
tmnxOspfAreaScopeUnkLsaCksumSum OBJECT-TYPE 
    SYNTAX      Integer32 
    MAX-ACCESS  read-only 
    STATUS      current 
    DESCRIPTION 
        "The value of tmnxOspfAreaScopeUnkLsaCksumSum indicates the 32-bit 
         unsigned sum of the unknown Area-Scope link state advertisements' 
         LS checksums contained in this area's link-state database. The sum 
         can be used to determine if there has been a change in a router's 
         link-state database, and to compare the link-state database of 
         two routers." 
    ::= { tmnxOspfAreaEntry 18 } 
 
tmnxOspfAreaNssaTranslatorState OBJECT-TYPE 
    SYNTAX      INTEGER { 
                    enabled (1), 
                    elected (2), 
                    disabled (3) 
                } 
    MAX-ACCESS  read-only 
    STATUS      current 
    DESCRIPTION 
        "The value of tmnxOspfAreaNssaTranslatorState indicates if 
         and how an NSSA Border router is performing NSSA translation 
         of NSSA-LSAs into AS-External-LSAs.  When this object is set 
         to 'enabled', the NSSA Border router's tmnxOspfAreaNssaTranslatorRole 
         has been set to always.  When this object is set to 'elected', 
         a candidate NSSA Border router is translating NSSA-LSAs into 
         AS-External-LSAs.  When this object is set to 'disabled', a 
         candidate NSSA Border router is NOT translating NSSA-LSAs into 
         AS-External-LSAs." 
    ::= { tmnxOspfAreaEntry 19 } 
 
tmnxOspfAreaActiveInterfaces OBJECT-TYPE
    SYNTAX      Unsigned32
    MAX-ACCESS  read-only
    STATUS      current
    DESCRIPTION
        "The value of tmnxOspfAreaActiveInterfaces indicates the
         total number of currently active interfaces in this area."
    ::= { tmnxOspfAreaEntry 20 }

tmnxOspfAreaInterfaceCount OBJECT-TYPE
    SYNTAX      Unsigned32
    MAX-ACCESS  read-only
    STATUS      current
    DESCRIPTION
        "The value of tmnxOspfAreaInterfaceCount indicates total number
         of interfaces configured in this area."
    ::= { tmnxOspfAreaEntry 21 }

tmnxOspfAreaVirtualLinkCount OBJECT-TYPE
    SYNTAX      Unsigned32
    MAX-ACCESS  read-only
    STATUS      current
    DESCRIPTION
        "The value of tmnxOspfAreaVirtualLinkCount indicates the total number
         of virtual links configured through this area."
    ::= { tmnxOspfAreaEntry 22 }

tmnxOspfAreaLastSpfRunTime OBJECT-TYPE
    SYNTAX      TimeStamp
    MAX-ACCESS  read-only
    STATUS      current
    DESCRIPTION
        "The value of tmnxOspfAreaLastSpfRunTime indicates the
         sysUpTime when Intra-area SPF was last run on this area."
    ::= { tmnxOspfAreaEntry 23 }

tmnxOspfAreaSpfRuns OBJECT-TYPE 
    SYNTAX      Counter32 
    MAX-ACCESS  read-only 
    STATUS      current 
    DESCRIPTION 
        "The value of tmnxOspfAreaSpfRuns indicates the number of 
         times that the intra-area route table has been calculated 
         using this area's link-state database. This is typically done 
         using Dijkstra's algorithm." 
    ::= { tmnxOspfAreaEntry 24 } 
 
tmnxOspfAreaNssaTranslatorEvents OBJECT-TYPE 
    SYNTAX      Counter32 
    MAX-ACCESS  read-only 
    STATUS      current 
    DESCRIPTION 
        "The value of tmnxOspfAreaNssaTranslatorEvents indicates the 
         number of Translator State changes that have occurred since 
         the last boot-up." 
    ::= { tmnxOspfAreaEntry 25 } 
    
tmnxOspfAreaNeighborCount OBJECT-TYPE
    SYNTAX      Gauge32
    MAX-ACCESS  read-only
    STATUS      current
    DESCRIPTION
        "The value of tmnxOspfAreaNeighborCount indicates total number
         of neighbors configured in this area."
    ::= { tmnxOspfAreaEntry 26 }

tmnxOspfAreaShamLinkCount OBJECT-TYPE
    SYNTAX      Gauge32
    MAX-ACCESS  read-only
    STATUS      current
    DESCRIPTION
        "The value of tmnxOspfAreaShamLinkCount indicates the total number
         of sham links configured in this area."
    ::= { tmnxOspfAreaEntry 27 }

tmnxOspfAreaKeyRolloverInterval  OBJECT-TYPE
    SYNTAX      Unsigned32 (10..300)
    UNITS       "seconds"
    MAX-ACCESS  read-create
    STATUS      current
    DESCRIPTION
        "The value of tmnxOspfAreaKeyRolloverInterval specifies the time after
         which a key rollover will start."
    DEFVAL { 10 }
    ::= { tmnxOspfAreaEntry 28 }

tmnxOspfAreaLoopfreeAltExclude OBJECT-TYPE
    SYNTAX      TruthValue
    MAX-ACCESS  read-create
    STATUS      current
    DESCRIPTION
        "The value of tmnxOspfAreaLoopfreeAltExclude specifies whether or not
         the OSPF area should be excluded during LFA calculations. If the value 
         is 'true', the OSPF area is excluded from LFA calculations. If the 
         value is 'false', the OSPF area is included in LFA calculations.

         The value of tmnxOspfAreaLoopfreeAltExclude is only valid when 
         tmnxOspfLoopfreeAlternate has a value of 'true'."
    DEFVAL { false }
    ::= { tmnxOspfAreaEntry 29 }

tmnxOspfAreaNssaAdjCheck OBJECT-TYPE
    SYNTAX      TruthValue
    MAX-ACCESS  read-create
    STATUS      current
    DESCRIPTION
        "The value of tmnxOspfAreaNssaAdjCheck specifies whether or not
         adjacency checks shall be performed for the NSSA. If the value 
         is 'false', then no checks are done. If the value is 'true', then
         adjacency checks will be done."
    DEFVAL { false }
    ::= { tmnxOspfAreaEntry 30 }

tmnxOspfAreaAdvRtrCapability OBJECT-TYPE
    SYNTAX      TruthValue
    MAX-ACCESS  read-create
    STATUS      current
    DESCRIPTION
        "The value of tmnxOspfAreaAdvRtrCapability specifies whether or not
         advertise-router-capabilities are enabled at area level."
    DEFVAL { true }
    ::= { tmnxOspfAreaEntry 31 }

--
-- OSPF Area Link-State Advertisement Counts
-- 
 
tmnxOspfAreaLsaCountTable OBJECT-TYPE 
    SYNTAX          SEQUENCE OF TmnxOspfAreaLsaCountEntry 
    MAX-ACCESS      not-accessible 
    STATUS          current 
    DESCRIPTION 
        "The tmnxOspfAreaLsaCountTable maintains per area per LSA type
         counters." 
    ::= { tmnxOspfObjects 7 } 
 
tmnxOspfAreaLsaCountEntry OBJECT-TYPE 
    SYNTAX          TmnxOspfAreaLsaCountEntry 
    MAX-ACCESS      not-accessible 
    STATUS          current 
    DESCRIPTION 
        "tmnxOspfAreaLsaCountEntry contains link state advertisements (LSAs) 
         counters of a given type of a given area." 
    INDEX       {   vRtrID,
                    tmnxOspfVersion,
                    tmnxOspfInstance,
                    tmnxOspfAreaId,
                    tmnxOspfAreaLsaCountLsaType 
                } 
    ::= { tmnxOspfAreaLsaCountTable 1 } 
    
TmnxOspfAreaLsaCountEntry ::= SEQUENCE {
        tmnxOspfAreaLsaCountLsaType         Unsigned32,
        tmnxOspfAreaLsaCountNumber          Gauge32 
    } 

tmnxOspfAreaLsaCountLsaType     OBJECT-TYPE
    SYNTAX      Unsigned32 (1..65535)
    MAX-ACCESS  not-accessible
    STATUS      current
    DESCRIPTION
        "The value of tmnxOspfAreaLsaCountLsaType identifies a row in
         this table for a specific LSA type within an area.
         
         When tmnxOspfVersion has a value of 'version2', the LSA types
         are limited to these values:
                routerLink (1),
                networkLink (2),
                summaryLink (3),
                asSummaryLink (4),
                multicastLink (6),
                nssaExternalLink (7),
                areaOpaqueLink (10)

         When tmnxOspfVersion has a value of 'version3', this value is
         taken from the lower 13-bits of the 'LsType' field."
    ::= { tmnxOspfAreaLsaCountEntry 1 }

tmnxOspfAreaLsaCountNumber      OBJECT-TYPE
    SYNTAX      Gauge32
    MAX-ACCESS  read-only
    STATUS      current
    DESCRIPTION
        "The value of tmnxOspfAreaLsaCountNumber indicates the number
         of LSAs of tmnxOspfAreaLsaCountLsaType with this area."
    ::= { tmnxOspfAreaLsaCountEntry 2 }

 

    -- OSPF AS-Scope Link State Database 
 
    -- The Link State Database contains the AS-Scope Link State 
    -- Advertisements from throughout the areas that the 
    -- device is attached to. 
 
tmnxOspfAsLsdbTable OBJECT-TYPE 
    SYNTAX          SEQUENCE OF TmnxOspfAsLsdbEntry 
    MAX-ACCESS      not-accessible 
    STATUS          current 
    DESCRIPTION 
        "The OSPF Process's AS-Scope Link State Database." 
    ::= { tmnxOspfObjects 8 } 
 
tmnxOspfAsLsdbEntry OBJECT-TYPE 
    SYNTAX          TmnxOspfAsLsdbEntry 
    MAX-ACCESS      not-accessible 
    STATUS          current 
    DESCRIPTION 
        "A single AS-Scope Link State Advertisement." 
    INDEX       {   vRtrID,
                    tmnxOspfVersion,
                    tmnxOspfInstance,
                    tmnxOspfAsLsdbType, 
                    tmnxOspfAsLsdbRouterId, 
                    tmnxOspfAsLsdbLsid 
                } 
    ::= { tmnxOspfAsLsdbTable 1 } 
    
TmnxOspfAsLsdbEntry ::= SEQUENCE { 
            tmnxOspfAsLsdbType          Unsigned32, 
            tmnxOspfAsLsdbRouterId      TmnxOspfRouterIdTc, 
            tmnxOspfAsLsdbLsid          Unsigned32, 
            tmnxOspfAsLsdbSequence      Integer32, 
            tmnxOspfAsLsdbAge           Integer32, 
            tmnxOspfAsLsdbChecksum      Integer32, 
            tmnxOspfAsLsdbAdvertisement OCTET STRING, 
            tmnxOspfAsLsdbTypeKnown     TruthValue 
    } 
 
tmnxOspfAsLsdbType OBJECT-TYPE 
    SYNTAX      Unsigned32(0..'FFFFFFFF'h) 
    MAX-ACCESS  not-accessible 
    STATUS      current 
    DESCRIPTION 
        "The value of tmnxOspfAsLsdbType specifies the type of the link-state 
         advertisement.  Each link-state type has a separate advertisement 
         format.  AS-Scope LSAs not recognized by the router may be stored 
         in the database." 
    ::= { tmnxOspfAsLsdbEntry 1 } 
 
tmnxOspfAsLsdbRouterId OBJECT-TYPE 
    SYNTAX      TmnxOspfRouterIdTc 
    MAX-ACCESS  not-accessible 
    STATUS      current 
    DESCRIPTION 
        "The value of tmnxOspfAsLsdbRouterId specifies the 32-bit number 
         that uniquely identifies the originating router in the Autonomous 
         System." 
    REFERENCE 
        "OSPF Version 2, Appendix C.1 Global parameters" 
    ::= { tmnxOspfAsLsdbEntry 2 } 
 
tmnxOspfAsLsdbLsid OBJECT-TYPE 
    SYNTAX      Unsigned32 
    MAX-ACCESS  not-accessible 
    STATUS      current 
    DESCRIPTION 
        "The value of tmnxOspfAsLsdbLsid specifies the Link State ID that 
         is an LS Type Specific field containing a unique identifier; 
         it identifies the piece of the routing domain that is being 
         described by the advertisement.  In OSPFv3, the LSID has no 
         addressing semantics." 
    ::= { tmnxOspfAsLsdbEntry 3 } 
 
    -- Note that the OSPF Sequence Number is a 32 bit signed 
    -- integer.  It starts with the value '80000001'h, 
    -- or -'7FFFFFFF'h, and increments until '7FFFFFFF'h 
    -- Thus, a typical sequence number will be very negative. 
 
tmnxOspfAsLsdbSequence OBJECT-TYPE 
    SYNTAX      Integer32 
    MAX-ACCESS  read-only 
    STATUS      current 
    DESCRIPTION 
        "The value of tmnxOspfAsLsdbSequence indicates the signed 32-bit 
         integer sequence number field. It is used to detect old and 
         duplicate link-state advertisements. The space of sequence 
         numbers is linearly ordered. The larger the sequence number 
         the more recent the advertisement." 
    REFERENCE 
        "OSPF Version  2,  Section  12.1.6  LS  sequence number" 
    ::= { tmnxOspfAsLsdbEntry 4 } 
 
tmnxOspfAsLsdbAge OBJECT-TYPE 
    SYNTAX      Integer32 -- Should be 0..'MaxAge' 
                          -- unless 'DoNotAge' bit is set 
    UNITS       "seconds" 
    MAX-ACCESS  read-only 
    STATUS      current 
    DESCRIPTION 
        "The value of tmnxOspfAsLsdbAge indicates the age of the link-state  
         advertisement in seconds." 
    REFERENCE 
        "OSPF Version 2, Section 12.1.1 LS age" 
    ::= { tmnxOspfAsLsdbEntry 5 } 
 
tmnxOspfAsLsdbChecksum OBJECT-TYPE 
    SYNTAX      Integer32 
    MAX-ACCESS  read-only 
    STATUS      current 
    DESCRIPTION 
        "The value of tmnxOspfAsLsdbChecksum indicates the checksum of 
         the complete contents of the advertisement, excepting the age 
         field. The age field is excepted so that an advertisement's age 
         can be incremented without updating the checksum. The checksum 
         used is the same that is used for ISO connectionless datagrams; 
         it is commonly referred to as the Fletcher checksum." 
    REFERENCE 
        "OSPF Version 2, Section 12.1.7 LS checksum" 
    ::= { tmnxOspfAsLsdbEntry 6 } 
 
tmnxOspfAsLsdbAdvertisement OBJECT-TYPE 
    SYNTAX      OCTET STRING (SIZE (1..65535)) 
    MAX-ACCESS  read-only 
    STATUS      current 
    DESCRIPTION 
        "The value of tmnxOspfAsLsdbAdvertisement indicates the entire 
         Link State Advertisement, including its header." 
    ::= { tmnxOspfAsLsdbEntry 7 } 
 
tmnxOspfAsLsdbTypeKnown OBJECT-TYPE 
    SYNTAX      TruthValue 
    MAX-ACCESS  read-only 
    STATUS      current 
    DESCRIPTION 
        "The value of tmnxOspfAsLsdbTypeKnown indicates whether the 
         LSA type is recognized by this Router." 
    ::= { tmnxOspfAsLsdbEntry 8 } 
 
 
    -- OSPF Area-Scope Link State Database 
 
    -- The Link State Database contains the Area-Scope Link State 
    -- Advertisements from throughout the area that the 
    -- device is attached to. 
 
tmnxOspfAreaLsdbTable OBJECT-TYPE 
    SYNTAX      SEQUENCE OF TmnxOspfAreaLsdbEntry 
    MAX-ACCESS  not-accessible 
    STATUS      current 
    DESCRIPTION 
        "The tmnxOspfAreaLsdbTable continins the OSPF Process's Area-Scope 
         Link State Database." 
    ::= { tmnxOspfObjects 9 } 
 
tmnxOspfAreaLsdbEntry OBJECT-TYPE 
    SYNTAX      TmnxOspfAreaLsdbEntry 
    MAX-ACCESS  not-accessible 
    STATUS      current 
    DESCRIPTION 
        "The tmnxOspfAreaLsdbEntry contains information about a single 
         Area-Scope Link State Advertisement." 
    INDEX       {   vRtrID,
                    tmnxOspfVersion,
                    tmnxOspfInstance,
                    tmnxOspfAreaLsdbAreaId, 
                    tmnxOspfAreaLsdbType, 
                    tmnxOspfAreaLsdbRouterId, 
                    tmnxOspfAreaLsdbLsid
                } 
    ::= { tmnxOspfAreaLsdbTable 1 } 
 
TmnxOspfAreaLsdbEntry ::= SEQUENCE { 
            tmnxOspfAreaLsdbAreaId          TmnxOspfAreaIdTc, 
            tmnxOspfAreaLsdbType            Unsigned32, 
            tmnxOspfAreaLsdbRouterId        TmnxOspfRouterIdTc, 
            tmnxOspfAreaLsdbLsid            Unsigned32, 
            tmnxOspfAreaLsdbSequence        Integer32, 
            tmnxOspfAreaLsdbAge             Integer32, 
            tmnxOspfAreaLsdbChecksum        Integer32, 
            tmnxOspfAreaLsdbAdvertisement   OCTET STRING, 
            tmnxOspfAreaLsdbTypeKnown       TruthValue 
            } 
 
tmnxOspfAreaLsdbAreaId OBJECT-TYPE 
    SYNTAX      TmnxOspfAreaIdTc 
    MAX-ACCESS  not-accessible 
    STATUS      current 
    DESCRIPTION 
        "The value of tmnxOspfAreaLsdbAreaId specifies the 32-bit 
         identifier of the Area from which the LSA was received." 
    REFERENCE 
        "OSPF Version 2, Appendix C.2 Area parameters" 
    ::= { tmnxOspfAreaLsdbEntry 1 } 
 
tmnxOspfAreaLsdbType OBJECT-TYPE 
    SYNTAX      Unsigned32(0..'FFFFFFFF'h) 
    MAX-ACCESS  not-accessible 
    STATUS      current 
    DESCRIPTION 
        "The value of tmnxOspfAreaLsdbType specifies the type of the 
         link state advertisement.  Each link state type has a separate 
         advertisement format. Area-Scope LSAs unrecognized by the router 
         are also stored in this database." 
    ::= { tmnxOspfAreaLsdbEntry 2 } 
 
tmnxOspfAreaLsdbRouterId OBJECT-TYPE 
    SYNTAX      TmnxOspfRouterIdTc 
    MAX-ACCESS  not-accessible
    STATUS      current 
    DESCRIPTION 
        "The value of tmnxOspfAreaLsdbRouterId specifies the 32-bit number 
         that uniquely identifies the originating router in the Autonomous 
         System." 
    REFERENCE 
        "OSPF Version 2, Appendix C.1 Global parameters" 
    ::= { tmnxOspfAreaLsdbEntry 3 } 
 
tmnxOspfAreaLsdbLsid OBJECT-TYPE 
    SYNTAX      Unsigned32 
    MAX-ACCESS  not-accessible 
    STATUS      current 
    DESCRIPTION 
        "The value of tmnxOspfAreaLsdbLsid specifies the Link State ID that
         is an LS Type Specific field containing a unique identifier; 
         it identifies the piece of the routing domain that is being 
         described by the advertisement.  In OSPFv3, the LSID has no 
         addressing semantics." 
    ::= { tmnxOspfAreaLsdbEntry 4 } 
 
    -- Note that the OSPF Sequence Number is a 32 bit signed 
    -- integer.  It starts with the value '80000001'h, 
    -- or -'7FFFFFFF'h, and increments until '7FFFFFFF'h 
    -- Thus, a typical sequence number will be very negative. 
 
tmnxOspfAreaLsdbSequence OBJECT-TYPE 
    SYNTAX      Integer32 
    MAX-ACCESS  read-only 
    STATUS      current 
    DESCRIPTION 
        "The value of tmnxOspfAreaLsdbSequence indicates the signed
         32-bit integer that is the sequence number field.  It is used 
         to detect old and duplicate link-state advertisements.  The 
         space of sequence numbers is linearly ordered.  The larger 
         the sequence number the more recent the advertisement." 
    REFERENCE 
        "OSPF Version  2,  Section  12.1.6  LS  sequence 
         number" 
    ::= { tmnxOspfAreaLsdbEntry 5 } 
 
tmnxOspfAreaLsdbAge OBJECT-TYPE 
    SYNTAX      Integer32 -- Should be 0..MaxAge 
                          -- unless 'DoNotAge' bit is set 
    UNITS       "seconds" 
    MAX-ACCESS  read-only 
    STATUS      current 
    DESCRIPTION 
        "The value of tmnxOspfAreaLsdbAge indicates the age of the 
         link-state advertisement in seconds." 
    REFERENCE 
        "OSPF Version 2, Section 12.1.1 LS age" 
    ::= { tmnxOspfAreaLsdbEntry 6 } 
 
tmnxOspfAreaLsdbChecksum OBJECT-TYPE 
    SYNTAX      Integer32 
    MAX-ACCESS  read-only 
    STATUS      current 
    DESCRIPTION 
        "The value of tmnxOspfAreaLsdbChecksum indicates the checksum 
         of the complete contents of the advertisement, excepting the 
         age field. The age field is excepted so that an advertisement's 
         age can be incremented without updating the checksum. The checksum 
         used is the same that is used for ISO connectionless datagrams; 
         it is commonly referred to as the Fletcher checksum." 
    REFERENCE 
        "OSPF Version 2, Section 12.1.7 LS checksum" 
    ::= { tmnxOspfAreaLsdbEntry 7 } 
 
tmnxOspfAreaLsdbAdvertisement OBJECT-TYPE 
    SYNTAX      OCTET STRING (SIZE (1..65535)) 
    MAX-ACCESS  read-only 
    STATUS      current 
    DESCRIPTION 
        "The value of tmnxOspfAreaLsdbAdvertisement indicates the entire 
         Link State Advertisement, including its header." 
    ::= { tmnxOspfAreaLsdbEntry 8 } 
 
tmnxOspfAreaLsdbTypeKnown OBJECT-TYPE 
    SYNTAX      TruthValue 
    MAX-ACCESS  read-only 
    STATUS      current 
    DESCRIPTION 
        "The value of tmnxOspfAreaLsdbTypeKnown indicates whether the 
         LSA type is recognized by this Router." 
    ::= { tmnxOspfAreaLsdbEntry 9 } 
 
-- OSPF Link-Scope Link State Database 
-- 
-- The Link State Database contains the Link-Scope Link State 
-- Advertisements from the links that the 
-- device is attached to. 
 
tmnxOspfLinkLsdbTable OBJECT-TYPE 
    SYNTAX      SEQUENCE OF TmnxOspfLinkLsdbEntry 
    MAX-ACCESS  not-accessible 
    STATUS      obsolete
    DESCRIPTION 
        "The tmnxOspfLinkLsdbTable contains the OSPF Process's Link-Scope 
         Link State Database.

         This table is obsoleted in release 9.0. It is replaced with
         tmnxOspfNgLinkLsdbTable" 
    ::= { tmnxOspfObjects 10 } 
 
tmnxOspfLinkLsdbEntry OBJECT-TYPE 
    SYNTAX      TmnxOspfLinkLsdbEntry 
    MAX-ACCESS  not-accessible 
    STATUS      obsolete
    DESCRIPTION 
        "The tmnxOspfLinkLsdbEntry contains information for a single 
         Link-Scope Link State Advertisement." 
    INDEX       {   vRtrID,
                    tmnxOspfVersion,
                    tmnxOspfInstance,
                    tmnxOspfLinkLsdbIfIndex, 
                    tmnxOspfLinkLsdbIfInstId, 
                    tmnxOspfLinkLsdbType, 
                    tmnxOspfLinkLsdbRouterId, 
                    tmnxOspfLinkLsdbLsid
                } 
    ::= { tmnxOspfLinkLsdbTable 1 } 
 
TmnxOspfLinkLsdbEntry ::= SEQUENCE { 
        tmnxOspfLinkLsdbIfIndex         InterfaceIndex, 
        tmnxOspfLinkLsdbIfInstId        TmnxOspfIfInstIdTc, 
        tmnxOspfLinkLsdbType            Unsigned32, 
        tmnxOspfLinkLsdbRouterId        TmnxOspfRouterIdTc, 
        tmnxOspfLinkLsdbLsid            Unsigned32, 
        tmnxOspfLinkLsdbSequence        Integer32, 
        tmnxOspfLinkLsdbAge             Integer32, 
        tmnxOspfLinkLsdbChecksum        Integer32, 
        tmnxOspfLinkLsdbAdvertisement   OCTET STRING, 
        tmnxOspfLinkLsdbTypeKnown       TruthValue 
    } 
 
tmnxOspfLinkLsdbIfIndex OBJECT-TYPE 
    SYNTAX      InterfaceIndex 
    MAX-ACCESS  not-accessible 
    STATUS      obsolete
    DESCRIPTION 
        "The value of tmnxOspfLinkLsdbIfIndex specifies the identifier 
         of the link from which the LSA was received." 
    ::= { tmnxOspfLinkLsdbEntry 1 } 
 
tmnxOspfLinkLsdbIfInstId OBJECT-TYPE 
    SYNTAX      TmnxOspfIfInstIdTc 
    MAX-ACCESS  not-accessible 
    STATUS      obsolete
    DESCRIPTION 
        "The value of tmnxOspfLinkLsdbIfInstId specifies the identifier 
         of the interface instance from which the LSA was received." 
    ::= { tmnxOspfLinkLsdbEntry 2 } 
 
tmnxOspfLinkLsdbType OBJECT-TYPE 
    SYNTAX      Unsigned32(0..'FFFFFFFF'h) 
    MAX-ACCESS  not-accessible 
    STATUS      obsolete
    DESCRIPTION 
        "The value of tmnxOspfLinkLsdbType specifies the type of the 
         link state advertisement.  Each link state type has a separate 
         advertisement format. Link-Scope LSAs unrecognized by the router 
         are also stored in this database." 
    ::= { tmnxOspfLinkLsdbEntry 3 } 
 
tmnxOspfLinkLsdbRouterId OBJECT-TYPE 
    SYNTAX      TmnxOspfRouterIdTc 
    MAX-ACCESS  not-accessible 
    STATUS      obsolete
    DESCRIPTION 
        "The value of tmnxOspfLinkLsdbRouterId specifies the 32-bit number 
         that uniquely identifies the originating router in the Autonomous 
         System." 
    REFERENCE 
        "OSPF Version 2, Appendix C.1 Global parameters" 
    ::= { tmnxOspfLinkLsdbEntry 4 } 
 
tmnxOspfLinkLsdbLsid OBJECT-TYPE 
    SYNTAX      Unsigned32 
    MAX-ACCESS  not-accessible 
    STATUS      obsolete
    DESCRIPTION 
        "The value of tmnxOspfLinkLsdbLsid specifies the Link State ID that
         is an LS Type Specific field containing a unique identifier; 
         it identifies the piece of the routing domain that is being 
         described by the advertisement. In OSPFv3, the LSID has no 
         addressing semantics." 
    ::= { tmnxOspfLinkLsdbEntry 5 } 
 
    -- Note that the OSPF Sequence Number is a 32 bit signed 
    -- integer.  It starts with the value '80000001'h, 
    -- or -'7FFFFFFF'h, and increments until '7FFFFFFF'h 
    -- Thus, a typical sequence number will be very negative. 
 
tmnxOspfLinkLsdbSequence OBJECT-TYPE 
    SYNTAX      Integer32 
    MAX-ACCESS  read-only 
    STATUS      obsolete
    DESCRIPTION 
        "The value of tmnxOspfLinkLsdbSequence indicates the signed 
         32-bit integer sequence number field. It is used to detect 
         old and duplicate link-state advertisements. The space of 
         sequence numbers is linearly ordered. The larger the sequence 
         number the more recent the advertisement." 
    REFERENCE 
        "OSPF Version  2,  Section  12.1.6  LS  sequence 
         number" 
    ::= { tmnxOspfLinkLsdbEntry 6 } 
 
tmnxOspfLinkLsdbAge OBJECT-TYPE 
    SYNTAX      Integer32 -- Should be 0..'MaxAge' 
                          -- unless 'DoNotAge' bit is set 
    UNITS       "seconds" 
    MAX-ACCESS  read-only 
    STATUS      obsolete
    DESCRIPTION 
        "The value of tmnxOspfLinkLsdbAge indicates the age of the 
         link-state advertisement in seconds." 
    REFERENCE 
        "OSPF Version 2, Section 12.1.1 LS age" 
    ::= { tmnxOspfLinkLsdbEntry 7 } 
 
tmnxOspfLinkLsdbChecksum OBJECT-TYPE 
    SYNTAX      Integer32 
    MAX-ACCESS  read-only 
    STATUS      obsolete
    DESCRIPTION 
        "The value of tmnxOspfLinkLsdbChecksum indicates the checksum 
         of the complete contents of the advertisement, excepting the 
         age field. The age field is excepted so that an advertisement's 
         age can be incremented without updating the checksum.  The 
         checksum used is the same that is used for ISO connectionless 
         datagrams; it is commonly referred to as the Fletcher checksum." 
    REFERENCE 
        "OSPF Version 2, Section 12.1.7 LS checksum" 
    ::= { tmnxOspfLinkLsdbEntry 8 } 
 
tmnxOspfLinkLsdbAdvertisement OBJECT-TYPE 
    SYNTAX      OCTET STRING (SIZE (1..65535)) 
    MAX-ACCESS  read-only 
    STATUS      obsolete
    DESCRIPTION 
        "The value of tmnxOspfLinkLsdbAdvertisement indicates the entire 
         Link State Advertisement, including its header." 
    ::= { tmnxOspfLinkLsdbEntry 9 } 
 
tmnxOspfLinkLsdbTypeKnown OBJECT-TYPE 
    SYNTAX      TruthValue 
    MAX-ACCESS  read-only 
    STATUS      obsolete
    DESCRIPTION 
        "The value of tmnxOspfLinkLsdbTypeKnown indicates whether the 
         LSA type is recognized by this Router." 
    ::= { tmnxOspfLinkLsdbEntry 10 } 
 
 
-- OSPF Host Table 
-- 
-- The Host/Metric Table indicates what hosts are directly 
-- attached to the Router, and what metrics and types of 
-- service should be advertised for them. 
 
tmnxOspfHostTable OBJECT-TYPE 
    SYNTAX          SEQUENCE OF TmnxOspfHostEntry 
    MAX-ACCESS      not-accessible 
    STATUS          current 
    DESCRIPTION 
        "The tmnxOspfHostTable contains the list of Hosts, and their 
         metrics, that the router will advertise as host routes." 
    REFERENCE 
        "OSPF Version 2, Appendix C.6  Host route 
         parameters" 
    ::= { tmnxOspfObjects 11 } 
 
tmnxOspfHostEntry OBJECT-TYPE 
    SYNTAX      TmnxOspfHostEntry 
    MAX-ACCESS  not-accessible 
    STATUS      current 
    DESCRIPTION 
        "The tmnxOspfHostEntry contains information about a metric to be 
         advertised when a given host is reachable." 
    INDEX       {   vRtrID,
                    tmnxOspfVersion,
                    tmnxOspfInstance,
                    tmnxOspfHostAddressType, 
                    tmnxOspfHostAddress
                } 
    ::= { tmnxOspfHostTable 1 } 
 
TmnxOspfHostEntry ::= SEQUENCE { 
        tmnxOspfHostAddressType     InetAddressType, 
        tmnxOspfHostAddress         InetAddress, 
        tmnxOspfHostMetric          Metric, 
        tmnxOspfHostStatus          RowStatus,
        tmnxOspfHostLastChanged     TimeStamp, 
        tmnxOspfHostAreaID          TmnxOspfAreaIdTc 
    } 
 
tmnxOspfHostAddressType OBJECT-TYPE 
    SYNTAX      InetAddressType 
    MAX-ACCESS  not-accessible 
    STATUS      current 
    DESCRIPTION 
        "The value of tmnxOspfHostAddressType specifis the address type of 
         tmnxOspfHostAddress. Only IPv4 or IPv6 addresses without zone index 
         are expected." 
    REFERENCE 
        "OSPF Version 2, Appendix C.6 Host route parameters" 
    ::= { tmnxOspfHostEntry 1 } 
 
 
tmnxOspfHostAddress OBJECT-TYPE 
    SYNTAX      InetAddress (SIZE (4|16)) 
    MAX-ACCESS  not-accessible 
    STATUS      current 
    DESCRIPTION 
        "The value of tmnxOspfHostAddress specifies the IP Address of the 
         Host.  This MUST be a Global address." 
    REFERENCE 
        "OSPF Version 2, Appendix C.6 Host route 
         parameters" 
    ::= { tmnxOspfHostEntry 2 } 
 
tmnxOspfHostMetric OBJECT-TYPE 
    SYNTAX      Metric 
    MAX-ACCESS  read-create 
    STATUS      current 
    DESCRIPTION 
        "The value of tmnxOspfHostMetric specifies the metric to be 
         advertised." 
    REFERENCE 
        "OSPF Version 2, Appendix C.6 Host route 
         parameters" 
    ::= { tmnxOspfHostEntry 3 } 
 
tmnxOspfHostStatus OBJECT-TYPE 
    SYNTAX      RowStatus 
    MAX-ACCESS  read-create 
    STATUS      current 
    DESCRIPTION 
        "The value of tmnxOspfHostStatus controls the status of this 
         row entry. The use of RowStatus is covered in 
         more detail in [6]." 
    ::= { tmnxOspfHostEntry 4 } 
 
tmnxOspfHostLastChanged  OBJECT-TYPE
    SYNTAX      TimeStamp
    MAX-ACCESS  read-only
    STATUS      current
    DESCRIPTION
        "The value of tmnxOspfHostLastChanged indicates the sysUpTime
         when a configurable object in this row was last modified."
    ::= { tmnxOspfHostEntry 5 } 

tmnxOspfHostAreaID OBJECT-TYPE 
    SYNTAX      TmnxOspfAreaIdTc 
    MAX-ACCESS  read-create 
    STATUS      current 
    DESCRIPTION 
        "The value of tmnxOspfHostAreaID specifies he Area the Host 
         Entry is to be found within.  By default, the area that a 
         subsuming OSPF interface is in, or Area 0" 
    REFERENCE 
        "OSPF Version 2, Appendix C.2 Area parameters" 
    ::= { tmnxOspfHostEntry 6 } 
 

    --
    -- OSPF Interface Table 
    --

tmnxOspfIfTable OBJECT-TYPE 
    SYNTAX          SEQUENCE OF TmnxOspfIfEntry 
    MAX-ACCESS      not-accessible 
    STATUS          obsolete
    DESCRIPTION 
        "The tmnxOspfIfTable contains information about the interfaces 
         associated with OSPF.

         This table is obsoleted in release 9.0. It is replaced with
         tmnxOspfNgIfTable and tmnxOspfNgIfOperTable." 
    REFERENCE 
        "OSPF Version 2, Appendix C.3 Router interface 
         parameters" 
    ::= { tmnxOspfObjects 12 } 
 
tmnxOspfIfEntry OBJECT-TYPE 
    SYNTAX          TmnxOspfIfEntry 
    MAX-ACCESS      not-accessible 
    STATUS          obsolete
    DESCRIPTION 
        "The tmnxOspfIfEntry contains information about one interface 
         associated with OSPF." 
    INDEX       {   vRtrID,
                    tmnxOspfVersion,
                    tmnxOspfInstance,
                    tmnxOspfIfIndex, 
                    tmnxOspfIfInstId
                } 
    ::= { tmnxOspfIfTable 1 } 
 
TmnxOspfIfEntry ::= SEQUENCE { 
        tmnxOspfIfIndex                     InterfaceIndex, 
        tmnxOspfIfInstId                    TmnxOspfIfInstIdTc, 
        tmnxOspfIfStatus                    RowStatus,
        tmnxOspfIfLastChanged               TimeStamp, 
        tmnxOspfIfAreaId                    TmnxOspfAreaIdTc, 
        tmnxOspfIfCfgType                   TmnxOspfIfTypeTc, 
        tmnxOspfIfAdminState                Status, 
        tmnxOspfIfRtrPriority               DesignatedRouterPriority, 
        tmnxOspfIfTransitDelay              TmnxOspfUpToRefreshIntervalTc, 
        tmnxOspfIfRetransInterval           TmnxOspfUpToRefreshIntervalTc, 
        tmnxOspfIfHelloInterval             HelloRange, 
        tmnxOspfIfRtrDeadInterval           TmnxOspfDeadIntRangeTc, 
        tmnxOspfIfPollInterval              Unsigned32, 
        tmnxOspfIfMulticastForwarding       INTEGER, 
        tmnxOspfIfCfgMTU                    Integer32,
        tmnxOspfIfCfgMetric                 Metric,
        tmnxOspfIfPassive                   TruthValue,
        tmnxOspfIfAdvtSubnet                TruthValue,
        tmnxOspfIfDemand                    TruthValue, 
        tmnxOspfIfDemandNbrProbe            TruthValue, 
        tmnxOspfIfDemandNbrProbeRetxLimit   Unsigned32, 
        tmnxOspfIfDemandNbrProbeInterval    Unsigned32, 
        tmnxOspfIfAuthType                  TmnxOspfAuthenticationType,
        tmnxOspfIfAuthKey                   OCTET STRING,
        tmnxOspfIfState                     INTEGER, 
        tmnxOspfIfLastEnabledTime           TimeStamp,
        tmnxOspfIfOperMTU                   Integer32,
        tmnxOspfIfMetricValue               Metric, 
        tmnxOspfIfDRId                      TmnxOspfRouterIdTc, 
        tmnxOspfIfDRIpAddrType              InetAddressType,
        tmnxOspfIfDRIpAddr                  InetAddress,
        tmnxOspfIfBDRId                     TmnxOspfRouterIdTc, 
        tmnxOspfIfBDRIpAddrType             InetAddressType,
        tmnxOspfIfBDRIpAddr                 InetAddress,
        tmnxOspfIfLinkLsaCount              Gauge32, 
        tmnxOspfIfLinkLsaCksumSum           Integer32, 
        tmnxOspfIfLinkUnkLsaCount           Gauge32, 
        tmnxOspfIfLinkUnkLsaCksumSum        Integer32, 
        tmnxOspfIfMD5TransmitKeyId          TmnxOspfIfMD5KeyId,
        tmnxOspfIfLocalIpAddressType        InetAddressType, 
        tmnxOspfIfLocalIpAddress            InetAddress,
        tmnxOspfIfMD5NumKeys                Gauge32,
        tmnxOspfIfType                      TmnxOspfIfTypeTc,
        tmnxOspfIfEnableBfd                 TruthValue,
        tmnxOspfIfRemainDownOnFail          TruthValue,
        tmnxOspfIfTeMetric                  Unsigned32,
        tmnxOspfIfTeState                   TmnxOperState,
        tmnxOspfIfAdminGroup                Unsigned32,
        tmnxOspfIfLdpSyncState              TmnxOperState,
        tmnxOspfIfLdpSyncMaxMetric          TruthValue,
        tmnxOspfIfLdpSyncTimerState         INTEGER,
        tmnxOspfIfLdpSyncTimeLeft           Unsigned32,
        tmnxOspfIfInboundSAName             TNamedItemOrEmpty, 
        tmnxOspfIfOutboundSAName            TNamedItemOrEmpty,
        tmnxOspfIfOperInbSAName             TNamedItemOrEmpty, 
        tmnxOspfIfOperInbSANameTemp         TNamedItemOrEmpty, 
        tmnxOspfIfOperOutbSAName            TNamedItemOrEmpty
    } 
 
tmnxOspfIfIndex OBJECT-TYPE 
    SYNTAX      InterfaceIndex 
    MAX-ACCESS  not-accessible 
    STATUS      obsolete
    DESCRIPTION 
        "The value of tmnxOspfIfIndex specifies the interface index of 
         this OSPF interface.  It corresponds to the interface index of the 
         IP interface on which OSPF is configured." 
    ::= { tmnxOspfIfEntry 1 } 
 
tmnxOspfIfInstId OBJECT-TYPE 
    SYNTAX      TmnxOspfIfInstIdTc 
    MAX-ACCESS  not-accessible 
    STATUS      obsolete
    DESCRIPTION 
        "The value of tmnxOspfIfInstId specifies the OSPF instance.  It 
         enables multiple interface instances of OSPF to be run over a 
         single link. Each protocol instance would be assigned a separate 
         ID. This ID has local link significance only." 
    ::= { tmnxOspfIfEntry 2 } 
 
tmnxOspfIfStatus OBJECT-TYPE 
    SYNTAX      RowStatus 
    MAX-ACCESS  read-create 
    STATUS      obsolete
    DESCRIPTION 
        "The value of tmnxOspfIfStatus controls creation and deletion of
         a row entry in this table." 
    ::= { tmnxOspfIfEntry 3 } 
 
tmnxOspfIfLastChanged  OBJECT-TYPE
    SYNTAX      TimeStamp
    MAX-ACCESS  read-only
    STATUS      obsolete
    DESCRIPTION
        "The value of tmnxOspfIfLastChanged indicates the sysUpTime
         when a configurable object in this row was last modified."
    ::= { tmnxOspfIfEntry 4 } 

tmnxOspfIfAreaId OBJECT-TYPE 
    SYNTAX      TmnxOspfAreaIdTc 
    MAX-ACCESS  read-create 
    STATUS      obsolete
    DESCRIPTION 
        "The value of tmnxOspfIfAreaId specifies a 32-bit integer uniquely 
         identifying the area to which the interface connects. Area ID 
         0 is used for the OSPF backbone." 
    DEFVAL { 0 } 
    ::= { tmnxOspfIfEntry 5 } 
 
tmnxOspfIfCfgType OBJECT-TYPE 
    SYNTAX      TmnxOspfIfTypeTc
    MAX-ACCESS  read-create 
    STATUS      obsolete
    DESCRIPTION 
        "The value of tmnxOspfIfCfgType specifies the OSPF interface type.
         
         The value of 'unspecified' is never returned in response to a query.
         It is only used in SET requests to reset the interface type to its
         default value based on the underlying physical interface type."
    ::= { tmnxOspfIfEntry 6 } 
 
tmnxOspfIfAdminState OBJECT-TYPE 
    SYNTAX      Status 
    MAX-ACCESS  read-create 
    STATUS      obsolete
    DESCRIPTION 
        "The value of tmnxOspfIfAdminState specifies the OSPF interface's 
         administrative status.  The value formed on the interface, and the 
         interface will be advertised as an internal route to some area.  
         The value 'disabled' denotes that the interface is external to OSPF." 
    DEFVAL { enabled } 
    ::= { tmnxOspfIfEntry 7 } 
 
tmnxOspfIfRtrPriority OBJECT-TYPE 
    SYNTAX      DesignatedRouterPriority 
    MAX-ACCESS  read-create 
    STATUS      obsolete
    DESCRIPTION 
        "The value of tmnxOspfIfRtrPriority specifies the priority of 
         this interface.  Used in multi-access networks, this field is 
         used in the designated router election algorithm. The value 0 
         signifies that the router is not eligible to become the designated 
         router on this particular network. In the event of a tie in 
         this value, routers will use their Router ID as a tie breaker." 
    DEFVAL { 1 } 
    ::= { tmnxOspfIfEntry 8 } 
 
tmnxOspfIfTransitDelay OBJECT-TYPE 
    SYNTAX      TmnxOspfUpToRefreshIntervalTc (1..1800)
    UNITS       "seconds" 
    MAX-ACCESS  read-create 
    STATUS      obsolete
    DESCRIPTION 
        "The value of tmnxOspfIfTransitDelay specifies the estimated 
         number of seconds it takes to transmit a link state update packet 
         over this interface." 
    DEFVAL { 1 } 
    ::= { tmnxOspfIfEntry 9 } 
 
tmnxOspfIfRetransInterval OBJECT-TYPE 
    SYNTAX      TmnxOspfUpToRefreshIntervalTc (1..1800)
    UNITS       "seconds" 
    MAX-ACCESS  read-create 
    STATUS      obsolete
    DESCRIPTION 
        "The value of tmnxOspfIfRetransInterval specifies the number of 
         seconds between link state advertisement retransmissions, for 
         adjacencies belonging to this interface. This value is also used 
         when retransmitting database description and link state request 
         packets." 
    DEFVAL { 5 } 
    ::= { tmnxOspfIfEntry 10 } 
 
tmnxOspfIfHelloInterval OBJECT-TYPE 
    SYNTAX      HelloRange 
    UNITS       "seconds" 
    MAX-ACCESS  read-create 
    STATUS      obsolete
    DESCRIPTION 
        "The value of tmnxOspfIfHelloInterval specifies the length of time, 
         in seconds, between the Hello packets that the router sends on the 
         interface.  This value MUST be the same for all routers attached to 
         a common network." 
    DEFVAL { 10 } 
    ::= { tmnxOspfIfEntry 11 } 
 
tmnxOspfIfRtrDeadInterval OBJECT-TYPE 
    SYNTAX      TmnxOspfDeadIntRangeTc 
    UNITS       "seconds" 
    MAX-ACCESS  read-create 
    STATUS      obsolete
    DESCRIPTION 
        "The value of tmnxOspfIfRtrDeadInterval specifies the number of 
         seconds that a router's Hello packets have not been seen before 
         its neighbors declare the router down on the interface.  This 
         should be some multiple of the Hello interval." 
    DEFVAL { 40 } 
    ::= { tmnxOspfIfEntry 12 } 
 
tmnxOspfIfPollInterval OBJECT-TYPE 
    SYNTAX      Unsigned32 
    UNITS       "seconds" 
    MAX-ACCESS  read-create 
    STATUS      obsolete
    DESCRIPTION 
        "The value of tmnxOspfIfPollInterval specifies the larger time 
         interval, in seconds, between the Hello packets sent to an inactive  
         non-broadcast multi-access neighbor." 
    DEFVAL { 120 } 
    ::= { tmnxOspfIfEntry 13 } 
 
tmnxOspfIfMulticastForwarding OBJECT-TYPE 
    SYNTAX      INTEGER { 
                    blocked(1),   -- no multicast forwarding 
                    multicast(2), -- using multicast address 
                    unicast(3)    -- to each OSPF neighbor 
                } 
    MAX-ACCESS  read-create 
    STATUS      obsolete
    DESCRIPTION 
        "The value of tmnxOspfIfMulticastForwarding specifies the way 
         multicasts should be forwarded on this interface: not forwarded, 
         forwarded as data link multicasts, or forwarded as data link  
         unicasts.  Data link multicasting is not meaningful on point-to-point 
         and NBMA interfaces, and setting tmnxOspfIfMulticastForwarding to 0 
         effectively disables all multicast forwarding." 
    DEFVAL { blocked } 
    ::= { tmnxOspfIfEntry 14 } 
 
tmnxOspfIfCfgMTU OBJECT-TYPE
    SYNTAX      Integer32 (0 | 512..9198)
    MAX-ACCESS  read-create
    STATUS      obsolete
    DESCRIPTION
        "The value of tmnxOspfIfCfgMTU specifies the desired size of the
         largest packet which can be sent/received on this OSPF interface,
         specified in octets. This size DOES include the underlying IP 
         header length, but not the underlying layer headers/trailers.

         Setting tmnxOspfIfCfgMTU to a value of zero (0), causes the agent
         to recalculate the default MTU size which can vary based on the
         current setting of tmnxPortMode and tmnxPortEncapType variables
         for the port to which this OSPF interface is bound."
    DEFVAL { 0 }
    ::= { tmnxOspfIfEntry 15 }

tmnxOspfIfCfgMetric OBJECT-TYPE 
    SYNTAX      Metric 
    MAX-ACCESS  read-create 
    STATUS      obsolete
    DESCRIPTION 
        "The value of tmnxOspfIfCfgMetric specifies the desired 
         metric value assigned to this interface.  The default value 
         '0' causes the value of the Metric to be calculated as 
         (Reference Bandwidth / ifSpeed).  The value of the reference 
         bandwidth is configured by the tmnxOspfReferenceBandwidth object."
    DEFVAL { 0 } 
    ::= { tmnxOspfIfEntry 16 } 
 
tmnxOspfIfPassive OBJECT-TYPE
    SYNTAX      TruthValue
    MAX-ACCESS  read-create
    STATUS      obsolete
    DESCRIPTION
        "The value of tmnxOspfIfPassive specifies whether or
         or not HELLOs are to be sent out on this interface and
         whether or not the router advertises it as STUB network/link 
         in its router LSAs.  If true, no HELLOs will be sent, and the 
         interface is advertised as a STUB link."
    DEFVAL { false }
    ::= { tmnxOspfIfEntry 17 }

tmnxOspfIfAdvtSubnet OBJECT-TYPE
    SYNTAX      TruthValue
    MAX-ACCESS  read-create
    STATUS      obsolete
    DESCRIPTION
            "The value of tmnxOspfIfAdvtSubnet specifies the advertisement
             method.  When tmnxOspfIfAdvtSubnet is set to 'true', OSPF will
             advertise the network number and netmask instead of the
             individual host-routes of an active point-to-point interface.
             Setting a value for this object has no effect when tmnxOspfVersion
             has the value 'version3'."
    REFERENCE 
        "RFC2328 OSPF Version 2, s12.4.1.1 pg130"
    DEFVAL { true }
    ::= { tmnxOspfIfEntry 18 }

tmnxOspfIfDemand OBJECT-TYPE 
    SYNTAX      TruthValue 
    MAX-ACCESS  read-create 
    STATUS      obsolete
    DESCRIPTION 
        "The value of tmnxOspfIfDemand specifies whether Demand OSPF 
         procedures (hello suppression to FULL neighbors and setting the 
         'DoNotAge' flag on propagated LSAs) should be performed on this 
         OSPF interface." 
    DEFVAL { false } 
    ::= { tmnxOspfIfEntry 19 } 
 
tmnxOspfIfDemandNbrProbe OBJECT-TYPE 
    SYNTAX      TruthValue 
    MAX-ACCESS  read-create 
    STATUS      obsolete
    DESCRIPTION 
        "The value of tmnxOspfIfDemandNbrProbe specifies whether or not 
         neighbor probing is enabled to determine whether or not the neighbor  
         is inactive. Neighbor probing is disabled by default." 
    DEFVAL { false } 
    ::= { tmnxOspfIfEntry 20 } 
 
tmnxOspfIfDemandNbrProbeRetxLimit OBJECT-TYPE  
    SYNTAX      Unsigned32  
    UNITS       "seconds"  
    MAX-ACCESS  read-create 
    STATUS      obsolete
    DESCRIPTION  
        "The value of tmnxOspfIfDemandNbrProbeRetxLimit specifies the 
         number of consecutive LSA retransmissions before the neighbor 
         is deemed inactive and the neighbor adjacency is brought down."  
    DEFVAL { 10 } 
    ::= { tmnxOspfIfEntry 21 }  
 
tmnxOspfIfDemandNbrProbeInterval OBJECT-TYPE  
    SYNTAX      Unsigned32  
    UNITS       "seconds"  
    MAX-ACCESS  read-create 
    STATUS      obsolete
    DESCRIPTION  
        "The value of tmnxOspfIfDemandNbrProbeInterval specifies how often 
         the neighbor will be probed."  
    DEFVAL { 120 } 
    ::= { tmnxOspfIfEntry 22 }  

tmnxOspfIfAuthType OBJECT-TYPE 
    SYNTAX       TmnxOspfAuthenticationType 
    MAX-ACCESS   read-create 
    STATUS       obsolete
    DESCRIPTION 
        "The value of tmnxOspfIfAuthType specifies the authentication 
         type to use for an interface. 
  
         Note that this object can be used to engage in significant attacks 
         against an OSPF router." 
    REFERENCE 
        "OSPF Version 2, Appendix D Authentication" 
    DEFVAL { none } -- no authentication, by default 
    ::= { tmnxOspfIfEntry 23 } 
  
tmnxOspfIfAuthKey OBJECT-TYPE 
    SYNTAX      OCTET STRING (SIZE (0..256)) 
    MAX-ACCESS  read-create 
    STATUS      obsolete
    DESCRIPTION 
        "The value of tmnxOspfIfAuthKey specifies the authentication key
         string.  The cleartext password is used as an OSPF Authentication 
         key when simplePassword security is enabled. This object does not 
         access any OSPF Cryptographic (e.g. MD5) Authentication Key under 
         any circumstance. 
  
         If the key length is shorter than 8 octets, the agent will left 
         adjust and zero fill to 8 octets. 
  
         Unauthenticated interfaces need no authentication key, and simple 
         password authentication cannot use a key of more than 8 octets. 
  
         Note that the use of simplePassword authentication is NOT recommended 
         when there is concern regarding attack upon the OSPF system. 
         This authentication is only sufficient to protect against 
         accidental misconfigurations because it re-uses cleartext passwords. 
         [RFC-1704] 
  
         When read, tmnxOspfIfAuthKey always returns an Octet String of 
         length zero.
         
         This object is valid only when tmnxOspfVersion has a value of
         'version2'." 
    REFERENCE 
        "OSPF Version 2, Section 9 The Interface Data Structure" 
    DEFVAL { '0000000000000000'H } -- 0.0.0.0.0.0.0.0 
    ::= { tmnxOspfIfEntry 24 } 

tmnxOspfIfState OBJECT-TYPE 
    SYNTAX      INTEGER { 
                    down(1), 
                    loopback(2), 
                    waiting(3), 
                    pointToPoint(4), 
                    designatedRouter(5), 
                    backupDesignatedRouter(6), 
                    otherDesignatedRouter(7) 
                } 
    MAX-ACCESS  read-only 
    STATUS      obsolete
    DESCRIPTION 
        "The OSPF Interface State." 
    ::= { tmnxOspfIfEntry 25 } 
 
tmnxOspfIfLastEnabledTime OBJECT-TYPE
    SYNTAX      TimeStamp
    MAX-ACCESS  read-only
    STATUS      obsolete
    DESCRIPTION
        "The value of tmnxOspfIfLastEnabledTime indicates the sysUpTime
         value when ospfIfAdminStat was last set to enabled (1) to
         run the ospf on this interface."
    ::= { tmnxOspfIfEntry 26 }

tmnxOspfIfOperMTU OBJECT-TYPE
    SYNTAX      Integer32
    MAX-ACCESS  read-only
    STATUS      obsolete
    DESCRIPTION
        "The value of tmnxOspfIfOperMTU indicates the operational size
         of the largest packet which can be sent/received on this OSPF
         interface, specified in octets.
         This size DOES include the underlying IP header length,
         but not the underlying layer headers/trailers."
    ::= { tmnxOspfIfEntry 27 }

tmnxOspfIfMetricValue OBJECT-TYPE 
    SYNTAX      Metric 
    MAX-ACCESS  read-only 
    STATUS      obsolete
    DESCRIPTION 
        "The value of tmnxOspfIfMetricValue indicates the metric value 
         this interface is using.  The default value of the Metric is 
         (Reference Bandwidth / ifSpeed).  The value of the reference 
         bandwidth is configured by the tmnxOspfReferenceBandwidth object." 
    ::= { tmnxOspfIfEntry 28 } 
 
tmnxOspfIfDRId      OBJECT-TYPE 
    SYNTAX      TmnxOspfRouterIdTc 
    MAX-ACCESS  read-only 
    STATUS      obsolete
    DESCRIPTION 
        "The value of tmnxOspfIfDRId indicates the Router ID of the 
         Designated Router." 
    ::= { tmnxOspfIfEntry 29 } 
 
tmnxOspfIfDRIpAddrType OBJECT-TYPE 
    SYNTAX      InetAddressType 
    MAX-ACCESS  read-only 
    STATUS      obsolete
    DESCRIPTION 
        "The value of tmnxOspfIfDRIpAddrType type indicates the IP address 
         type of tmnxOspfIfDRIpAddr. For IPv6 type addresses only addresses 
         with zone index are expected." 
    ::= { tmnxOspfIfEntry 30 } 
 
tmnxOspfIfDRIpAddr    OBJECT-TYPE 
    SYNTAX      InetAddress (SIZE (0|4|20)) 
    MAX-ACCESS  read-only 
    STATUS      obsolete
    DESCRIPTION 
        "The value of tmnxOspfIfDRIpAddr indicates the IP address of 
         the Designated Router." 
    ::= { tmnxOspfIfEntry 31 } 
 
tmnxOspfIfBDRId     OBJECT-TYPE 
    SYNTAX      TmnxOspfRouterIdTc 
    MAX-ACCESS  read-only 
    STATUS      obsolete
    DESCRIPTION 
        "The value of tmnxOspfIfBDRId indicates the Router ID of the 
         Backup Designated Router." 
    ::= { tmnxOspfIfEntry 32 } 
 
tmnxOspfIfBDRIpAddrType OBJECT-TYPE 
    SYNTAX      InetAddressType 
    MAX-ACCESS  read-only 
    STATUS      obsolete
    DESCRIPTION 
        "The value of tmnxOspfIfBDRIpAddrType indicates the IP address 
         type of the Backup Designated Router. For IPv6 type addresses 
         only addresses with zone index are expected." 
    ::= { tmnxOspfIfEntry 33 } 
 
tmnxOspfIfBDRIpAddr     OBJECT-TYPE 
    SYNTAX      InetAddress (SIZE (0|4|20)) 
    MAX-ACCESS  read-only 
    STATUS      obsolete
    DESCRIPTION 
        "The value of tmnxOspfIfBDRIpAddr indicates the IP address of 
         the Backup Designated Router." 
    ::= { tmnxOspfIfEntry 34 } 
 
tmnxOspfIfLinkLsaCount OBJECT-TYPE 
    SYNTAX      Gauge32 
    MAX-ACCESS  read-only 
    STATUS      obsolete
    DESCRIPTION 
        "The value of tmnxOspfIfLinkLsaCount indicates the total 
         number of Link-Scope link-state advertisements in this link's 
         link-state database." 
    ::= { tmnxOspfIfEntry 35 } 
 
tmnxOspfIfLinkLsaCksumSum OBJECT-TYPE 
    SYNTAX      Integer32 
    MAX-ACCESS  read-only 
    STATUS      obsolete
    DESCRIPTION 
        "The value of tmnxOspfIfLinkLsaCksumSum indicates the 32-bit 
         unsigned sum of the Link-Scope link-state advertisements' LS 
         checksums contained in this link's link-state database.  The 
         sum can be used to determine if there has been a change in a 
         router's link-state database, and to compare the link state 
         database of two routers." 
    ::= { tmnxOspfIfEntry 36 } 
 
tmnxOspfIfLinkUnkLsaCount OBJECT-TYPE 
    SYNTAX      Gauge32 
    MAX-ACCESS  read-only 
    STATUS      obsolete
    DESCRIPTION 
        "The value of tmnxOspfIfLinkUnkLsaCount indicates the total 
         number of unknown Link-Scope link-state advertisements in this 
         link's link-state database." 
    ::= { tmnxOspfIfEntry 37 } 
 
tmnxOspfIfLinkUnkLsaCksumSum OBJECT-TYPE 
    SYNTAX      Integer32 
    MAX-ACCESS  read-only 
    STATUS      obsolete
    DESCRIPTION 
        "The value of tmnxOspfIfLinkUnkLsaCksumSum indicates the 32-bit 
         unsigned sum of the unknown Link-Scope link-state advertisements' 
         LS checksums contained in this link's link-state database.  The 
         sum can be used to determine if there has been a change in a 
         router's link-state database, and to compare the link-state 
         database of two routers." 
    ::= { tmnxOspfIfEntry 38 } 
 
tmnxOspfIfMD5TransmitKeyId    OBJECT-TYPE
    SYNTAX      TmnxOspfIfMD5KeyId
    MAX-ACCESS  read-only
    STATUS      obsolete
    DESCRIPTION
        "The value of tmnxOspfIfMD5TransmitKeyId indicates the index value
         used to access the row entry in the tmnxOspfIfMD5KeyTable that
         specifies the authentication type and key transmitted on this
         OSPF interface.  This object is valid only when tmnxOspfVersion
         has the value 'version2'.

         If tmnxOspfIfMD5TransmitKeyId has a value of 0, it means that no
         keys are configured."
    ::= { tmnxOspfIfEntry 39 }

tmnxOspfIfLocalIpAddressType OBJECT-TYPE 
    SYNTAX      InetAddressType 
    MAX-ACCESS  read-only 
    STATUS      obsolete
    DESCRIPTION 
        "The value of tmnxOspfIfLocalIpAddressType indicates the IP address 
         type of tmnxOspfIfLocalIpAddress. For IPv6 type addresses only  
         addresses with zone index are expected." 
    ::= { tmnxOspfIfEntry 40 } 
 
tmnxOspfIfLocalIpAddress OBJECT-TYPE 
    SYNTAX      InetAddress (SIZE (0|4|20))  
    MAX-ACCESS  read-only 
    STATUS      obsolete
    DESCRIPTION 
        "The value of tmnxOspfIfLocalIpAddress indicates the IP address of 
         this OSPF local link interface." 
    ::= { tmnxOspfIfEntry 41 } 
 
tmnxOspfIfMD5NumKeys OBJECT-TYPE 
    SYNTAX      Gauge32 
    MAX-ACCESS  read-only 
    STATUS      obsolete
    DESCRIPTION 
        "The value of tmnxOspfIfMD5NumKeys indicates the number of MD5 Key
         entries for this OSPF interface."
    ::= { tmnxOspfIfEntry 42 } 

tmnxOspfIfType OBJECT-TYPE 
    SYNTAX      TmnxOspfIfTypeTc
    MAX-ACCESS  read-only 
    STATUS      obsolete
    DESCRIPTION 
        "The value of tmnxOspfIfType indicates the operational 
         OSPF interface type."
    ::= { tmnxOspfIfEntry 43 } 


tmnxOspfIfEnableBfd       OBJECT-TYPE
    SYNTAX      TruthValue
    MAX-ACCESS  read-create
    STATUS      obsolete
    DESCRIPTION
        "The value of tmnxOspfIfEnableBfd specifies whether Bi-directional
         Forwarding Detection is enabled in this OSPF interface.

         When the value is 'true', this interface can establish BFD sessions 
         and use BFD as a signalling mechanism. When it is 'false', it cannot 
         use BFD."
    DEFVAL { false }
    ::= { tmnxOspfIfEntry 44 }

tmnxOspfIfRemainDownOnFail      OBJECT-TYPE
    SYNTAX      TruthValue
    MAX-ACCESS  read-create
    STATUS      obsolete
    DESCRIPTION
        "The value of tmnxOspfIfRemainDownOnFail specifies whether an OSPF
         adjacency should go down when the BFD session to the peer goes 
         down."
    DEFVAL { false }
    ::= { tmnxOspfIfEntry 45 }

tmnxOspfIfTeMetric  OBJECT-TYPE
    SYNTAX      Unsigned32 (0..16777215)
    MAX-ACCESS  read-only
    STATUS      obsolete
    DESCRIPTION
        "The value of tmnxOspfIfTeMetric indicates the MPLS TE metric configured
         for this interface. This metric is flooded out in the TE metric sub-tlv
         in the OSPF TE LSAs.
         Depending on the configuration, either the TE metric
         value or the native OSPF metric value is used in CSPF computations."
    ::= { tmnxOspfIfEntry 46 }

tmnxOspfIfTeState  OBJECT-TYPE
    SYNTAX      TmnxOperState
    MAX-ACCESS  read-only
    STATUS      obsolete
    DESCRIPTION
        "The value of tmnxOspfIfTeState indicates the MPLS interface TE status 
         from OSPF standpoint."
    ::= { tmnxOspfIfEntry 47 }

tmnxOspfIfAdminGroup  OBJECT-TYPE
    SYNTAX      Unsigned32
    MAX-ACCESS  read-only
    STATUS      obsolete
    DESCRIPTION
        "The value of tmnxOspfIfAdminGroup indicates the bit-map inherited from 
         MPLS interface that identifies the admin groups to which this interface 
         belongs. If bit 'n' is set, then the interface belongs to the admin 
         group with value 'n'."
    ::= { tmnxOspfIfEntry 48 }

tmnxOspfIfLdpSyncState  OBJECT-TYPE
    SYNTAX      TmnxOperState
    MAX-ACCESS  read-only
    STATUS      obsolete
    DESCRIPTION
        "The value of tmnxOspfIfLdpSyncState indicates if IGP-LDP 
         synchronization is enabled on this interface. tmnxOspfIfLdpSyncState 
         is derived from tmnxOspfLdpSyncAdminState and also whether it was 
         enabled at the IP layer from OSPF standpoint."
    ::= { tmnxOspfIfEntry 49 }

tmnxOspfIfLdpSyncMaxMetric   OBJECT-TYPE
    SYNTAX      TruthValue
    MAX-ACCESS  read-only
    STATUS      obsolete
    DESCRIPTION
        "The value of tmnxOspfIfLdpSyncMaxMetric indicates if OSPF  
         advertised maximum metric value for the interface, depending on 
         whether tmnxOspfIfLdpSyncState is enabled on this interface."
    ::= { tmnxOspfIfEntry 50 }

tmnxOspfIfLdpSyncTimerState   OBJECT-TYPE
    SYNTAX      INTEGER {
                    waitForLdpAdj (1), -- Waiting for LDP adj to come up
                    timerActive (2),   -- LDP adj up (sync timer running)
                    ldpExchgDone (3),  -- LDP label exchange done
                    timerExpired (4),  -- Sync timer expired
                    manualExit (5),    -- User intervened for sync termination                    
                    disabled (6)       -- LDP Sync is not being done
                }
    MAX-ACCESS  read-only
    STATUS      obsolete
    DESCRIPTION
        "The value of tmnxOspfIfLdpSyncTimerState indicates the state of the
         tmnxOspfIfLdpSyncTimeLeft on this OSPF interface."
    ::= { tmnxOspfIfEntry 51 }

tmnxOspfIfLdpSyncTimeLeft  OBJECT-TYPE
    SYNTAX      Unsigned32 (0|1..1800)
    UNITS       "seconds"
    MAX-ACCESS  read-only
    STATUS      obsolete
    DESCRIPTION
        "The value of tmnxOspfIfLdpSyncTimeLeft indicates the time left
         before OSPF reverts back to advertising normal metric for this 
         interface. This is applicable only when tmnxOspfIfLdpSyncMaxMetric 
         is 'true'."
    ::= { tmnxOspfIfEntry 52 }

tmnxOspfIfInboundSAName  OBJECT-TYPE
    SYNTAX      TNamedItemOrEmpty
    MAX-ACCESS  read-create
    STATUS      obsolete
    DESCRIPTION
        "The value of tmnxOspfIfInboundSAName specifies the manually configured
         IPsec Security Association name in case the Ospfv3 traffic on the
         [interface] has to be authenticated.

         This object is only valid when tmnxOspfVersion has a value of
         'version3'."
    DEFVAL { ''H }   -- the empty string
    ::= { tmnxOspfIfEntry 53 }

tmnxOspfIfOutboundSAName  OBJECT-TYPE
    SYNTAX      TNamedItemOrEmpty
    MAX-ACCESS  read-create
    STATUS      obsolete
    DESCRIPTION
        "The value of tmnxOspfIfOutboundSAName specifies the manually configured
         IPsec Security Association name in case the Ospfv3 traffic on the
         [interface] has to be authenticated.

         This object is only valid when tmnxOspfVersion has a value of
         'version3'."
    DEFVAL { ''H }   -- the empty string
    ::= { tmnxOspfIfEntry 54 }

tmnxOspfIfOperInbSAName  OBJECT-TYPE
    SYNTAX      TNamedItemOrEmpty
    MAX-ACCESS  read-only
    STATUS      obsolete
    DESCRIPTION
        "The value of tmnxOspfIfOperInbSAName indicates the name of the
         operational inbound manual IPsec Security Association, used for
         authenticating inbound Ospfv3 traffic."
    DEFVAL { ''H }   -- the empty string
    ::= { tmnxOspfIfEntry 55 }

tmnxOspfIfOperInbSANameTemp  OBJECT-TYPE
    SYNTAX      TNamedItemOrEmpty
    MAX-ACCESS  read-only
    STATUS      obsolete
    DESCRIPTION
        "The value of tmnxOspfIfOperInbSANameTemp indicates the name of a
         temporary operational inbound manual IPsec Security Association, used
         for authenticating inbound Ospfv3 traffic.

         This field can only contain a value when the key-rollover mechanism is
         ongoing."
    DEFVAL { ''H }   -- the empty string
    ::= { tmnxOspfIfEntry 56 }

tmnxOspfIfOperOutbSAName  OBJECT-TYPE
    SYNTAX      TNamedItemOrEmpty
    MAX-ACCESS  read-only
    STATUS      obsolete
    DESCRIPTION
        "The value of tmnxOspfIfOperOutbSAName indicates the name of the
         operational outbound manual IPsec Security Association, used for
         authenticating outbound Ospfv3 traffic. When the key-rollover mechanism
         is ongoing, the value can temporarely be different from the value of
         the tmnxOspfIfOutboundSAName field."
    DEFVAL { ''H }   -- the empty string
    ::= { tmnxOspfIfEntry 57 }

-- 
--  Augmentation of the tmnxOspfIfTable.
--  Use of AUGMENTS clause implies a one-to-one dependent relationship between
--  the base table, tmnxOspIfTable, and the augmenting table, 
--  tmnxOspfIfStatsTable.
--
--  This in effect extends the tmnxOspfIfTable with additional columns.  
--  Creation (or deletion) of a row in the tmnxOspfIfTable results in 
--  the same fate for the row in the tmnxOspfIfStatsTable.
-- 
tmnxOspfIfStatsTable OBJECT-TYPE
    SYNTAX      SEQUENCE OF TmnxOspfIfStatsEntry
    MAX-ACCESS  not-accessible
    STATUS      obsolete
    DESCRIPTION
        "The tmnxOspfIfStatsTable provides an extension of the 
         tmnxOspfIfTable for statistics for an OSPF interface.

         This table is obsoleted in release 9.0. It is replaced with
         tmnxOspfNgIfStatsTable"
    ::= { tmnxOspfObjects 13 }

tmnxOspfIfStatsEntry OBJECT-TYPE
    SYNTAX      TmnxOspfIfStatsEntry
    MAX-ACCESS  not-accessible
    STATUS      obsolete
    DESCRIPTION
        "Each row entry in the tmnxOspfIfStatsTable represents 
         additional columns for statistics for an OSPF interface."
    AUGMENTS { tmnxOspfIfEntry }
   ::= { tmnxOspfIfStatsTable 1 }

TmnxOspfIfStatsEntry ::=
    SEQUENCE {
        tmnxOspfIfEvents                    Counter32, 
        tmnxOspfIfTxPackets                 Counter32,
        tmnxOspfIfTxHellos                  Counter32,
        tmnxOspfIfTxDBDs                    Counter32,
        tmnxOspfIfTxLSRs                    Counter32,
        tmnxOspfIfTxLSUs                    Counter32,
        tmnxOspfIfTxLSAcks                  Counter32,
        tmnxOspfIfRxPackets                 Counter32,
        tmnxOspfIfRxHellos                  Counter32,
        tmnxOspfIfRxDBDs                    Counter32,
        tmnxOspfIfRxLSRs                    Counter32,
        tmnxOspfIfRxLSUs                    Counter32,
        tmnxOspfIfRxLSAcks                  Counter32,
        tmnxOspfIfDiscardPackets            Counter32,
        tmnxOspfIfRetransmitOuts            Counter32,
        tmnxOspfIfBadVersions               Counter32,
        tmnxOspfIfBadNetworks               Counter32,
        tmnxOspfIfBadVirtualLinks           Counter32,
        tmnxOspfIfBadAreas                  Counter32,
        tmnxOspfIfBadDstAddrs               Counter32,
        tmnxOspfIfBadNeighbors              Counter32,
        tmnxOspfIfBadPacketTypes            Counter32,
        tmnxOspfIfNeighborCount             Integer32,
        tmnxOspfIfLastEventTime             TimeStamp,
        tmnxOspfIfBadLengths                Counter32,
        tmnxOspfIfBadHelloIntervals         Counter32,
        tmnxOspfIfBadDeadIntervals          Counter32,
        tmnxOspfIfBadOptions                Counter32,
        tmnxOspfIfRxBadChecksums            Counter32,
        tmnxOspfIfBadAuthTypes              Counter32,
        tmnxOspfIfAuthFailures              Counter32
    }   

tmnxOspfIfEvents OBJECT-TYPE 
    SYNTAX      Counter32 
    MAX-ACCESS  read-only 
    STATUS      obsolete
    DESCRIPTION 
        "The value of tmnxOspfIfEvents indicates the number of times 
         this OSPF interface has changed its state, or an error has occurred." 
    ::= { tmnxOspfIfStatsEntry 1 } 
 
tmnxOspfIfTxPackets OBJECT-TYPE
    SYNTAX      Counter32
    MAX-ACCESS  read-only
    STATUS      obsolete
    DESCRIPTION
        "The value of tmnxOspfIfTxPackets indicates the total number of
         OSPF packets transmitted on this interface since tmnxOspfAdminState
         was last set to 'enabled'."
    ::= { tmnxOspfIfStatsEntry 2 }

tmnxOspfIfTxHellos OBJECT-TYPE
    SYNTAX      Counter32
    MAX-ACCESS  read-only
    STATUS      obsolete
    DESCRIPTION
        "The value of tmnxOspfIfTxHellos indicates the total number
         of OSPF Hello packets transmitted on this interface since
         tmnxOspfAdminState was last set to 'enabled'."
    ::= { tmnxOspfIfStatsEntry 3 }

tmnxOspfIfTxDBDs OBJECT-TYPE
    SYNTAX      Counter32
    MAX-ACCESS  read-only
    STATUS      obsolete
    DESCRIPTION
        "The value of tmnxOspfIfTxDBDs indicates the total number
         of OSPF Database Description packets transmitted on this
         interface since tmnxOspfAdminState was last set to 'enabled'."
    ::= { tmnxOspfIfStatsEntry 4 }

tmnxOspfIfTxLSRs OBJECT-TYPE
    SYNTAX      Counter32
    MAX-ACCESS  read-only
    STATUS      obsolete
    DESCRIPTION
        "The value of tmnxOspfIfTxLSRs indicates the total number
         of OSPF Link State Requests (LSRs)transmitted on this
         interface since tmnxOspfAdminState was last set to 'enabled'."
    ::= { tmnxOspfIfStatsEntry 5 }

tmnxOspfIfTxLSUs OBJECT-TYPE
    SYNTAX      Counter32
    MAX-ACCESS  read-only
    STATUS      obsolete
    DESCRIPTION
        "The value of tmnxOspfIfTxLSUs indicates the total number
         of OSPF Link State Updates (LSUs) transmitted on this
         interface since tmnxOspfAdminState was last set to 'enabled'."
    ::= { tmnxOspfIfStatsEntry 6 }

tmnxOspfIfTxLSAcks OBJECT-TYPE
    SYNTAX      Counter32
    MAX-ACCESS  read-only
    STATUS      obsolete
    DESCRIPTION
        "The value of tmnxOspfIfTxLSAcks indicates the total number
         of OSPF Link State Acknowledgements transmitted on this
         interface since tmnxOspfAdminState was last set to 'enabled'."
    ::= { tmnxOspfIfStatsEntry 7 }

tmnxOspfIfRxPackets OBJECT-TYPE
    SYNTAX      Counter32
    MAX-ACCESS  read-only
    STATUS      obsolete
    DESCRIPTION
        "The value of tmnxOspfIfRxPackets indicates the total number of
         OSPF packets received on this interface since tmnxOspfAdminState was
         last set to 'enabled'."
    ::= { tmnxOspfIfStatsEntry 8 }

tmnxOspfIfRxHellos OBJECT-TYPE
    SYNTAX      Counter32
    MAX-ACCESS  read-only
    STATUS      obsolete
    DESCRIPTION
        "The value of tmnxOspfIfRxHellos indicates the total number of
         OSPF Hello packets received on this interface since tmnxOspfAdminState
         was last set to 'enabled'."
    ::= { tmnxOspfIfStatsEntry 9 }

tmnxOspfIfRxDBDs OBJECT-TYPE
    SYNTAX      Counter32
    MAX-ACCESS  read-only
    STATUS      obsolete
    DESCRIPTION
        "The value of tmnxOspfIfRxDBDs indicates the total number of
         OSPF Database Description packets  received on this interface since
         tmnxOspfAdminState was last set to 'enabled'."
    ::= { tmnxOspfIfStatsEntry 10 }

tmnxOspfIfRxLSRs OBJECT-TYPE
    SYNTAX      Counter32
    MAX-ACCESS  read-only
    STATUS      obsolete
    DESCRIPTION
        "The value of tmnxOspfIfRxLSRs indicates the total number of
         Link State Requests (LSRs) received on this interface since
         tmnxOspfAdminState was last set to 'enabled'."
    ::= { tmnxOspfIfStatsEntry 11 }

tmnxOspfIfRxLSUs OBJECT-TYPE
    SYNTAX      Counter32
    MAX-ACCESS  read-only
    STATUS      obsolete
    DESCRIPTION
        "The value of tmnxOspfIfRxLSUs indicates the total number of
         Link State Updates (LSUs) received on this interface since
         tmnxOspfAdminState was last set to 'enabled'."
    ::= { tmnxOspfIfStatsEntry 12 }

tmnxOspfIfRxLSAcks OBJECT-TYPE
    SYNTAX      Counter32
    MAX-ACCESS  read-only
    STATUS      obsolete
    DESCRIPTION
        "The value of tmnxOspfIfRxLSAcks indicates the total number of
         Link State Acknowledgements received on this interface since
         tmnxOspfAdminState was last set to 'enabled'."
    ::= { tmnxOspfIfStatsEntry 13 }

tmnxOspfIfDiscardPackets OBJECT-TYPE
    SYNTAX      Counter32
    MAX-ACCESS  read-only
    STATUS      obsolete
    DESCRIPTION
        "The value of tmnxOspfIfDiscardPackets indicates the total number
         of OSPF packets discarded on this interface since tmnxOspfAdminState 
         was last set to 'enabled'."
    ::= { tmnxOspfIfStatsEntry 14 }

tmnxOspfIfRetransmitOuts OBJECT-TYPE
    SYNTAX      Counter32
    MAX-ACCESS  read-only
    STATUS      obsolete
    DESCRIPTION
        "The value of tmnxOspfIfRetransmitOuts indicates the total number
         of OSPF Retransmits sent on this interface since tmnxOspfAdminState was
         last set to 'enabled'."
    ::= { tmnxOspfIfStatsEntry 15 }

tmnxOspfIfBadVersions OBJECT-TYPE
    SYNTAX      Counter32
    MAX-ACCESS  read-only
    STATUS      obsolete
    DESCRIPTION
        "The value of tmnxOspfIfBadVersions indicates the total number of
         OSPF packets received with bad OSPF version numbers since
         tmnxOspfAdminState was last set to 'enabled'."
    ::= { tmnxOspfIfStatsEntry 16 }

tmnxOspfIfBadNetworks OBJECT-TYPE
    SYNTAX      Counter32
    MAX-ACCESS  read-only
    STATUS      obsolete
    DESCRIPTION
        "The value of tmnxOspfIfBadNetworks indicates the total number of
         OSPF packets received with invalid network or mask since
         tmnxOspfAdminState was last set to 'enabled'."
    ::= { tmnxOspfIfStatsEntry 17 }

tmnxOspfIfBadVirtualLinks OBJECT-TYPE
    SYNTAX      Counter32
    MAX-ACCESS  read-only
    STATUS      obsolete
    DESCRIPTION
        "The value of tmnxOspfIfBadVirtualLinks indicates the total number
         of OSPF packets received on this interface that are destined to a
         virtual link that does not exist since tmnxOspfAdminState was last set
         to 'enabled'."
    ::= { tmnxOspfIfStatsEntry 18 }

tmnxOspfIfBadAreas OBJECT-TYPE
    SYNTAX      Counter32
    MAX-ACCESS  read-only
    STATUS      obsolete
    DESCRIPTION
        "The value of tmnxOspfIfBadAreas indicates the total number of OSPF
         packets received with an area mismatch
         since tmnxOspfAdminState was last set to 'enabled'."
    ::= { tmnxOspfIfStatsEntry 19 }

tmnxOspfIfBadDstAddrs OBJECT-TYPE
    SYNTAX      Counter32
    MAX-ACCESS  read-only
    STATUS      obsolete
    DESCRIPTION
        "The value of tmnxOspfIfBadDstAddrs indicates the total number
         of OSPF packets received with the incorrect IP destination address
         since tmnxOspfAdminState was last set to 'enabled'."
    ::= { tmnxOspfIfStatsEntry 20 }

tmnxOspfIfBadNeighbors OBJECT-TYPE
    SYNTAX      Counter32
    MAX-ACCESS  read-only
    STATUS      obsolete
    DESCRIPTION
        "The value of tmnxOspfIfBadNeighbors indicates the total number
         of OSPF packets received where the neighbor
         information does not match the information this router has
         for the neighbor since tmnxOspfAdminState was last set to 'enabled'."
    ::= { tmnxOspfIfStatsEntry 21 }

tmnxOspfIfBadPacketTypes OBJECT-TYPE
    SYNTAX      Counter32
    MAX-ACCESS  read-only
    STATUS      obsolete
    DESCRIPTION
        "The value of tmnxOspfIfBadPacketTypes indicates the total number
         of OSPF packets received with an invalid OSPF packet type since
         tmnxOspfAdminState was last set to 'enabled'."
    ::= { tmnxOspfIfStatsEntry 22 }

tmnxOspfIfNeighborCount OBJECT-TYPE
    SYNTAX      Integer32
    MAX-ACCESS  read-only
    STATUS      obsolete
    DESCRIPTION
        "The value of tmnxOspfIfNeighborCount indicates the total number of
         OSPF neighbors adjacent on this interface, in a state of INIT or
         greater, since tmnxOspfAdminState was last set to 'enabled'."
    ::= { tmnxOspfIfStatsEntry 23 }

tmnxOspfIfLastEventTime OBJECT-TYPE
    SYNTAX      TimeStamp
    MAX-ACCESS  read-only
    STATUS      obsolete
    DESCRIPTION
        "The value of tmnxOspfIfLastEventTime indicates the value of
         sysUpTime when an event was last associated with this OSPF
         interface."
    ::= { tmnxOspfIfStatsEntry 24 }

tmnxOspfIfBadLengths OBJECT-TYPE
    SYNTAX      Counter32
    MAX-ACCESS  read-only
    STATUS      obsolete
    DESCRIPTION
        "The value of tmnxOspfIfBadLengths indicates the total number
         of OSPF packets received on this interface with a total length
         not equal to the length given in the packet itself since
         tmnxOspfAdminState was last set to 'enabled'."
    ::= { tmnxOspfIfStatsEntry 25 }

tmnxOspfIfBadHelloIntervals OBJECT-TYPE
    SYNTAX      Counter32
    MAX-ACCESS  read-only
    STATUS      obsolete
    DESCRIPTION
        "The value of tmnxOspfIfBadHelloIntervals indicates the
         total number of OSPF packets received where the hello interval
         given in packet was not equal to that configured on this interface
         since tmnxOspfAdminState was last set to 'enabled'."
    ::= { tmnxOspfIfStatsEntry 26 }

tmnxOspfIfBadDeadIntervals OBJECT-TYPE
    SYNTAX      Counter32
    MAX-ACCESS  read-only
    STATUS      obsolete
    DESCRIPTION
        "The value of tmnxOspfIfBadDeadIntervals indicates the
         total number of OSPF packets received where the dead interval
         given in the packet was not equal to that configured on this
         interface since tmnxOspfAdminState was last set to 'enabled'."
    ::= { tmnxOspfIfStatsEntry 27 }

tmnxOspfIfBadOptions OBJECT-TYPE
    SYNTAX      Counter32
    MAX-ACCESS  read-only
    STATUS      obsolete
    DESCRIPTION
        "The value of tmnxOspfIfBadOptions indicates the total number
         of OSPF packets received with an option that does not match
         those configured for this interface or area since
         tmnxOspfAdminState was last set to 'enabled'."
    ::= { tmnxOspfIfStatsEntry 28 }

tmnxOspfIfRxBadChecksums OBJECT-TYPE
    SYNTAX      Counter32
    MAX-ACCESS  read-only
    STATUS      obsolete
    DESCRIPTION
        "The value of tmnxOspfIfRxBadChecksums indicates the count
         of LSAs received with bad checksums."
    ::= { tmnxOspfIfStatsEntry 29 }

tmnxOspfIfBadAuthTypes OBJECT-TYPE
    SYNTAX      Counter32
    MAX-ACCESS  read-only
    STATUS      obsolete
    DESCRIPTION
        "The value of tmnxOspfIfBadAuthTypes indicates the total 
         number of OSPF packets received with an invalid authorization
         type since tmnxOspfAdminState was last set to 'enabled'."
    ::= { tmnxOspfIfStatsEntry 30 }

tmnxOspfIfAuthFailures OBJECT-TYPE
    SYNTAX      Counter32
    MAX-ACCESS  read-only
    STATUS      obsolete
    DESCRIPTION
        "The value of tmnxOspfIfAuthFailures indicates the total 
         number of OSPF packets received with an invalid authorization
         key since tmnxOspfAdminState was last set to 'enabled'."
    ::= { tmnxOspfIfStatsEntry 31 }
 

    -- OSPF Virtual Interface Table 
 
    -- The Virtual Interface Table describes the virtual 
    -- links that the OSPF Process is configured to 
    -- carry on. 
 
tmnxOspfVirtIfTable OBJECT-TYPE 
    SYNTAX      SEQUENCE OF TmnxOspfVirtIfEntry 
    MAX-ACCESS  not-accessible 
    STATUS      current 
    DESCRIPTION 
        "The tmnxOspfVirtIfTable contains information about this router's 
         virtual interfaces." 
    REFERENCE 
        "OSPF Version 2, Appendix C.4 Virtual link 
         parameters" 
    ::= { tmnxOspfObjects 14 } 
 
tmnxOspfVirtIfEntry OBJECT-TYPE 
    SYNTAX          TmnxOspfVirtIfEntry 
    MAX-ACCESS      not-accessible 
    STATUS          current 
    DESCRIPTION 
        "The tmnxOspfVirtIfEntry contains information about a single 
         Virtual Interface." 
    INDEX       {   vRtrID,
                    tmnxOspfVersion,
                    tmnxOspfInstance,
                    tmnxOspfVirtIfAreaId, 
                    tmnxOspfVirtIfNeighbor
                } 
    ::= { tmnxOspfVirtIfTable 1 } 
 
TmnxOspfVirtIfEntry ::= SEQUENCE { 
        tmnxOspfVirtIfAreaId                TmnxOspfAreaIdTc, 
        tmnxOspfVirtIfNeighbor              TmnxOspfRouterIdTc, 
        tmnxOspfVirtIfStatus                RowStatus,
        tmnxOspfVirtIfLastChanged           TimeStamp, 
        tmnxOspfVirtIfIndex                 InterfaceIndex, 
        tmnxOspfVirtIfInstId                TmnxOspfIfInstIdTc, 
        tmnxOspfVirtIfAdminStat             Status,
        tmnxOspfVirtIfTransitDelay          TmnxOspfUpToRefreshIntervalTc, 
        tmnxOspfVirtIfRetransInterval       TmnxOspfUpToRefreshIntervalTc, 
        tmnxOspfVirtIfHelloInterval         HelloRange, 
        tmnxOspfVirtIfRtrDeadInterval       TmnxOspfDeadIntRangeTc, 
        tmnxOspfVirtIfAuthType              TmnxOspfAuthenticationType,
        tmnxOspfVirtIfAuthKey               OCTET STRING,
        tmnxOspfVirtIfState                 INTEGER, 
        tmnxOspfVirtIfLastEnabledTime       TimeStamp,
        tmnxOspfVirtIfCost                  Metric,
        tmnxOspfVirtIfLinkLsaCount          Gauge32, 
        tmnxOspfVirtIfLinkLsaCksumSum       Integer32, 
        tmnxOspfVirtIfLinkUnkLsaCount       Gauge32, 
        tmnxOspfVirtIfLinkUnkLsaCksumSum    Integer32, 
        tmnxOspfVirtIfMD5TransmitKeyId      TmnxOspfIfMD5KeyId,
        tmnxOspfVirtIfLocalIpAddrType       InetAddressType, 
        tmnxOspfVirtIfLocalIpAddress        InetAddress,
        tmnxOspfVirtIfMD5NumKeys            Gauge32,
        tmnxOspfVirtIfInboundSAName         TNamedItemOrEmpty, 
        tmnxOspfVirtIfOutboundSAName        TNamedItemOrEmpty,
        tmnxOspfVirtIfOperInbSAName         TNamedItemOrEmpty, 
        tmnxOspfVirtIfOperInbSANameTemp     TNamedItemOrEmpty, 
        tmnxOspfVirtIfOperOutbSAName        TNamedItemOrEmpty,
        tmnxOspfVirtIfAuthKeyChain          TNamedItemOrEmpty
    } 
 
tmnxOspfVirtIfAreaId OBJECT-TYPE 
    SYNTAX      TmnxOspfAreaIdTc 
    MAX-ACCESS  not-accessible 
    STATUS      current 
    DESCRIPTION 
        "The value of tmnxOspfVirtIfAreaId specifies the Transit Area 
         that the Virtual Link traverses.  By definition, this is not 
         Area 0." 
    ::= { tmnxOspfVirtIfEntry 1 } 
 
tmnxOspfVirtIfNeighbor OBJECT-TYPE 
    SYNTAX      TmnxOspfRouterIdTc 
    MAX-ACCESS  not-accessible
    STATUS      current 
    DESCRIPTION 
        "The value of tmnxOspfVirtIfNeighbor specifies the Router ID of 
         the Virtual Neighbor." 
    ::= { tmnxOspfVirtIfEntry 2 } 
 
tmnxOspfVirtIfStatus OBJECT-TYPE 
    SYNTAX      RowStatus 
    MAX-ACCESS  read-create 
    STATUS      current 
    DESCRIPTION 
        "The value of tmnxOspfVirtIfStatus controls creation and deletion
         or a row entry in this table." 
    ::= { tmnxOspfVirtIfEntry 3 } 
 
tmnxOspfVirtIfLastChanged  OBJECT-TYPE
    SYNTAX      TimeStamp
    MAX-ACCESS  read-only
    STATUS      current
    DESCRIPTION
        "The value of tmnxOspfVirtIfLastChanged indicates the sysUpTime
         when a configurable object in this row was last modified."
    ::= { tmnxOspfVirtIfEntry 4 } 

tmnxOspfVirtIfIndex OBJECT-TYPE 
    SYNTAX      InterfaceIndex 
    MAX-ACCESS  read-create 
    STATUS      current 
    DESCRIPTION 
        "The value of tmnxOspfVirtIfIndex specifies the interface index 
         assigned to this OSPF virtual interface.  It is advertised in 
         Hello's sent over the virtal link and in the router's router-LSAs." 
    ::= { tmnxOspfVirtIfEntry 5 } 
 
tmnxOspfVirtIfInstId OBJECT-TYPE 
    SYNTAX      TmnxOspfIfInstIdTc 
    MAX-ACCESS  read-create 
    STATUS      current 
    DESCRIPTION 
        "The value of tmnxOspfVirtIfInstId specifies the interface instance 
         ID to be used for the virtual interface.  This ID has local link 
         significance only." 
    DEFVAL { 0 } 
    ::= { tmnxOspfVirtIfEntry 6 } 
 
tmnxOspfVirtIfAdminStat OBJECT-TYPE
    SYNTAX      Status
    MAX-ACCESS  read-create
    STATUS      current
    DESCRIPTION
        "The value of tmnxOspfVirtIfAdminStat specifies the desired
         administrative state of OSPF on this virtual interface."
    DEFVAL { disabled }
    ::= { tmnxOspfVirtIfEntry 7 }

tmnxOspfVirtIfTransitDelay OBJECT-TYPE 
    SYNTAX      TmnxOspfUpToRefreshIntervalTc (1..1800)
    UNITS       "seconds" 
    MAX-ACCESS  read-create 
    STATUS      current 
    DESCRIPTION 
        "The value of tmnxOspfVirtIfTransitDelay specifies the estimated 
         number of seconds it takes to transmit a link-state update packet 
         over this interface." 
    DEFVAL { 1 } 
    ::= { tmnxOspfVirtIfEntry 8 } 
 
tmnxOspfVirtIfRetransInterval OBJECT-TYPE 
    SYNTAX      TmnxOspfUpToRefreshIntervalTc (1..1800)
    UNITS       "seconds" 
    MAX-ACCESS  read-create 
    STATUS      current 
    DESCRIPTION 
        "The value of tmnxOspfVirtIfRetransInterval specifies the number 
         of seconds between link-state advertisement retransmissions, for 
         adjacencies belonging to this interface.  This value is also used 
         when retransmitting database description and link-state request 
         packets.  This value should be well over the expected round-trip 
         time." 
    DEFVAL { 5 } 
    ::= { tmnxOspfVirtIfEntry 9 } 
 
tmnxOspfVirtIfHelloInterval OBJECT-TYPE 
    SYNTAX      HelloRange 
    UNITS       "seconds" 
    MAX-ACCESS  read-create 
    STATUS      current 
    DESCRIPTION 
        "The value of tmnxOspfVirtIfHelloInterval specifies the length of 
         time, in seconds, between the Hello packets that the router sends 
         on the interface.  This value MUST be the same for the virtual 
         neighbor." 
    DEFVAL { 10 } 
    ::= { tmnxOspfVirtIfEntry 10 } 
 
tmnxOspfVirtIfRtrDeadInterval OBJECT-TYPE 
    SYNTAX      TmnxOspfDeadIntRangeTc 
    UNITS       "seconds" 
    MAX-ACCESS  read-create 
    STATUS      current 
    DESCRIPTION 
        "The value of tmnxOspfVirtIfRtrDeadInterval specifies the number 
         of seconds that a router's Hello packets have not been seen before 
         its neighbors declare the router down.  This should be some multiple 
         of the Hello interval.  This value MUST be the same for the virtual 
         neighbor." 
    DEFVAL { 60 } 
    ::= { tmnxOspfVirtIfEntry 11 } 
 
tmnxOspfVirtIfAuthType OBJECT-TYPE 
    SYNTAX       TmnxOspfAuthenticationType 
    MAX-ACCESS   read-create 
    STATUS       current 
    DESCRIPTION 
        "The value of tmnxOspfVirtIfAuthType specifies the authentication 
         type to use for an interface. 
  
         Note that this object can be used to engage in significant attacks 
         against an OSPF router." 
    REFERENCE 
        "OSPF Version 2, Appendix D Authentication" 
    DEFVAL { none } -- no authentication, by default 
    ::= { tmnxOspfVirtIfEntry 12 } 
  
tmnxOspfVirtIfAuthKey OBJECT-TYPE 
    SYNTAX      OCTET STRING (SIZE (0..256)) 
    MAX-ACCESS  read-create 
    STATUS      current 
    DESCRIPTION 
        "The value of tmnxOspfVirtIfAuthKey specifies the authentication key
         string.  The cleartext password is used as an OSPF Authentication 
         key when simplePassword security is enabled. This object does not 
         access any OSPF Cryptographic (e.g. MD5) Authentication Key under 
         any circumstance. 
  
         If the key length is shorter than 8 octets, the agent will left 
         adjust and zero fill to 8 octets. 
  
         Unauthenticated interfaces need no authentication key, and simple 
         password authentication cannot use a key of more than 8 octets. 
  
         Note that the use of simplePassword authentication is NOT recommended 
         when there is concern regarding attack upon the OSPF system. 
         This authentication is only sufficient to protect against 
         accidental misconfigurations because it re-uses cleartext passwords. 
         [RFC-1704] 
  
         When read, tmnxOspfVirtIfAuthKey always returns an Octet String of 
         length zero.
         
         This object is valid only when tmnxOspfVersion has a value of
         'version2'." 
    REFERENCE 
        "OSPF Version 2, Section 9 The Interface Data Structure" 
    DEFVAL { '0000000000000000'H } -- 0.0.0.0.0.0.0.0 
    ::= { tmnxOspfVirtIfEntry 13 } 

tmnxOspfVirtIfState OBJECT-TYPE 
    SYNTAX      INTEGER { 
                    down(1), 
                    pointToPoint(4) 
                } 
    MAX-ACCESS  read-only 
    STATUS      current 
    DESCRIPTION 
        "The value of tmnxOspfVirtIfState indicates the operational state
         of this virtual interface." 
    ::= { tmnxOspfVirtIfEntry 14 } 
 
tmnxOspfVirtIfLastEnabledTime OBJECT-TYPE
    SYNTAX      TimeStamp
    MAX-ACCESS  read-only
    STATUS      current
    DESCRIPTION
        "The value of tmnxOspfVirtIfLastEnabledTime indicates the sysUpTime
         value when this entry row entry was enabled."
    ::= { tmnxOspfVirtIfEntry 15 }

tmnxOspfVirtIfCost OBJECT-TYPE
    SYNTAX      Metric
    MAX-ACCESS  read-only
    STATUS      current
    DESCRIPTION
        "The value of tmnxOspfVirtIfCost indicates the OSPF virtual
         interface cost represents the cost to traverse the transit area
         to the adjacent router. If multiple routes are
         available the lowest cost link will be used to maintain the
         adjacency and route traffic across the transit area."
    ::= { tmnxOspfVirtIfEntry 16 }

tmnxOspfVirtIfLinkLsaCount OBJECT-TYPE 
    SYNTAX      Gauge32 
    MAX-ACCESS  read-only 
    STATUS      current 
    DESCRIPTION 
        "The value of tmnxOspfVirtIfLinkLsaCount indicates the total 
         number of Link-Scope link-state advertisements in this virtual 
         link's link-state database." 
    ::= { tmnxOspfVirtIfEntry 17 } 
 
tmnxOspfVirtIfLinkLsaCksumSum OBJECT-TYPE 
    SYNTAX      Integer32 
    MAX-ACCESS  read-only 
    STATUS      current 
    DESCRIPTION 
        "The value of tmnxOspfVirtIfLinkLsaCksumSum indicates the 32-bit 
         unsigned sum of the Link-Scope link-state advertisements' LS 
         checksums contained in this virtual link's link-state database.  
         The sum can be used to determine if there has been a change in a 
         router's link-state database, and to compare the link-state database 
         of two routers." 
    ::= { tmnxOspfVirtIfEntry 18 } 
 
tmnxOspfVirtIfLinkUnkLsaCount OBJECT-TYPE 
    SYNTAX      Gauge32 
    MAX-ACCESS  read-only 
    STATUS      current 
    DESCRIPTION 
        "The value of tmnxOspfVirtIfLinkUnkLsaCount indicates the total 
         number of unknown Link-Scope link-state advertisements in this 
         virtual link's link-state database." 
    ::= { tmnxOspfVirtIfEntry 19 } 
 
tmnxOspfVirtIfLinkUnkLsaCksumSum OBJECT-TYPE 
    SYNTAX      Integer32 
    MAX-ACCESS  read-only 
    STATUS      current 
    DESCRIPTION 
        "The value of tmnxOspfVirtIfLinkUnkLsaCksumSum indicates the 
         32-bit unsigned sum of the unknown Link-Scope link-state 
         advertisements' LS checksums contained in this virtual link's 
         link-state database.  The sum can be used to determine if there 
         has been a change in a router's link state database, and to 
         compare the link-state database of two routers." 
    ::= { tmnxOspfVirtIfEntry 20 } 
 
tmnxOspfVirtIfMD5TransmitKeyId    OBJECT-TYPE
    SYNTAX      TmnxOspfIfMD5KeyId
    MAX-ACCESS  read-only
    STATUS      current
    DESCRIPTION
        "The value of tmnxOspfVirtIfMD5TransmitKeyId indicates the index value
         used to access the row entry in the tmnxOspfVirtIfMD5KeyTable that
         specifies the authentication type and key transmitted on this
         OSPF virtual interface.  This object is valid only when 
         tmnxOspfVersion has the value 'version2'.

         If tmnxOspfVirtIfMD5TransmitKeyId has a value of 0, it means that no
         keys are configured."
    ::= { tmnxOspfVirtIfEntry 21 }

tmnxOspfVirtIfLocalIpAddrType OBJECT-TYPE 
    SYNTAX      InetAddressType 
    MAX-ACCESS  read-only 
    STATUS      current 
    DESCRIPTION 
        "The value of tmnxOspfVirtIfLocalIpAddrType type indicates the 
        IP address type of tmnxOspfVirtIfLocalIpAddress. For IPv6 type   
        addresses only addresses without zone index are expected." 
    ::= { tmnxOspfVirtIfEntry 22 } 
 
tmnxOspfVirtIfLocalIpAddress OBJECT-TYPE 
    SYNTAX      InetAddress (SIZE (0|4|16))  
    MAX-ACCESS  read-only 
    STATUS      current 
    DESCRIPTION 
        "The value of tmnxOspfVirtIfLocalIpAddress indicates the IP address
         of the local egress interface that is used to  maintain the
         adjacency to reach this virtual neighbor."
    ::= { tmnxOspfVirtIfEntry 23 } 

tmnxOspfVirtIfMD5NumKeys OBJECT-TYPE 
    SYNTAX      Gauge32
    MAX-ACCESS  read-only 
    STATUS      current 
    DESCRIPTION 
        "The value of tmnxOspfVirtIfMD5NumKeys indicates the number of MD5 Key
         entries for this OSPF virtual interface."
    ::= { tmnxOspfVirtIfEntry 24 } 

tmnxOspfVirtIfInboundSAName  OBJECT-TYPE
    SYNTAX      TNamedItemOrEmpty
    MAX-ACCESS  read-create
    STATUS      current
    DESCRIPTION
        "The value of tmnxOspfVirtIfInboundSAName specifies the manually
         configured IPsec Security Association name in case the Ospfv3 traffic
         on the [virtual link] has to be authenticated.

         This object is only valid when tmnxOspfVersion has a value of
         'version3'."
    DEFVAL { ''H }   -- the empty string
    ::= { tmnxOspfVirtIfEntry 25 }

tmnxOspfVirtIfOutboundSAName  OBJECT-TYPE
    SYNTAX      TNamedItemOrEmpty
    MAX-ACCESS  read-create
    STATUS      current
    DESCRIPTION
        "The value of tmnxOspfVirtIfOutboundSAName specifies the manually
         configured IPsec Security Association name in case the Ospfv3 traffic
         on the [virtual link] has to be authenticated.

         This object is only valid when tmnxOspfVersion has a value of
         'version3'."
    DEFVAL { ''H }   -- the empty string
    ::= { tmnxOspfVirtIfEntry 26 }

tmnxOspfVirtIfOperInbSAName  OBJECT-TYPE
    SYNTAX      TNamedItemOrEmpty
    MAX-ACCESS  read-only
    STATUS      current
    DESCRIPTION
        "The value of tmnxOspfVirtIfOperInbSAName indicates the name of the
         operational inbound manual IPsec Security Association, used for
         authenticating inbound Ospfv3 traffic."
    DEFVAL { ''H }   -- the empty string
    ::= { tmnxOspfVirtIfEntry 27 }

tmnxOspfVirtIfOperInbSANameTemp  OBJECT-TYPE
    SYNTAX      TNamedItemOrEmpty
    MAX-ACCESS  read-only
    STATUS      current
    DESCRIPTION
        "The value of tmnxOspfVirtIfOperInbSANameTemp indicates the name of a
         temporary operational inbound manual IPsec Security Association, used
         for authenticating inbound Ospfv3 traffic.

         This field can only contain a value when the key-rollover mechanism is
         ongoing."
    DEFVAL { ''H }   -- the empty string
    ::= { tmnxOspfVirtIfEntry 28 }

tmnxOspfVirtIfOperOutbSAName  OBJECT-TYPE
    SYNTAX      TNamedItemOrEmpty
    MAX-ACCESS  read-only
    STATUS      current
    DESCRIPTION
        "The value of tmnxOspfVirtIfOperOutbSAName indicates the name of the
         operational outbound manual IPsec Security Association, used for
         authenticating outbound Ospfv3 traffic. When the key-rollover mechanism
         is ongoing, the value can temporarely be different from the value of
         the tmnxOspfVirtIfOutboundSAName field."
    DEFVAL { ''H }   -- the empty string
    ::= { tmnxOspfVirtIfEntry 29 }

tmnxOspfVirtIfAuthKeyChain OBJECT-TYPE
    SYNTAX      TNamedItemOrEmpty
    MAX-ACCESS  read-create
    STATUS      current
    DESCRIPTION
        "The value of tmnxOspfVirtIfAuthKeyChain specifies the
         keychain which will be used to sign and/or authenticate the OSPF
         protocol stream.

         The keychain name is defined by tmnxKeyChainName and is the index for
         TIMETRA-SECURITY-MIB::tmnxKeyChainTable."
    DEFVAL { ''H }
    ::= { tmnxOspfVirtIfEntry 30 }

    
-- 
--  Augmentation of the tmnxOspfVirtIfTable.
--  Use of AUGMENTS clause implies a one-to-one dependent relationship 
--  between the base table, tmnxOspVirtIfTable, and the augmenting table, 
--  tmnxOspfVirtIfStatsTable.
--
--  This in effect extends the tmnxOspfVirtIfTable with additional columns.  
--  Creation (or deletion) of a row in the tmnxOspfVirtIfTable results in 
--  the same fate for the row in the tmnxOspfVirtIfStatsTable.
-- 
tmnxOspfVirtIfStatsTable OBJECT-TYPE
    SYNTAX      SEQUENCE OF TmnxOspfVirtIfStatsEntry
    MAX-ACCESS  not-accessible
    STATUS      current
    DESCRIPTION
        "The tmnxOspfVirtIfStatsTable provides an extension of the 
         tmnxOspfVirtIfTable for statistics for an OSPF virtual interface."
    ::= { tmnxOspfObjects 15 }

tmnxOspfVirtIfStatsEntry OBJECT-TYPE
    SYNTAX      TmnxOspfVirtIfStatsEntry
    MAX-ACCESS  not-accessible
    STATUS      current
    DESCRIPTION
        "Each row entry in the tmnxOspfVirtIfStatsTable represents 
         additional columns for statistics for an OSPF virtual interface."
    AUGMENTS { tmnxOspfVirtIfEntry }
   ::= { tmnxOspfVirtIfStatsTable 1 }

TmnxOspfVirtIfStatsEntry ::=
    SEQUENCE {
        tmnxOspfVirtIfEvents            Counter32, 
        tmnxOspfVirtIfTxPackets         Counter32,
        tmnxOspfVirtIfTxHellos          Counter32,
        tmnxOspfVirtIfTxDBDs            Counter32,
        tmnxOspfVirtIfTxLSRs            Counter32,
        tmnxOspfVirtIfTxLSUs            Counter32,
        tmnxOspfVirtIfTxLSAcks          Counter32,
        tmnxOspfVirtIfRxPackets         Counter32,
        tmnxOspfVirtIfRxHellos          Counter32,
        tmnxOspfVirtIfRxDBDs            Counter32,
        tmnxOspfVirtIfRxLSRs            Counter32,
        tmnxOspfVirtIfRxLSUs            Counter32,
        tmnxOspfVirtIfRxLSAcks          Counter32,
        tmnxOspfVirtIfDiscardPackets    Counter32,
        tmnxOspfVirtIfRetransmitOuts    Counter32,
        tmnxOspfVirtIfBadVersions       Counter32,
        tmnxOspfVirtIfBadNetworks       Counter32,
        tmnxOspfVirtIfBadAreas          Counter32,
        tmnxOspfVirtIfBadDstAddrs       Counter32,
        tmnxOspfVirtIfBadNeighbors      Counter32,
        tmnxOspfVirtIfBadPacketTypes    Counter32,
        tmnxOspfVirtIfLastEventTime     TimeStamp,
        tmnxOspfVirtIfBadLengths        Counter32,
        tmnxOspfVirtIfBadHelloIntervls  Counter32,
        tmnxOspfVirtIfBadDeadIntervals  Counter32,
        tmnxOspfVirtIfBadOptions        Counter32,
        tmnxOspfVirtIfRxBadChecksums    Counter32,
        tmnxOspfVirtIfBadAuthTypes      Counter32,    
        tmnxOspfVirtIfAuthFailures      Counter32
    }

tmnxOspfVirtIfEvents OBJECT-TYPE 
    SYNTAX      Counter32 
    MAX-ACCESS  read-only 
    STATUS      current 
    DESCRIPTION 
        "The value of tmnxOspfVirtIfEvents indicates the number of 
         state changes or error events on this Virtual Link" 
    ::= { tmnxOspfVirtIfStatsEntry 1 } 
 
tmnxOspfVirtIfTxPackets OBJECT-TYPE
    SYNTAX      Counter32
    MAX-ACCESS  read-only
    STATUS      current
    DESCRIPTION
        "The value of tmnxOspfVirtIfTxPackets indicates the total number of
         OSPF packets transmitted on this virtual interface since it was
         created."
    ::= { tmnxOspfVirtIfStatsEntry 2 }

tmnxOspfVirtIfTxHellos OBJECT-TYPE
    SYNTAX      Counter32
    MAX-ACCESS  read-only
    STATUS      current
    DESCRIPTION
        "The value of tmnxOspfVirtIfTxHellos indicates the total number of
         OSPF Hello packets transmitted on this virtual interface since it
         was created."
    ::= { tmnxOspfVirtIfStatsEntry 3 }

tmnxOspfVirtIfTxDBDs OBJECT-TYPE
    SYNTAX      Counter32
    MAX-ACCESS  read-only
    STATUS      current
    DESCRIPTION
        "The value of tmnxOspfVirtIfTxDBDs indicates the total number of
         OSPF Database Description packets transmitted on this virtual
         interface."
    ::= { tmnxOspfVirtIfStatsEntry 4 }

tmnxOspfVirtIfTxLSRs OBJECT-TYPE
    SYNTAX      Counter32
    MAX-ACCESS  read-only
    STATUS      current
    DESCRIPTION
        "The value of tmnxOspfVirtIfTxLSRs indicates the total number of
         OSPF Link State Requests (LSRs) transmitted on this virtual
         interface."
    ::= { tmnxOspfVirtIfStatsEntry 5 }

tmnxOspfVirtIfTxLSUs OBJECT-TYPE
    SYNTAX      Counter32
    MAX-ACCESS  read-only
    STATUS      current
    DESCRIPTION
        "The value of tmnxOspfVirtIfTxLSUs indicates the total number of
         OSPF Link State Updates (LSUs) transmitted on this virtual
         interface."
    ::= { tmnxOspfVirtIfStatsEntry 6 }

tmnxOspfVirtIfTxLSAcks OBJECT-TYPE
    SYNTAX      Counter32
    MAX-ACCESS  read-only
    STATUS      current
    DESCRIPTION
        "The value of tmnxOspfVirtIfTxLSAcks indicates the total number of
         OSPF Link State Acknowledgements transmitted on this virtual
         interface."
    ::= { tmnxOspfVirtIfStatsEntry 7 }

tmnxOspfVirtIfRxPackets OBJECT-TYPE
    SYNTAX      Counter32
    MAX-ACCESS  read-only
    STATUS      current
    DESCRIPTION
        "The value of tmnxOspfVirtIfRxPackets indicates the total number of
         OSPF packets received on this virtual interface since it was
         created."
    ::= { tmnxOspfVirtIfStatsEntry 8 }

tmnxOspfVirtIfRxHellos OBJECT-TYPE
    SYNTAX      Counter32
    MAX-ACCESS  read-only
    STATUS      current
    DESCRIPTION
        "The value of tmnxOspfVirtIfRxHellos indicates the total number of
         OSPF Hello packets received on this virtual interface."
    ::= { tmnxOspfVirtIfStatsEntry 9 }

tmnxOspfVirtIfRxDBDs OBJECT-TYPE
    SYNTAX      Counter32
    MAX-ACCESS  read-only
    STATUS      current
    DESCRIPTION
        "The value of tmnxOspfVirtIfRxDBDs indicates the total number of
         OSPF Database Description packets received on this virtual
         interface."
    ::= { tmnxOspfVirtIfStatsEntry 10 }

tmnxOspfVirtIfRxLSRs OBJECT-TYPE
    SYNTAX      Counter32
    MAX-ACCESS  read-only
    STATUS      current
    DESCRIPTION
        "The value of tmnxOspfVirtIfRxLSRs indicates the total number of
         OSPF Link State Requests (LSRs) received on this virtual interface."
    ::= { tmnxOspfVirtIfStatsEntry 11 }

tmnxOspfVirtIfRxLSUs OBJECT-TYPE
    SYNTAX      Counter32
    MAX-ACCESS  read-only
    STATUS      current
    DESCRIPTION
        "The value of tmnxOspfVirtIfRxLSUs indicates the total number of
         OSPF Link State Updates (LSUs) received on this virtual interface."
    ::= { tmnxOspfVirtIfStatsEntry 12 }

tmnxOspfVirtIfRxLSAcks OBJECT-TYPE
    SYNTAX      Counter32
    MAX-ACCESS  read-only
    STATUS      current
    DESCRIPTION
        "The value of tmnxOspfVirtIfRxLSAcks indicates the total number of
         Link State Acknowledgements received on this virtual interface."
    ::= { tmnxOspfVirtIfStatsEntry 13 }

tmnxOspfVirtIfDiscardPackets OBJECT-TYPE
    SYNTAX      Counter32
    MAX-ACCESS  read-only
    STATUS      current
    DESCRIPTION
        "The value of tmnxOspfVirtIfDiscardPackets indicates the total
         number of OSPF packets discarded on this virtual
         interface."
    ::= { tmnxOspfVirtIfStatsEntry 14 }

tmnxOspfVirtIfRetransmitOuts OBJECT-TYPE
    SYNTAX      Counter32
    MAX-ACCESS  read-only
    STATUS      current
    DESCRIPTION
        "The value of tmnxOspfVirtIfRetransmitOuts indicates the total
         number of OSPF packets retransmitted on this virtual
         interface."
    ::= { tmnxOspfVirtIfStatsEntry 15 }

tmnxOspfVirtIfBadVersions OBJECT-TYPE
    SYNTAX      Counter32
    MAX-ACCESS  read-only
    STATUS      current
    DESCRIPTION
        "The value of tmnxOspfVirtIfBadVersions indicates the total number
         of OSPF packets received on this virtual interface
         with invalid OSPF version numbers."
    ::= { tmnxOspfVirtIfStatsEntry 16 }

tmnxOspfVirtIfBadNetworks OBJECT-TYPE
    SYNTAX      Counter32
    MAX-ACCESS  read-only
    STATUS      current
    DESCRIPTION
        "The value of tmnxOspfVirtIfBadNetworks indicates the total number
         of OSPF packets received on this virtual
         interface with invalid network or mask fields."
    ::= { tmnxOspfVirtIfStatsEntry 17 }

tmnxOspfVirtIfBadAreas OBJECT-TYPE
    SYNTAX      Counter32
    MAX-ACCESS  read-only
    STATUS      current
    DESCRIPTION
        "The value of tmnxOspfVirtIfBadAreas indicates the total number
         of OSPF packets received on this virtual interface with area
         mismatches."
    ::= { tmnxOspfVirtIfStatsEntry 18 }

tmnxOspfVirtIfBadDstAddrs OBJECT-TYPE
    SYNTAX      Counter32
    MAX-ACCESS  read-only
    STATUS      current
    DESCRIPTION
        "The value of tmnxOspfVirtIfBadDstAddrs indicates the total number
         of OSPF packets received on this virtual
         interface with invalid destination IP address."
    ::= { tmnxOspfVirtIfStatsEntry 19 }

tmnxOspfVirtIfBadNeighbors OBJECT-TYPE
    SYNTAX      Counter32
    MAX-ACCESS  read-only
    STATUS      current
    DESCRIPTION
        "The value of tmnxOspfVirtIfBadNeighbors indicates the total
         number of OSPF packets received where the neighbor information
         does not match the configuration this router has
         for the neighbor."
    ::= { tmnxOspfVirtIfStatsEntry 20 }

tmnxOspfVirtIfBadPacketTypes OBJECT-TYPE
    SYNTAX      Counter32
    MAX-ACCESS  read-only
    STATUS      current
    DESCRIPTION
        "The value of tmnxOspfVirtIfBadPacketTypes indicates the total
         number of OSPF packets received on this virtual interface with 
         invalid OSPF packet types."
    ::= { tmnxOspfVirtIfStatsEntry 21 }

tmnxOspfVirtIfLastEventTime OBJECT-TYPE
    SYNTAX      TimeStamp
    MAX-ACCESS  read-only
    STATUS      current
    DESCRIPTION
        "The value of tmnxOspfVirtIfLastEventTime indicates the value of
         sysUpTime when an event was last associated with this OSPF
         virtual interface."
    ::= { tmnxOspfVirtIfStatsEntry 22 }

tmnxOspfVirtIfBadLengths OBJECT-TYPE
    SYNTAX      Counter32
    MAX-ACCESS  read-only
    STATUS      current
    DESCRIPTION
        "The value of tmnxOspfVirtIfBadLengths indicates the total number
         of OSPF packets received on this virtual interface with a total
         length not equal to the length given in the packet itself since
         tmnxOspfAdminState was last set to 'enabled'."
    ::= { tmnxOspfVirtIfStatsEntry 23 }

tmnxOspfVirtIfBadHelloIntervls OBJECT-TYPE
    SYNTAX      Counter32
    MAX-ACCESS  read-only
    STATUS      current
    DESCRIPTION
        "The value of tmnxOspfVirtIfBadHelloIntervls indicates the total
         number  of OSPF packets received where the hello interval given
         in packet was not equal to that configured on this virtual
         interface since tmnxOspfAdminState was last set to 'enabled'."
    ::= { tmnxOspfVirtIfStatsEntry 24 }

tmnxOspfVirtIfBadDeadIntervals OBJECT-TYPE
    SYNTAX      Counter32
    MAX-ACCESS  read-only
    STATUS      current
    DESCRIPTION
        "The value of tmnxOspfVirtIfBadDeadIntervals indicates the total
         number of OSPF packets received where the dead interval given in
         the packet was not equal to that configured on this virtual
         interface since tmnxOspfAdminState was last set to 'enabled'."
    ::= { tmnxOspfVirtIfStatsEntry 25 }

tmnxOspfVirtIfBadOptions OBJECT-TYPE
    SYNTAX      Counter32
    MAX-ACCESS  read-only
    STATUS      current
    DESCRIPTION
        "The value of tmnxOspfVirtIfBadOptions indicates the total number
         of OSPF packets received with an option that does not match those
         configured for this virtual interface or transit-area since
         tmnxOspfAdminState was last set to 'enabled'."
    ::= { tmnxOspfVirtIfStatsEntry 26 }

tmnxOspfVirtIfRxBadChecksums OBJECT-TYPE
    SYNTAX      Counter32
    MAX-ACCESS  read-only
    STATUS      current
    DESCRIPTION
        "The value of tmnxOspfVirtIfRxBadChecksums indicates the count of
         LSAs received with bad checksums."
    ::= { tmnxOspfVirtIfStatsEntry 27 }

tmnxOspfVirtIfBadAuthTypes OBJECT-TYPE
    SYNTAX      Counter32
    MAX-ACCESS  read-only
    STATUS      current
    DESCRIPTION
        "The value of tmnxOspfVirtIfBadAuthTypes indicates the total 
         number of OSPF packets received on this virtual
         interface with invalid authentication types."
    ::= { tmnxOspfVirtIfStatsEntry 28 }

tmnxOspfVirtIfAuthFailures OBJECT-TYPE
    SYNTAX      Counter32
    MAX-ACCESS  read-only
    STATUS      current
    DESCRIPTION
        "The value of tmnxOspfVirtIfAuthFailures indicates the total 
         number of OSPF packets received on this virtual
         interface with invalid authentication keys."
    ::= { tmnxOspfVirtIfStatsEntry 29 }


    -- OSPF Neighbor Table 
    -- 
    -- The OSPF Neighbor Table describes all neighbors in 
    -- the locality of the subject router. 
 
tmnxOspfNbrTable OBJECT-TYPE 
    SYNTAX      SEQUENCE OF TmnxOspfNbrEntry 
    MAX-ACCESS  not-accessible 
    STATUS      obsolete
    DESCRIPTION 
        "The tmnxOspfNbrTable contains information about non-virtual 
         neighbors.

         This table is obsoleted in release 9.0. It is replaced with
         tmnxOspfNgNbrTable." 
    REFERENCE 
        "OSPF Version 2, Section 10 The Neighbor Data 
         Structure" 
    ::= { tmnxOspfObjects 16 } 
 
tmnxOspfNbrEntry OBJECT-TYPE 
    SYNTAX          TmnxOspfNbrEntry 
    MAX-ACCESS      not-accessible 
    STATUS          obsolete
    DESCRIPTION 
        "The tmnxOspfNbrEntry contains information regarding a single 
         non-virtual neighbor." 
    REFERENCE 
        "OSPF Version 2, Section 10 The Neighbor Data 
         Structure" 
    INDEX       {   vRtrID,
                    tmnxOspfVersion,
                    tmnxOspfInstance,
                    tmnxOspfNbrIfIndex, 
                    tmnxOspfNbrIfInstId, 
                    tmnxOspfNbrRtrId
                } 
    ::= { tmnxOspfNbrTable 1 } 
 
TmnxOspfNbrEntry ::= SEQUENCE { 
        tmnxOspfNbrIfIndex              InterfaceIndex, 
        tmnxOspfNbrIfInstId             TmnxOspfIfInstIdTc, 
        tmnxOspfNbrRtrId                TmnxOspfRouterIdTc, 
        tmnxOspfNbrAddressType          InetAddressType, 
        tmnxOspfNbrAddress              InetAddress,             
        tmnxOspfNbrOptions              Integer32, 
        tmnxOspfNbrPriority             DesignatedRouterPriority, 
        tmnxOspfNbrState                INTEGER, 
        tmnxOspfNbrHelloSuppressed      TruthValue, 
        tmnxOspfNbrIfId                 InterfaceIndexOrZero, 
        tmnxOspfNbrRestartHelperStatus  INTEGER,  
        tmnxOspfNbrRestartHelperAge     TmnxOspfUpToRefreshIntervalTc,  
        tmnxOspfNbrRestartHelperExitRc  INTEGER,
        tmnxOspfNbrUpTime               TimeInterval,
        tmnxOspfNbrLastEventTime        TimeStamp,
        tmnxOspfNbrDeadTimeOutstanding  Unsigned32,
        tmnxOspfNbrLastRestartTime      TimeStamp,
        tmnxOspfNbrRestartReason        TmnxOspfRestartReasonTc,
        tmnxOspfNbrBfdTracking          TruthValue,
        tmnxOspfNbrDrId                 TmnxOspfRouterIdTc,
        tmnxOspfNbrBdrId                TmnxOspfRouterIdTc
    } 

tmnxOspfNbrIfIndex OBJECT-TYPE 
    SYNTAX      InterfaceIndex 
    MAX-ACCESS  not-accessible 
    STATUS      obsolete
    DESCRIPTION 
        "The value of tmnxOspfNbrIfIndex specifies the local link ID of 
         the link over which the neighbor can be reached." 
    ::= { tmnxOspfNbrEntry 1 } 
 
tmnxOspfNbrIfInstId OBJECT-TYPE 
    SYNTAX      TmnxOspfIfInstIdTc 
    MAX-ACCESS  not-accessible 
    STATUS      obsolete
    DESCRIPTION 
        "The value of tmnxOspfNbrIfInstId specifies the interface instance 
         over which the neighbor can be reached.  This ID has local link 
         significance only." 
    ::= { tmnxOspfNbrEntry 2 } 
 
tmnxOspfNbrRtrId OBJECT-TYPE 
    SYNTAX      TmnxOspfRouterIdTc 
    MAX-ACCESS  not-accessible 
    STATUS      obsolete
    DESCRIPTION 
        "The value of tmnxOspfNbrRtrId specifies a 32-bit integer uniquely 
         identifying the neighboring router in the Autonomous System." 
    ::= { tmnxOspfNbrEntry 3 } 
 
tmnxOspfNbrAddressType OBJECT-TYPE 
    SYNTAX      InetAddressType 
    MAX-ACCESS  read-only 
    STATUS      obsolete
    DESCRIPTION 
        "The value of tmnxOspfNbrAddressType indicates the address type of 
         tmnxOspfNbrAddress. For addresses of IPv6 type only addresses 
         with zone index are expected." 
    ::= { tmnxOspfNbrEntry 4 } 
 
tmnxOspfNbrAddress OBJECT-TYPE 
    SYNTAX      InetAddress (SIZE (4|20)) 
    MAX-ACCESS  read-only 
    STATUS      obsolete
    DESCRIPTION 
        "The value of tmnxOspfNbrAddress indicates the IP address of the 
         neighbor associated with the local link." 
    ::= { tmnxOspfNbrEntry 5 } 
 
tmnxOspfNbrOptions OBJECT-TYPE 
    SYNTAX      Integer32 
    MAX-ACCESS  read-only 
    STATUS      obsolete
    DESCRIPTION 
        "The value of tmnxOspfNbrOptions indicates a Bit Mask corresponding 
         to the neighbor's options field." 
    REFERENCE 
        "OSPF Version 3, Appendix A.2 the Options field" 
    ::= { tmnxOspfNbrEntry 6 } 
 
tmnxOspfNbrPriority OBJECT-TYPE 
    SYNTAX      DesignatedRouterPriority 
    MAX-ACCESS  read-only 
    STATUS      obsolete
    DESCRIPTION 
        "The value of tmnxOspfNbrPriority indicates the priority of this 
         neighbor in the designated router election algorithm.  The value 
         0 signifies that the neighbor is not eligible to become the 
         designated router on this particular network." 
    ::= { tmnxOspfNbrEntry 7 } 
 
tmnxOspfNbrState OBJECT-TYPE 
    SYNTAX      INTEGER { 
                    down            (1), 
                    attempt         (2), 
                    init            (3), 
                    twoWay          (4), 
                    exchangeStart   (5), 
                    exchange        (6), 
                    loading         (7), 
                    full            (8) 
                } 
    MAX-ACCESS  read-only 
    STATUS      obsolete
    DESCRIPTION 
        "The value of tmnxOspfNbrState indicates the State of the 
         relationship with this Neighbor." 
    REFERENCE 
        "OSPF Version 2, Section 10.1 Neighbor States" 
    ::= { tmnxOspfNbrEntry 8 } 
 
tmnxOspfNbrHelloSuppressed OBJECT-TYPE 
    SYNTAX      TruthValue 
    MAX-ACCESS  read-only 
    STATUS      obsolete
    DESCRIPTION 
        "The value of tmnxOspfNbrHelloSuppressed indicates whether Hellos 
         are being suppressed to the neighbor." 
    ::= { tmnxOspfNbrEntry 9 } 
 
tmnxOspfNbrIfId OBJECT-TYPE 
    SYNTAX      InterfaceIndexOrZero 
    MAX-ACCESS  read-only 
    STATUS      obsolete
    DESCRIPTION 
        "The value of tmnxOspfNbrIfId indicates the interface ID that the 
         neighbor advertises in its Hello Packets on this link, that is, the 
         neighbor's local interface index." 
    ::= { tmnxOspfNbrEntry 10 } 
 
tmnxOspfNbrRestartHelperStatus OBJECT-TYPE  
    SYNTAX      INTEGER { 
                    notHelping (1),  
                    helping (2)  
                }  
    MAX-ACCESS  read-only  
    STATUS      obsolete
    DESCRIPTION  
        "The value of tmnxOspfNbrRestartHelperStatus indicates whether 
         the router is acting as a Graceful restart helper for the neighbor."  
    ::= { tmnxOspfNbrEntry 11 }  
        
tmnxOspfNbrRestartHelperAge OBJECT-TYPE  
    SYNTAX      TmnxOspfUpToRefreshIntervalTc 
    UNITS       "seconds"  
    MAX-ACCESS  read-only  
    STATUS      obsolete
    DESCRIPTION  
        "The value of tmnxOspfNbrRestartHelperAge indicates the remaining 
         time in the current OSPF Graceful restart interval, if the router 
         is acting as a restart helper for the neighbor."  
    ::= { tmnxOspfNbrEntry 12 }  
        
tmnxOspfNbrRestartHelperExitRc OBJECT-TYPE  
    SYNTAX      INTEGER {
                    none (1), 
                    inProgress (2),  
                    completed (3),  
                    timedOut (4),  
                    topologyChanged (5) 
                }  
    MAX-ACCESS  read-only  
    STATUS      obsolete
    DESCRIPTION  
        "The value of tmnxOspfNbrRestartHelperExitRc indicates the outcome 
         of the last attempt at acting as a Graceful restart helper for the 
         neighbor. 
    
              none             No restart has yet been attempted. 
              inProgress       A restart attempt is currently underway. 
              completed        The last restart completed successfully. 
              timedOut         The last restart timed out. 
              topologyChanged  The last restart was aborted due to 
                               a topology change."  
    ::= { tmnxOspfNbrEntry 13 } 

tmnxOspfNbrUpTime OBJECT-TYPE
    SYNTAX      TimeInterval
    MAX-ACCESS  read-only
    STATUS      obsolete
    DESCRIPTION
        "The value of tmnxOspfNbrUpTime indicates the uninterrupted time,
         in hundredths of seconds, the adjacency to this neighbour
         has been up."
    ::= { tmnxOspfNbrEntry 14 }

tmnxOspfNbrLastEventTime OBJECT-TYPE
    SYNTAX      TimeStamp
    MAX-ACCESS  read-only
    STATUS      obsolete
    DESCRIPTION
        "The value of tmnxOspfNbrLastEventTime indicates the value of
         sysUpTime when the last event occurred that affected the adjacency
         to the neighbour."
    ::= { tmnxOspfNbrEntry 15 }

tmnxOspfNbrDeadTimeOutstanding OBJECT-TYPE
    SYNTAX      Unsigned32 (0..'7FFFFFFF'h)
    UNITS       "seconds"
    MAX-ACCESS  read-only
    STATUS      obsolete
    DESCRIPTION
        "The value of tmnxOspfNbrDeadTimeOutstanding indicates the amount
         of time in seconds until the  dead-router interval expires. Normally,
         this value should not be significantly smaller than the configured
         dead router interval minus one hello interval."
    ::= { tmnxOspfNbrEntry 16 }

tmnxOspfNbrLastRestartTime OBJECT-TYPE
    SYNTAX      TimeStamp
    MAX-ACCESS  read-only
    STATUS      obsolete
    DESCRIPTION
        "The value of tmnxOspfNbrLastRestartTime indicates the last time the 
         neighbor attempted restart."
    ::= { tmnxOspfNbrEntry 17 } 

tmnxOspfNbrRestartReason OBJECT-TYPE
    SYNTAX      TmnxOspfRestartReasonTc
    MAX-ACCESS  read-only
    STATUS      obsolete
    DESCRIPTION
        "The value of tmnxOspfNbrRestartReason indicates the OSPF 
         neighbor's graceful restart reason." 
    ::= { tmnxOspfNbrEntry 18 } 

tmnxOspfNbrBfdTracking OBJECT-TYPE
    SYNTAX      TruthValue
    MAX-ACCESS  read-only
    STATUS      obsolete
    DESCRIPTION
        "The value of tmnxOspfNbrBfdTracking indicates whether a BFD
        session is being maintained to track the forwarding path to
        this neighbor or not."
    ::= { tmnxOspfNbrEntry 19 } 

tmnxOspfNbrDrId OBJECT-TYPE 
    SYNTAX      TmnxOspfRouterIdTc 
    MAX-ACCESS  read-only 
    STATUS      obsolete
    DESCRIPTION 
        "The value of tmnxOspfNbrDrId indicates the DR value advertised 
         in the HELLO packets received from the OSPF neighbor.
         If it is not a broadcast interface tmnxOspfNbrDrId will be zero."
    ::= { tmnxOspfNbrEntry 20 } 

tmnxOspfNbrBdrId  OBJECT-TYPE 
    SYNTAX      TmnxOspfRouterIdTc 
    MAX-ACCESS  read-only 
    STATUS      obsolete
    DESCRIPTION 
        "The value of tmnxOspfNbrBdrId indicates the BDR value advertised
         in the HELLO packets received from the OSPF neighbor.
         If it is not a broadcast interface tmnxOspfNbrBdrId will be zero."
    ::= { tmnxOspfNbrEntry 21 } 

-- 
--  Augmentation of the tmnxOspfNbrTable.
--  Use of AUGMENTS clause implies a one-to-one dependent relationship 
--  between the base table, tmnxOspfNbrTable, and the augmenting table, 
--  tmnxOspfNbrStatsTable.
--
--  This in effect extends the tmnxOspfNbrTable with additional columns.  
--  Creation (or deletion) of a row in the tmnxOspfNbrTable results in 
--  the same fate for the row in the tmnxOspfNbrStatsTable.
-- 
tmnxOspfNbrStatsTable OBJECT-TYPE
    SYNTAX      SEQUENCE OF TmnxOspfNbrStatsEntry
    MAX-ACCESS  not-accessible
    STATUS      obsolete
    DESCRIPTION
        "The tmnxOspfNbrStatsTable provides an extension of the 
         tmnxOspfNbrTable for statistics for an OSPF neighbor.

         This table is obsoleted in release 9.0. It is replaced with
         tmnxOspfNgNbrStatsTable."
    ::= { tmnxOspfObjects 17 }

tmnxOspfNbrStatsEntry OBJECT-TYPE
    SYNTAX      TmnxOspfNbrStatsEntry
    MAX-ACCESS  not-accessible
    STATUS      obsolete
    DESCRIPTION
        "Each row entry in the tmnxOspfNbrStatsTable represents 
         additional columns for statistics for an OSPF neighbor."
    AUGMENTS { tmnxOspfNbrEntry }
   ::= { tmnxOspfNbrStatsTable 1 }

TmnxOspfNbrStatsEntry ::=
    SEQUENCE {
        tmnxOspfNbrEvents               Counter32, 
        tmnxOspfNbrLsRetransQLen        Gauge32, 
        tmnxOspfNbrBadNbrStates         Counter32,
        tmnxOspfNbrLsaInstallFailed     Counter32,
        tmnxOspfNbrBadSeqNums           Counter32,
        tmnxOspfNbrBadMTUs              Counter32,
        tmnxOspfNbrBadPackets           Counter32,
        tmnxOspfNbrLsaNotInLsdbs        Counter32,
        tmnxOspfNbrOptionMismatches     Counter32,
        tmnxOspfNbrDuplicates           Counter32,
        tmnxOspfNbrNumRestarts          Counter32
    }

tmnxOspfNbrEvents OBJECT-TYPE 
    SYNTAX      Counter32 
    MAX-ACCESS  read-only 
    STATUS      obsolete
    DESCRIPTION 
        "The value of tmnxOspfNbrEvents indicates the number of times 
         this neighbor relationship has changed state, or an error has 
         occurred." 
    ::= { tmnxOspfNbrStatsEntry 1 } 
 
tmnxOspfNbrLsRetransQLen OBJECT-TYPE 
    SYNTAX      Gauge32 
    MAX-ACCESS  read-only 
    STATUS      obsolete
    DESCRIPTION 
        "The value of tmnxOspfNbrLsRetransQLen indicates the current 
         length of the retransmission queue." 
    ::= { tmnxOspfNbrStatsEntry 2 } 
 
tmnxOspfNbrBadNbrStates OBJECT-TYPE
    SYNTAX      Counter32
    MAX-ACCESS  read-only
    STATUS      obsolete
    DESCRIPTION
        "The value of tmnxOspfNbrBadNbrStates indicates the total number
         of OSPF packets received when the neighbor state was not
         expecting to receive this packet type since tmnxOspfAdminState
         was last set to 'enabled'."
    ::= { tmnxOspfNbrStatsEntry 3 }

tmnxOspfNbrLsaInstallFailed OBJECT-TYPE
    SYNTAX      Counter32
    MAX-ACCESS  read-only
    STATUS      obsolete
    DESCRIPTION
        "The value of tmnxOspfNbrLsaInstallFailed indicates the total number
         of times an LSA could not be installed into the LSDB due to
         a resource allocation issue since tmnxOspfAdminState was last set
         to 'enabled'."
    ::= { tmnxOspfNbrStatsEntry 4 }

tmnxOspfNbrBadSeqNums OBJECT-TYPE
    SYNTAX      Counter32
    MAX-ACCESS  read-only
    STATUS      obsolete
    DESCRIPTION
        "The value of tmnxOspfNbrBadSeqNums indicates the total number
         of times when a database description packet was received with a
         sequence number mismatch since tmnxOspfAdminState was last
         set to 'enabled'."
    ::= { tmnxOspfNbrStatsEntry 5 }

tmnxOspfNbrBadMTUs OBJECT-TYPE
    SYNTAX      Counter32
    MAX-ACCESS  read-only
    STATUS      obsolete
    DESCRIPTION
        "The value of tmnxOspfNbrBadMTUs indicates the total number of times
         when the MTU in a received database description packet was
         larger than the MTU of the receiving interface since
         tmnxOspfAdminState was last set to 'enabled'."
    ::= { tmnxOspfNbrStatsEntry 6 }

tmnxOspfNbrBadPackets OBJECT-TYPE
    SYNTAX      Counter32
    MAX-ACCESS  read-only
    STATUS      obsolete
    DESCRIPTION
        "The value of tmnxOspfNbrBadPackets indicates the total number
         of times when an LS update was received with an illegal LS type or an
         option mismatch since tmnxOspfAdminState was last set to 'enabled'."
    ::= { tmnxOspfNbrStatsEntry 7 }

tmnxOspfNbrLsaNotInLsdbs OBJECT-TYPE
    SYNTAX      Counter32
    MAX-ACCESS  read-only
    STATUS      obsolete
    DESCRIPTION
        "The value of tmnxOspfNbrLsaNotInLsdbs indicates the total number of
         times when an LS request was received for an LSA not installed in the
         LSDB of this router since tmnxOspfAdminState was last set to 
         'enabled'."
    ::= { tmnxOspfNbrStatsEntry 8 }

tmnxOspfNbrOptionMismatches OBJECT-TYPE
    SYNTAX      Counter32
    MAX-ACCESS  read-only
    STATUS      obsolete
    DESCRIPTION
        "The value of tmnxOspfNbrOptionMismatches indicates the total
         number of times when a LS update was received with an option mismatch
         since tmnxOspfAdminState was last set to 'enabled'."
    ::= { tmnxOspfNbrStatsEntry 9 }

tmnxOspfNbrDuplicates OBJECT-TYPE
    SYNTAX      Counter32
    MAX-ACCESS  read-only
    STATUS      obsolete
    DESCRIPTION
        "The value of tmnxOspfNbrDuplicates indicates the total number
         of times when a duplicate database description packet was received
         during the Exchange state since tmnxOspfAdminState was last set
         to 'enabled'."
    ::= { tmnxOspfNbrStatsEntry 10 }

tmnxOspfNbrNumRestarts OBJECT-TYPE
    SYNTAX      Counter32
    MAX-ACCESS  read-only
    STATUS      obsolete
    DESCRIPTION
        "The value of tmnxOspfNbrNumRestarts indicates the number of times 
         the neighbor has attempted restart."
    ::= { tmnxOspfNbrStatsEntry 11 } 


 
    -- OSPF Configured Neighbor Table 
 
    -- The OSPF Configured Neighbor Table describes all configured 
    -- neighbors and neighbors dynamically discovered by 
    -- lower-level protocols such as Inverse Neighbor Discovery. 
 
tmnxOspfCfgNbrTable OBJECT-TYPE 
    SYNTAX      SEQUENCE OF TmnxOspfCfgNbrEntry 
    MAX-ACCESS  not-accessible 
    STATUS      current 
    DESCRIPTION 
        "The tmnxOspfCfgNbrTable contains information about configured 
         non-virtual neighbors and neighbors dynamically discovered 
         by lower-level protocols such as Inverse Neighbor Discovery." 
    REFERENCE 
        "OSPF Version 2, Section 10 The Neighbor Data Structure" 
    ::= { tmnxOspfObjects 18 } 
 
tmnxOspfCfgNbrEntry OBJECT-TYPE 
    SYNTAX      TmnxOspfCfgNbrEntry 
    MAX-ACCESS  not-accessible 
    STATUS      current 
    DESCRIPTION 
        "The tmnxOspfCfgNbrEntry contains information regarding a single 
         configured neighbor or neighbor discovered by lower-level 
         protocols such as Inverse Neighbor Discovery." 
    REFERENCE 
        "OSPF Version 2, Section 10 The Neighbor Data Structure" 
    INDEX       {   vRtrID,
                    tmnxOspfVersion,
                    tmnxOspfInstance,
                    tmnxOspfCfgNbrIfIndex, 
                    tmnxOspfCfgNbrIfInstId, 
                    tmnxOspfCfgNbrAddressType, 
                    tmnxOspfCfgNbrAddress
                } 
    ::= { tmnxOspfCfgNbrTable 1 } 
 
TmnxOspfCfgNbrEntry ::= SEQUENCE { 
        tmnxOspfCfgNbrIfIndex       InterfaceIndex, 
        tmnxOspfCfgNbrIfInstId      TmnxOspfIfInstIdTc, 
        tmnxOspfCfgNbrAddressType   InetAddressType, 
        tmnxOspfCfgNbrAddress       InetAddress, 
        tmnxOspfCfgNbrStatus        RowStatus, 
        tmnxOspfCfgNbrStorageType   StorageType,
        tmnxOspfCfgNbrLastChanged   TimeStamp, 
        tmnxOspfCfgNbrPriority      DesignatedRouterPriority, 
        tmnxOspfCfgNbrRtrId         TmnxOspfRouterIdTc, 
        tmnxOspfCfgNbrState         INTEGER 
    } 
 
tmnxOspfCfgNbrIfIndex OBJECT-TYPE 
    SYNTAX      InterfaceIndex 
    MAX-ACCESS  not-accessible 
    STATUS      current 
    DESCRIPTION 
        "The value of tmnxOspfCfgNbrIfIndex specifies the local link ID of 
         the link over which the neighbor can be reached." 
    ::= { tmnxOspfCfgNbrEntry 1 } 
 
tmnxOspfCfgNbrIfInstId OBJECT-TYPE 
    SYNTAX      TmnxOspfIfInstIdTc 
    MAX-ACCESS  not-accessible 
    STATUS      current 
    DESCRIPTION 
        "The value of tmnxOspfCfgNbrIfInstId specifies the interface 
         instance over which the neighbor can be reached.  This ID has 
         local link significance only." 
    ::= { tmnxOspfCfgNbrEntry 2 } 
 
tmnxOspfCfgNbrAddressType OBJECT-TYPE 
    SYNTAX      InetAddressType 
    MAX-ACCESS  not-accessible 
    STATUS      current 
    DESCRIPTION 
        "The value of tmnxOspfCfgNbrAddressType specifies the address type 
         of tmnxOspfCfgNbrAddress.  For IPv6 type addresses only addresses 
         with zone index are expected." 
    ::= { tmnxOspfCfgNbrEntry 3 } 
 
tmnxOspfCfgNbrAddress OBJECT-TYPE 
    SYNTAX      InetAddress (SIZE (4|20)) 
    MAX-ACCESS  not-accessible 
    STATUS      current 
    DESCRIPTION 
        "The value of tmnxOspfCfgNbrAddress specifies the IP address of 
        the neighbor associated with the local link." 
    ::= { tmnxOspfCfgNbrEntry 4 } 
 
tmnxOspfCfgNbrStatus OBJECT-TYPE 
    SYNTAX      RowStatus 
    MAX-ACCESS  read-create 
    STATUS      current 
    DESCRIPTION 
        "The value of tmnxOspfCfgNbrStatus controls creation and deletion
         of row entries in this table." 
    ::= { tmnxOspfCfgNbrEntry 5 } 

tmnxOspfCfgNbrStorageType OBJECT-TYPE 
    SYNTAX      StorageType 
    MAX-ACCESS  read-create 
    STATUS      current 
    DESCRIPTION 
        "The value of tmnxOspfCfgNbrStorageType specifies the storage type 
         for this conceptual row.  Conceptual rows having the value 
         'permanent' need not allow write-access to any columnar objects 
         in the row.  Manually configured entries will have a storage type 
         of nonVolatile while entries dynamically created as a result of a 
         lower-level protocol such as Inverse Neighbor Discovery will have a 
         storage type of volatile." 
    DEFVAL { nonVolatile } 
    ::= { tmnxOspfCfgNbrEntry 6 } 
 
tmnxOspfCfgNbrLastChanged  OBJECT-TYPE
    SYNTAX      TimeStamp
    MAX-ACCESS  read-only
    STATUS      current
    DESCRIPTION
        "The value of tmnxOspfCfgNbrLastChanged indicates the sysUpTime
         when a configurable object in this row was last modified."
    ::= { tmnxOspfCfgNbrEntry 7 } 

tmnxOspfCfgNbrPriority OBJECT-TYPE 
    SYNTAX      DesignatedRouterPriority 
    MAX-ACCESS  read-create 
    STATUS      current 
    DESCRIPTION 
        "The value of tmnxOspfCfgNbrPriority specifies the priority of 
         this neighbor in the designated router election algorithm. The 
         value 0 signifies that the neighbor is not eligible to become the 
         designated router on this particular network." 
    DEFVAL { 1 } 
    ::= { tmnxOspfCfgNbrEntry 8 } 
 
tmnxOspfCfgNbrRtrId OBJECT-TYPE 
    SYNTAX      TmnxOspfRouterIdTc 
    MAX-ACCESS  read-only 
    STATUS      current 
    DESCRIPTION 
        "The value of tmnxOspfCfgNbrRtrId indicates a 32-bit integer 
         uniquely identifying the neighboring router in the Autonomous 
         System. A value of 0 is returned until a Hello is received 
         from the configured neighbor." 
    ::= { tmnxOspfCfgNbrEntry 9 } 
 
tmnxOspfCfgNbrState OBJECT-TYPE 
    SYNTAX      INTEGER { 
                    down            (1), 
                    attempt         (2), 
                    init            (3), 
                    twoWay          (4), 
                    exchangeStart   (5), 
                    exchange        (6), 
                    loading         (7), 
                    full            (8) 
                } 
    MAX-ACCESS  read-only 
    STATUS      current 
    DESCRIPTION 
        "The value of tmnxOspfCfgNbrState indicates the State of the 
         relationship with this Neighbor." 
    REFERENCE 
        "OSPF Version 2, Section 10.1 Neighbor States" 
    ::= { tmnxOspfCfgNbrEntry 10 } 
    
     
 
    -- OSPF Virtual Neighbor Table 
 
    -- This table describes all virtual neighbors. 
    -- Since Virtual Links are configured in the 
    -- virtual interface table, this table is read-only. 
 
tmnxOspfVirtNbrTable OBJECT-TYPE 
    SYNTAX          SEQUENCE OF TmnxOspfVirtNbrEntry 
    MAX-ACCESS      not-accessible 
    STATUS          current 
    DESCRIPTION 
        "The tmnxOspfVirtNbrTable contains virtual neighbors information." 
    REFERENCE 
        "OSPF Version 2, Section 15 Virtual Links" 
    ::= { tmnxOspfObjects 19 } 
 
tmnxOspfVirtNbrEntry OBJECT-TYPE 
    SYNTAX          TmnxOspfVirtNbrEntry 
    MAX-ACCESS      not-accessible 
    STATUS          current 
    DESCRIPTION 
        "The tmnxOspfVirtNbrEntry contains information for a specific
         Virtual neighbor." 
    INDEX       {   vRtrID,
                    tmnxOspfVersion,
                    tmnxOspfInstance,
                    tmnxOspfVirtNbrArea, 
                    tmnxOspfVirtNbrRtrId
                } 
    ::= { tmnxOspfVirtNbrTable 1 } 
 
TmnxOspfVirtNbrEntry ::= SEQUENCE { 
        tmnxOspfVirtNbrArea                 TmnxOspfAreaIdTc, 
        tmnxOspfVirtNbrRtrId                TmnxOspfRouterIdTc, 
        tmnxOspfVirtNbrIfIndex              InterfaceIndex, 
        tmnxOspfVirtNbrIfInstId             TmnxOspfIfInstIdTc, 
        tmnxOspfVirtNbrAddressType          InetAddressType, 
        tmnxOspfVirtNbrAddress              InetAddress, 
        tmnxOspfVirtNbrOptions              Integer32, 
        tmnxOspfVirtNbrState                INTEGER, 
        tmnxOspfVirtNbrHelloSuppressed      TruthValue, 
        tmnxOspfVirtNbrIfId                 InterfaceIndexOrZero, 
        tmnxOspfVirtNbrRestartHelperStatus  INTEGER,  
        tmnxOspfVirtNbrRestartHelperAge     TmnxOspfUpToRefreshIntervalTc,  
        tmnxOspfVirtNbrRestartHelperExitRc  INTEGER, 
        tmnxOspfVirtNbrUpTime               TimeInterval,
        tmnxOspfVirtNbrLastEventTime        TimeStamp,
        tmnxOspfVirtNbrDeadTmeOutstng       Unsigned32,
        tmnxOspfVirtNbrLastRestartTime      TimeStamp,
        tmnxOspfVirtNbrRestartReason        TmnxOspfRestartReasonTc
    } 
 
tmnxOspfVirtNbrArea OBJECT-TYPE 
    SYNTAX      TmnxOspfAreaIdTc 
    MAX-ACCESS  not-accessible 
    STATUS      current 
    DESCRIPTION 
        "The value of tmnxOspfVirtNbrArea specifies the Transit Area 
         Identifier." 
    ::= { tmnxOspfVirtNbrEntry 1 } 
 
tmnxOspfVirtNbrRtrId OBJECT-TYPE 
    SYNTAX      TmnxOspfRouterIdTc 
    MAX-ACCESS  not-accessible 
    STATUS      current 
    DESCRIPTION 
        "The value of tmnxOspfVirtNbrRtrId specifies a 32-bit integer 
         uniquely identifying the neighboring router in the Autonomous 
         System." 
::= { tmnxOspfVirtNbrEntry 2 } 
 
tmnxOspfVirtNbrIfIndex OBJECT-TYPE 
    SYNTAX      InterfaceIndex 
    MAX-ACCESS  read-only 
    STATUS      current 
    DESCRIPTION 
        "The value of tmnxOspfVirtNbrIfIndex indicates the local interface 
         ID for the virtual link over which the neighbor can be reached." 
    ::= { tmnxOspfVirtNbrEntry 3 } 
 
tmnxOspfVirtNbrIfInstId OBJECT-TYPE 
    SYNTAX      TmnxOspfIfInstIdTc 
    MAX-ACCESS  read-only 
    STATUS      current 
    DESCRIPTION 
        "The value of tmnxOspfVirtNbrIfInstId indicates the interface 
         instance for the virtual link over which the neighbor can be 
         reached." 
    ::= { tmnxOspfVirtNbrEntry 4 } 
 
tmnxOspfVirtNbrAddressType OBJECT-TYPE 
    SYNTAX      InetAddressType 
    MAX-ACCESS  read-only 
    STATUS      current 
    DESCRIPTION 
        "The value of tmnxOspfVirtNbrAddressType indicates the address 
         type of tmnxOspfVirtNbrAddress. For IPv6 address type only 
         addresses without zone index are expected." 
    ::= { tmnxOspfVirtNbrEntry 5 } 
 
tmnxOspfVirtNbrAddress OBJECT-TYPE 
    SYNTAX      InetAddress (SIZE (4|16))  
    MAX-ACCESS  read-only 
    STATUS      current 
    DESCRIPTION 
        "The value of tmnxOspfVirtNbrAddress indicates the IP address 
         advertised by this Virtual Neighbor. It must be a Global scope 
         address." 
    ::= { tmnxOspfVirtNbrEntry 6 } 
 
tmnxOspfVirtNbrOptions OBJECT-TYPE 
    SYNTAX      Integer32 
    MAX-ACCESS  read-only 
    STATUS      current 
    DESCRIPTION 
        "The value of tmnxOspfVirtNbrOptions indicates a Bit Mask 
         corresponding to the neighbor's options field." 
    REFERENCE 
        "OSPF Version 3, Appendix A.2 the Options field" 
    ::= { tmnxOspfVirtNbrEntry 7 } 
 
tmnxOspfVirtNbrState OBJECT-TYPE 
    SYNTAX      INTEGER { 
                    down            (1), 
                    attempt         (2), 
                    init            (3), 
                    twoWay          (4), 
                    exchangeStart   (5), 
                    exchange        (6), 
                    loading         (7), 
                    full            (8) 
                } 
    MAX-ACCESS  read-only 
    STATUS      current 
    DESCRIPTION 
        "The value of tmnxOspfVirtNbrState indicates the state of the 
         Virtual Neighbor Relationship." 
    ::= { tmnxOspfVirtNbrEntry 8 } 
 
tmnxOspfVirtNbrHelloSuppressed OBJECT-TYPE 
    SYNTAX      TruthValue 
    MAX-ACCESS  read-only 
    STATUS      current 
    DESCRIPTION 
        "The value of tmnxOspfVirtNbrHelloSuppressed indicates whether 
         Hellos are being suppressed to the neighbor" 
    ::= { tmnxOspfVirtNbrEntry 9 } 
 
tmnxOspfVirtNbrIfId OBJECT-TYPE 
    SYNTAX      InterfaceIndexOrZero 
    MAX-ACCESS  read-only 
    STATUS      current 
    DESCRIPTION 
        "The value of tmnxOspfVirtNbrIfId indicates the interface ID that 
         the neighbor advertises in its Hello Packets on this virtual link, 
         that is, the neighbor's local interface ID." 
    ::= { tmnxOspfVirtNbrEntry 10 } 
 
tmnxOspfVirtNbrRestartHelperStatus OBJECT-TYPE  
    SYNTAX      INTEGER { 
                    notHelping (1),  
                    helping (2)  
                }  
    MAX-ACCESS  read-only  
    STATUS      current  
    DESCRIPTION  
        "The value of tmnxOspfVirtNbrRestartHelperStatus indicates whether 
         the router is acting as a Graceful restart helper for the neighbor."  
    ::= { tmnxOspfVirtNbrEntry 11 }  
        
tmnxOspfVirtNbrRestartHelperAge OBJECT-TYPE  
    SYNTAX      TmnxOspfUpToRefreshIntervalTc 
    UNITS       "seconds"  
    MAX-ACCESS  read-only  
    STATUS      current  
    DESCRIPTION  
        "The value of tmnxOspfVirtNbrRestartHelperAge indicates the 
         remaining time in current OSPF Graceful restart interval, 
         if the router is acting as a restart helper for the neighbor."  
    ::= { tmnxOspfVirtNbrEntry 12 }  
        
tmnxOspfVirtNbrRestartHelperExitRc OBJECT-TYPE  
    SYNTAX      INTEGER { 
                    none (1),  
                    inProgress (2),  
                    completed (3),  
                    timedOut (4),  
                    topologyChanged (5)  
                }  
    MAX-ACCESS  read-only  
    STATUS      current  
    DESCRIPTION  
        "The value of tmnxOspfVirtNbrRestartHelperExitRc indicates the 
         outcome of the last attempt at acting as a Graceful restart 
         helper for the neighbor. 
    
              none             No restart has yet been attempted. 
              inProgress       A restart attempt is currently underway. 
              completed        The last restart completed successfully. 
              timedOut         The last restart timed out. 
              topologyChanged  The last restart was aborted due to 
                               a topology change."  
    ::= { tmnxOspfVirtNbrEntry 13 }

tmnxOspfVirtNbrUpTime OBJECT-TYPE
    SYNTAX      TimeInterval
    MAX-ACCESS  read-only
    STATUS      current
    DESCRIPTION
        "The value of tmnxOspfVirtNbrUpTime indicates the uninterrupted time,
         in hundredths of seconds, the adjacency to this virtual neighbour
         has been up."
    ::= { tmnxOspfVirtNbrEntry 14 }

tmnxOspfVirtNbrLastEventTime OBJECT-TYPE
    SYNTAX      TimeStamp
    MAX-ACCESS  read-only
    STATUS      current
    DESCRIPTION
        "The value of tmnxOspfVirtNbrLastEventTime indicates the value of
         sysUpTime when the last event occurred that affected the adjacency
         to the virtual neighbour."
    ::= { tmnxOspfVirtNbrEntry 15 }

tmnxOspfVirtNbrDeadTmeOutstng  OBJECT-TYPE
    SYNTAX      Unsigned32 (0..'7FFFFFFF'h)
    UNITS       "seconds"
    MAX-ACCESS  read-only
    STATUS      current
    DESCRIPTION
        "The value of tmnxOspfVirtNbrDeadTmeOutstng indicates the amount 
         of time in seconds until the dead-router interval expires.
         Normally, this value should not be significantly smaller than the
         configured dead router interval minus one hello interval."
    ::= { tmnxOspfVirtNbrEntry 16 }

tmnxOspfVirtNbrLastRestartTime OBJECT-TYPE
    SYNTAX      TimeStamp
    MAX-ACCESS  read-only
    STATUS      current
    DESCRIPTION
        "The value of tmnxOspfVirtNbrLastRestartTime indicates the 
        last time the neighbor attempted restart."
    ::= { tmnxOspfVirtNbrEntry 17 }

tmnxOspfVirtNbrRestartReason OBJECT-TYPE
    SYNTAX      TmnxOspfRestartReasonTc
    MAX-ACCESS  read-only
    STATUS      current
    DESCRIPTION
        "The value of tmnxOspfVirtNbrRestartReason indicates the OSPF 
         neighbor's graceful restart reason." 
    ::= { tmnxOspfVirtNbrEntry 18 } 
 
-- 
--  Augmentation of the tmnxOspfVirtNbrTable.
--  Use of AUGMENTS clause implies a one-to-one dependent relationship 
--  between the base table, tmnxOspfVirtNbrTable, and the augmenting table, 
--  tmnxOspfVirtNbrStatsTable.
--
--  This in effect extends the tmnxOspfVirtNbrTable with additional columns.  
--  Creation (or deletion) of a row in the tmnxOspfVirtNbrTable results in 
--  the same fate for the row in the tmnxOspfVirtNbrStatsTable.
-- 
tmnxOspfVirtNbrStatsTable OBJECT-TYPE
    SYNTAX      SEQUENCE OF TmnxOspfVirtNbrStatsEntry
    MAX-ACCESS  not-accessible
    STATUS      current
    DESCRIPTION
        "The tmnxOspfVirtNbrStatsTable provides an extension of the 
         tmnxOspfVirtNbrTable for statistics for an OSPF virtual neighbor."
    ::= { tmnxOspfObjects 20 }

tmnxOspfVirtNbrStatsEntry OBJECT-TYPE
    SYNTAX      TmnxOspfVirtNbrStatsEntry
    MAX-ACCESS  not-accessible
    STATUS      current
    DESCRIPTION
        "Each row entry in the tmnxOspfVirtNbrStatsTable represents 
         additional columns for statistics for an OSPF virtual neighbor."
    AUGMENTS { tmnxOspfVirtNbrEntry }
   ::= { tmnxOspfVirtNbrStatsTable 1 }

TmnxOspfVirtNbrStatsEntry ::=
    SEQUENCE {
        tmnxOspfVirtNbrEvents               Counter32, 
        tmnxOspfVirtNbrLsRetransQLen        Gauge32, 
        tmnxOspfVirtNbrBadNbrStates         Counter32,
        tmnxOspfVirtNbrLsaInstallFail       Counter32,
        tmnxOspfVirtNbrBadSeqNums           Counter32,
        tmnxOspfVirtNbrBadMTUs              Counter32,
        tmnxOspfVirtNbrBadPackets           Counter32,
        tmnxOspfVirtNbrLsaNotInLsdbs        Counter32,
        tmnxOspfVirtNbrOptionMismatch       Counter32,
        tmnxOspfVirtNbrDuplicates           Counter32,
        tmnxOspfVirtNbrNumRestarts          Counter32
    }

tmnxOspfVirtNbrEvents OBJECT-TYPE 
    SYNTAX      Counter32 
    MAX-ACCESS  read-only 
    STATUS      current 
    DESCRIPTION 
        "The value of tmnxOspfVirtNbrEvents indicates the number of times 
         this virtual link has changed its state, or an error has occurred." 
    ::= { tmnxOspfVirtNbrStatsEntry 1 } 
 
tmnxOspfVirtNbrLsRetransQLen OBJECT-TYPE 
    SYNTAX      Gauge32 
    MAX-ACCESS  read-only 
    STATUS      current 
    DESCRIPTION 
        "The value of tmnxOspfVirtNbrLsRetransQLen indicates the current 
         length of the retransmission queue." 
    ::= { tmnxOspfVirtNbrStatsEntry 2 } 
 
tmnxOspfVirtNbrBadNbrStates OBJECT-TYPE
    SYNTAX      Counter32
    MAX-ACCESS  read-only
    STATUS      current
    DESCRIPTION
        "The value of tmnxOspfVirtNbrBadNbrStates indicates the total
         number of OSPF packets received when the virtual neighbor state 
         was not expecting to receive this packet type since
         tmnxOspfAdminState was last set to 'enabled'."
    ::= { tmnxOspfVirtNbrStatsEntry 3 }

tmnxOspfVirtNbrLsaInstallFail OBJECT-TYPE
    SYNTAX      Counter32
    MAX-ACCESS  read-only
    STATUS      current
    DESCRIPTION
        "The value of tmnxOspfVirtNbrLsaInstallFail indicates the total
         number of times when an LSA could not be installed into the LSDB
         due to a resource allocation issue since tmnxOspfAdminState was 
         last set to 'enabled'."
    ::= { tmnxOspfVirtNbrStatsEntry 4 }

tmnxOspfVirtNbrBadSeqNums OBJECT-TYPE
    SYNTAX      Counter32
    MAX-ACCESS  read-only
    STATUS      current
    DESCRIPTION
        "The value of tmnxOspfVirtNbrBadSeqNums indicates the total number 
         of times when a database description packet was received with a
         sequence number mismatch since tmnxOspfAdminState was last set to
         'enabled'."
    ::= { tmnxOspfVirtNbrStatsEntry 5 }

tmnxOspfVirtNbrBadMTUs OBJECT-TYPE
    SYNTAX      Counter32
    MAX-ACCESS  read-only
    STATUS      current
    DESCRIPTION
        "The value of tmnxOspfVirtNbrBadMTUs indicates the total number
         of times when the MTU in a received database description packet
         was larger than the MTU of the receiving interface since
         tmnxOspfAdminState was last set to 'enabled'."
    ::= { tmnxOspfVirtNbrStatsEntry 6 }

tmnxOspfVirtNbrBadPackets OBJECT-TYPE
    SYNTAX      Counter32
    MAX-ACCESS  read-only
    STATUS      current
    DESCRIPTION
        "The value of tmnxOspfVirtNbrBadPackets indicates the total number of
         times when an LS update was received with an illegal LS type or
         an option mismatch since tmnxOspfAdminState was last set to 
         'enabled'."
    ::= { tmnxOspfVirtNbrStatsEntry 7 }

tmnxOspfVirtNbrLsaNotInLsdbs OBJECT-TYPE
    SYNTAX      Counter32
    MAX-ACCESS  read-only
    STATUS      current
    DESCRIPTION
        "The value of tmnxOspfVirtNbrLsaNotInLsdbs indicates the total
         number of times when an LS request was received for an LSA not
         installed in the LSDB of this router since tmnxOspfAdminState was
         last set to 'enabled'."
    ::= { tmnxOspfVirtNbrStatsEntry 8 }

tmnxOspfVirtNbrOptionMismatch OBJECT-TYPE
    SYNTAX      Counter32
    MAX-ACCESS  read-only
    STATUS      current
    DESCRIPTION
        "The value of tmnxOspfVirtNbrOptionMismatch indicates the total
         number of times when a LS update was received with an option mismatch
         since tmnxOspfAdminState was last set to 'enabled'."
    ::= { tmnxOspfVirtNbrStatsEntry 9 }

tmnxOspfVirtNbrDuplicates OBJECT-TYPE
    SYNTAX      Counter32
    MAX-ACCESS  read-only
    STATUS      current
    DESCRIPTION
        "The value of tmnxOspfVirtNbrDuplicates indicates the total number of
         times when a duplicate database description packet was received
         during the Exchange state since tmnxOspfAdminState was last set to
         'enabled'."
    ::= { tmnxOspfVirtNbrStatsEntry 10 }

tmnxOspfVirtNbrNumRestarts OBJECT-TYPE
    SYNTAX      Counter32
    MAX-ACCESS  read-only
    STATUS      current
    DESCRIPTION
        "The value of tmnxOspfVirtNbrNumRestarts indicates the number
         of times the virtual neighbor has attempted restart since 
         tmnxOspfAdminState was last set to 'enabled'."
    ::= { tmnxOspfVirtNbrStatsEntry 11 } 



    -- 
    -- The OSPF Area Aggregate Table 
    -- 
 
tmnxOspfAreaAggrTable OBJECT-TYPE 
    SYNTAX      SEQUENCE OF TmnxOspfAreaAggrEntry 
    MAX-ACCESS  not-accessible 
    STATUS      current 
    DESCRIPTION 
        "The tmnxOspfAreaAggrTable contains information about area
         aggregates defined by a range of IP prefixes specified by a 
         prefix/prefix length pair.  Note that if ranges are configured 
         such that one range subsumes another range the most specific 
         match is the preferred one." 
    ::= { tmnxOspfObjects 21 } 
 
tmnxOspfAreaAggrEntry OBJECT-TYPE 
    SYNTAX      TmnxOspfAreaAggrEntry 
    MAX-ACCESS  not-accessible 
    STATUS      current 
    DESCRIPTION 
        "The tmnxOspfAreaAggrEntry contains information about a specific
         range of IP prefixes specified by a prefix/prefix length pair. 
         Note that if ranges are configured such that one range subsumes 
         another range the most specific match is the preferred one." 
    REFERENCE 
        "OSPF Version 2, Appendix C.2  Area parameters" 
    INDEX       {   vRtrID,
                    tmnxOspfVersion,
                    tmnxOspfInstance,
                    tmnxOspfAreaAggrAreaID,  
                    tmnxOspfAreaAggrAreaLsdbType, 
                    tmnxOspfAreaAggrPrefixType, 
                    tmnxOspfAreaAggrPrefix, 
                    tmnxOspfAreaAggrPrefixLength
                } 
    ::= { tmnxOspfAreaAggrTable 1 } 
 
TmnxOspfAreaAggrEntry ::= SEQUENCE { 
        tmnxOspfAreaAggrAreaID          TmnxOspfAreaIdTc, 
        tmnxOspfAreaAggrAreaLsdbType    INTEGER, 
        tmnxOspfAreaAggrPrefixType      InetAddressType, 
        tmnxOspfAreaAggrPrefix          InetAddress, 
        tmnxOspfAreaAggrPrefixLength    InetAddressPrefixLength, 
        tmnxOspfAreaAggrStatus          RowStatus,
        tmnxOspfAreaAggrLastChanged     TimeStamp, 
        tmnxOspfAreaAggrEffect          INTEGER, 
        tmnxOspfAreaAggrRouteTag        Integer32 
} 
 
tmnxOspfAreaAggrAreaID OBJECT-TYPE 
    SYNTAX      TmnxOspfAreaIdTc 
    MAX-ACCESS  not-accessible 
    STATUS      current 
    DESCRIPTION 
        "The value of tmnxOspfAreaAggrAreaID specifies the Area the 
         Address Aggregate is to be found within." 
    REFERENCE 
        "OSPF Version 2, Appendix C.2 Area parameters" 
    ::= { tmnxOspfAreaAggrEntry 1 } 
 
tmnxOspfAreaAggrAreaLsdbType OBJECT-TYPE 
    SYNTAX      INTEGER { 
                    interAreaPrefixLsa(8195),
                    nssaExternalLsa(8199)
                } 
    MAX-ACCESS  not-accessible 
    STATUS      current 
    DESCRIPTION 
        "The value of tmnxOspfAreaAggrAreaLsdbType specifies the type of 
         the Address Aggregate.  This field specifies the Area Lsdb type 
         that this Address Aggregate applies to." 
    REFERENCE 
        "OSPF Version 2, Appendix A.4.1 The Link State 
         Advertisement header" 
    ::= { tmnxOspfAreaAggrEntry 2 } 
 
tmnxOspfAreaAggrPrefixType OBJECT-TYPE 
    SYNTAX      InetAddressType 
    MAX-ACCESS  not-accessible 
    STATUS      current 
    DESCRIPTION 
        "The tmnxOspfAreaAggrPrefixType specifies the prefix type of 
         tmnxOspfAreaAggrPrefix. For addresses of IPv6 type only addresses 
         without zone index are expected." 
    ::= { tmnxOspfAreaAggrEntry 3 } 
 
tmnxOspfAreaAggrPrefix OBJECT-TYPE 
    SYNTAX      InetAddress (SIZE (4|16)) 
    MAX-ACCESS  not-accessible 
    STATUS      current 
    DESCRIPTION 
        "The value of tmnxOspfAreaAggrPrefix specifies the IP Prefix." 
    REFERENCE 
        "OSPF Version 2, Appendix C.2 Area parameters" 
    ::= { tmnxOspfAreaAggrEntry 4 } 
 
tmnxOspfAreaAggrPrefixLength OBJECT-TYPE 
    SYNTAX      InetAddressPrefixLength (0..128) 
    UNITS       "bits" 
    MAX-ACCESS  not-accessible 
    STATUS      current 
    DESCRIPTION 
        "The value of tmnxOspfAreaAggrPrefixLength specifies the length of 
         the prefix (in bits).  An IPv6 prefix cannot be shorter than 
         3 bits.  The 0, 1, and 2 prefix lengths are only valid for IPv4 
         addresses." 
    REFERENCE 
        "OSPF Version 2, Appendix C.2 Area parameters" 
    ::= { tmnxOspfAreaAggrEntry 5 } 
 
tmnxOspfAreaAggrStatus OBJECT-TYPE 
    SYNTAX      RowStatus 
    MAX-ACCESS  read-create 
    STATUS      current 
    DESCRIPTION 
        "The value of tmnxOspfAreaAggrStatus controls the creation and
         deletion of row entries in this table." 
    ::= { tmnxOspfAreaAggrEntry 6 } 
 
tmnxOspfAreaAggrLastChanged  OBJECT-TYPE
    SYNTAX      TimeStamp
    MAX-ACCESS  read-only
    STATUS      current
    DESCRIPTION
        "The value of tmnxOspfAreaAggrLastChanged indicates the value of
         sysUpTime when a configurable object in this row was last modified."
    ::= { tmnxOspfAreaAggrEntry 7 } 

tmnxOspfAreaAggrEffect OBJECT-TYPE 
    SYNTAX      INTEGER { 
                    advertiseMatching(1), 
                    doNotAdvertiseMatching(2) 
                } 
    MAX-ACCESS  read-create 
    STATUS      current 
    DESCRIPTION 
        "The value of tmnxOspfAreaAggrEffect specifies the prefixes 
         subsumed by ranges either trigger the advertisement of the 
         indicated aggregate, 'advertiseMatching', or result in the prefix 
         not being advertised at all outside the area." 
    DEFVAL { advertiseMatching } 
    ::= { tmnxOspfAreaAggrEntry 8 } 
 
tmnxOspfAreaAggrRouteTag OBJECT-TYPE 
    SYNTAX      Integer32 
    MAX-ACCESS  read-create 
    STATUS      current 
    DESCRIPTION 
        "The value of tmnxOspfAreaAggrRouteTag specifies the tag that 
         is advertised only in the summarized As-External LSA when 
         summarizing from NSSA-LSAs to AS-External-LSAs." 
    DEFVAL { 0 } 
    ::= { tmnxOspfAreaAggrEntry 9 } 
 
             
--
--  The MD5 Key table for OSPF MD5 authentication
--

tmnxOspfIfMD5KeyTable    OBJECT-TYPE
    SYNTAX      SEQUENCE OF TmnxOspfIfMD5KeyEntry
    MAX-ACCESS  not-accessible
    STATUS      obsolete
    DESCRIPTION
        "The tmnxOspfIfMD5KeyTable contains a list of MD5 keys to be used
         to authenticate OSPFv2 packets.

         This table is obsoleted in release 9.0. It is replaced with
         tmnxOspfNgIfMD5KeyTable."
    ::= { tmnxOspfObjects 22 }

tmnxOspfIfMD5KeyEntry    OBJECT-TYPE
    SYNTAX      TmnxOspfIfMD5KeyEntry
    MAX-ACCESS  not-accessible
    STATUS      obsolete
    DESCRIPTION
        "Each row entry represents a MD5 key to be used to authenticate
         a OSPFv2 packet addressed to a particular OSPF IP address.
         Entries can be created and deleted via SNMP SET operations.  
         Creation requires a SET request containing at least 
         tmnxOspfIfMD5KeyKey and tmnxOspfIfMD5KeyStatus."
    INDEX       {   vRtrID,
                    tmnxOspfVersion,
                    tmnxOspfInstance,
                    tmnxOspfIfIndex, 
                    tmnxOspfIfInstId,
                    tmnxOspfIfMD5KeyIndex
                } 
    ::= { tmnxOspfIfMD5KeyTable 1 }

TmnxOspfIfMD5KeyEntry ::=
    SEQUENCE {
        tmnxOspfIfMD5KeyIndex           TmnxOspfIfMD5KeyId,
        tmnxOspfIfMD5KeyStatus          RowStatus,
        tmnxOspfIfMD5KeyKey             OCTET STRING,
        tmnxOspfIfMD5KeyStartTime       DateAndTime,
        tmnxOspfIfMD5KeyStopTime        DateAndTime
    }

tmnxOspfIfMD5KeyIndex    OBJECT-TYPE
    SYNTAX      TmnxOspfIfMD5KeyId
    MAX-ACCESS  not-accessible
    STATUS      obsolete
    DESCRIPTION
        "The value of tmnxOspfIfMD5KeyIndex provides a unique identifier 
         for a key to be used for authentication on a specific OSPFv2
         IP address.

         If tmnxOspfIfMD5KeyIndex has a value of 0, it means that no
         keys are configured."
    ::= { tmnxOspfIfMD5KeyEntry 1 }

tmnxOspfIfMD5KeyStatus    OBJECT-TYPE
    SYNTAX      RowStatus
    MAX-ACCESS  read-create
    STATUS      obsolete
    DESCRIPTION
        "The object tmnxOspfIfMD5KeyStatus is the RowStatus used for 
         creation, deletion, or control of tmnxOspfIfMD5KeyTable entries.  
         Before the row can be placed into the 'active' state 
         tmnxOspfIfMD5KeyKey must have been assigned a value."
    ::= { tmnxOspfIfMD5KeyEntry 2 }

tmnxOspfIfMD5KeyKey    OBJECT-TYPE
    SYNTAX      OCTET STRING (SIZE(0..16))
    MAX-ACCESS  read-create
    STATUS      obsolete
    DESCRIPTION
        "The value of tmnxOspfIfMD5KeyKey specifies the MD5 authentication 
         key to be used on this OSPFv2 IP address. 
         
         When read, tmnxOspfIfMD5KeyKey always returns an OCTET STRING of 
         length zero."
    ::= { tmnxOspfIfMD5KeyEntry 3 }

tmnxOspfIfMD5KeyStartTime    OBJECT-TYPE
    SYNTAX      DateAndTime
    MAX-ACCESS  read-create
    STATUS      obsolete
    DESCRIPTION
        "The value of tmnxOspfIfMD5KeyStartTime specifies the date and 
         time when this MD5 authentication key becomes valid for use. 
         If no date and time is set, represented by a DateAndTime string 
         with 0 length, the key is valid by default."
    DEFVAL { ''H }
    ::= { tmnxOspfIfMD5KeyEntry 4 }

tmnxOspfIfMD5KeyStopTime    OBJECT-TYPE
    SYNTAX      DateAndTime
    MAX-ACCESS  read-create
    STATUS      obsolete
    DESCRIPTION
        "The value of tmnxOspfIfMD5KeyStopTime specifies the date and 
         time when this MD5 authentication key becomes invalid for use.  
         If no date and time is set, represented by a DateAndTime string 
         with 0 length, the key is valid indefinitely."
    DEFVAL { ''H }
    ::= { tmnxOspfIfMD5KeyEntry 5 }

--
--  The MD5 Key table for OSPFv2 MD5 authentication on virtual interfaces
--

tmnxOspfVirtIfMD5KeyTable    OBJECT-TYPE
    SYNTAX      SEQUENCE OF TmnxOspfVirtIfMD5KeyEntry
    MAX-ACCESS  not-accessible
    STATUS      current
    DESCRIPTION
        "The tmnxOspfVirtIfMD5KeyTable contains a list of MD5 keys to be used
         to authenticate OSPFv2 packets on an OSPFv2 interface."
    ::= { tmnxOspfObjects 23 }

tmnxOspfVirtIfMD5KeyEntry    OBJECT-TYPE
    SYNTAX      TmnxOspfVirtIfMD5KeyEntry
    MAX-ACCESS  not-accessible
    STATUS      current
    DESCRIPTION
        "Each row entry represents a MD5 key to be used to authenticate
         a OSPFv2 packet addressed to a particular OSPFv2 IP address.
         Entries can be created and deleted via SNMP SET operations.  
         Creation requires a SET request containing at least 
         tmnxOspfVirtIfMD5KeyKey and tmnxOspfVirtIfMD5KeyStatus."
    INDEX       {   vRtrID,
                    tmnxOspfVersion,
                    tmnxOspfInstance,
                    tmnxOspfVirtIfAreaId, 
                    tmnxOspfVirtIfNeighbor,
                    tmnxOspfVirtIfMD5KeyIndex
                } 
    ::= { tmnxOspfVirtIfMD5KeyTable 1 }

TmnxOspfVirtIfMD5KeyEntry ::=
    SEQUENCE {
        tmnxOspfVirtIfMD5KeyIndex           TmnxOspfIfMD5KeyId,
        tmnxOspfVirtIfMD5KeyStatus          RowStatus,
        tmnxOspfVirtIfMD5KeyKey             OCTET STRING,
        tmnxOspfVirtIfMD5KeyStartTime       DateAndTime,
        tmnxOspfVirtIfMD5KeyStopTime        DateAndTime
    }

tmnxOspfVirtIfMD5KeyIndex    OBJECT-TYPE
    SYNTAX      TmnxOspfIfMD5KeyId
    MAX-ACCESS  not-accessible
    STATUS      current
    DESCRIPTION
        "The value of tmnxOspfVirtIfMD5KeyIndex provides a unique identifier 
         for a key to be used for authentication on a specific OSPFv2 
         virtual interface.

         If tmnxOspfVirtIfMD5KeyIndex has a value of 0, it means that no
         keys are configured."
        ::= { tmnxOspfVirtIfMD5KeyEntry 1 }

tmnxOspfVirtIfMD5KeyStatus    OBJECT-TYPE
    SYNTAX      RowStatus
    MAX-ACCESS  read-create
    STATUS      current
    DESCRIPTION
        "The value of tmnxOspfVirtIfMD5KeyStatus is the RowStatus used 
         for creation, deletion, or control of tmnxOspfVirtIfMD5KeyTable 
         entries.  Before the row can be placed into the 'active' state 
         tmnxOspfVirtIfMD5KeyKey must have been assigned a value."
    ::= { tmnxOspfVirtIfMD5KeyEntry 2 }

tmnxOspfVirtIfMD5KeyKey    OBJECT-TYPE
    SYNTAX      OCTET STRING (SIZE(0..16))
    MAX-ACCESS  read-create
    STATUS      current
    DESCRIPTION
        "The value of tmnxOspfVirtIfMD5KeyKey specifies the MD5 
         authentication key to be used on this OSPFv2 virtual interface.
         
         When read, tmnxOspfVirtIfMD5KeyKey always returns an OCTET STRING 
         of length zero."
    ::= { tmnxOspfVirtIfMD5KeyEntry 3 }

tmnxOspfVirtIfMD5KeyStartTime    OBJECT-TYPE
    SYNTAX      DateAndTime
    MAX-ACCESS  read-create
    STATUS      current
    DESCRIPTION
        "The value of tmnxOspfVirtIfMD5KeyStartTime specifies the date and 
         time when this MD5 authentication key becomes valid for use. If no 
         date and time is set, represented by a DateAndTime string with 0 
         length, the key is valid by default."
    DEFVAL { ''H }
    ::= { tmnxOspfVirtIfMD5KeyEntry 4 }

tmnxOspfVirtIfMD5KeyStopTime    OBJECT-TYPE
    SYNTAX      DateAndTime
    MAX-ACCESS  read-create
    STATUS      current
    DESCRIPTION
        "The value of tmnxOspfVirtIfMD5KeyStopTime specifies the date and 
         time when this MD5 authentication key becomes invalid for use.  
         If no date and time is set, represented by a DateAndTime string 
         with 0 length, the key is valid indefinitely."
    DEFVAL { ''H }
    ::= { tmnxOspfVirtIfMD5KeyEntry 5 }

-- 
-- OSPF Notification Support Objects 
--  
tmnxOspfNotifyObjs      OBJECT IDENTIFIER ::= { tmnxOspfObjects 24 }
  
tmnxOspfSetTrap         OBJECT-TYPE 
    SYNTAX      OCTET STRING (SIZE(4)) 
    MAX-ACCESS  read-write 
    STATUS      current 
    DESCRIPTION 
        "The value of tmnxOspfSetTrap specifies a four-octet string serving 
         as a bit map for the OSPF trap events.  This object is used 
         to enable and disable specific OSPF traps where a 1 in the bit 
         field represents enabled. The right-most bit  (least 
         significant) represents trap 0." 
    ::= { tmnxOspfNotifyObjs 1 } 
  
tmnxOspfConfigErrorType OBJECT-TYPE 
    SYNTAX      INTEGER { 
                    badVersion (1), 
                    areaMismatch (2), 
                    unknownNbmaNbr (3), -- Router is DR eligible 
                    unknownVirtualNbr (4), 
                    authTypeMismatch(5), 
                    authFailure (6), 
                    netMaskMismatch (7), 
                    helloIntervalMismatch (8), 
                    deadIntervalMismatch (9), 
                    optionMismatch (10), 
                    mtuMismatch (11), 
                    duplicateRouterId (12),  
                    noError (13),
                    instanceMismatch (14),
                    ifTypeMismatch (1001),
                    nullRouterId (1002),
                    ifAdminDown (1003),
                    ifPassive (1004)
                } 
    MAX-ACCESS  read-only 
    STATUS      current 
    DESCRIPTION 
        "The value of tmnxOspfConfigErrorType indicates the potential types 
         of configuration conflicts.  Used  by the tmnxOspfNgIfConfigError and 
         tmnxOspfVirtIfConfigError notifications.  When the last value of a 
         notification using this object is needed, but no notifications of 
         that type have been sent, the value pertaining to this object 
         should be returned as 'noError'." 
    ::= { tmnxOspfNotifyObjs 2 } 
  
tmnxOspfPacketType      OBJECT-TYPE 
    SYNTAX      INTEGER { 
                    hello (1), 
                    dbDescript (2), 
                    lsReq (3), 
                    lsUpdate (4), 
                    lsAck (5), 
                    nullPacket (6)
                } 
    MAX-ACCESS  read-only 
    STATUS      current 
    DESCRIPTION 
        "The value of tmnxOspfPacketType specifies the OSPF packet type.
         When the last value of a notification using this object is needed, 
         but no notifications of that type have been sent, this value 
         pertaining to this object should be returned as 'nullPacket'." 
    ::= { tmnxOspfNotifyObjs 3 } 
  
tmnxOspfPacketSrcAddressType OBJECT-TYPE 
    SYNTAX      InetAddressType 
    MAX-ACCESS  read-only 
    STATUS      current 
    DESCRIPTION 
        "The IP address type of tmnxOspfPacketSrcAddress." 
    ::= { tmnxOspfNotifyObjs 4 } 
 
tmnxOspfPacketSrcAddress OBJECT-TYPE 
    SYNTAX      InetAddress (SIZE (4|16|20))  
    MAX-ACCESS  read-only 
    STATUS      current 
    DESCRIPTION 
        "The value of tmnxOspfPacketSrcAddress indicates the IP address of an 
         inbound packet that cannot be identified by a neighbor instance. 
         When the last value of a notification using this object is 
         needed, but no notifications of that type have been sent, this 
         value pertaining to this object should be returned as 0.0.0.0" 
    ::= { tmnxOspfNotifyObjs 5 } 

tmnxOspfIfIpName OBJECT-TYPE 
    SYNTAX      DisplayString  (SIZE(1..45))
    MAX-ACCESS  accessible-for-notify 
    STATUS      current 
    DESCRIPTION 
        "The value of tmnxOspfIfIpName specifies the name of the OSPF
         interface that has experienced a state change.  It is the
         an ASCII string representation of the IP address of the IP 
         interface on which OSPF is configured.  It is used by the 
         tmnxOspfNgIfStateChange notification." 
    ::= { tmnxOspfNotifyObjs 6 } 

tmnxOspfIfEvent OBJECT-TYPE 
    SYNTAX      DisplayString (SIZE(1..32))     
    MAX-ACCESS  accessible-for-notify
    STATUS      current
    DESCRIPTION
         "The value of tmnxOspfIfEvent specifies the root cause that
          resulted in a tmnxOspfNgIfStateChange notification.  Some
          possible causes are interface up, interface down, and neighbor 
          changed." 
    ::= { tmnxOspfNotifyObjs 7 }

tmnxOspfFailureReasonCode OBJECT-TYPE 
    SYNTAX      INTEGER { 
                    other          (1),
                    mallocFailure  (2),
                    rtrLsaTooBig   (3),
                    spfFailures    (4),
                    rteTblAdd      (5),
                    rteTblModify   (6),
                    rteTblDelete   (7)
                } 
    MAX-ACCESS  accessible-for-notify
    STATUS      current 
    DESCRIPTION 
        "The value of tmnxOspfFailureReasonCode indicates the reason for the
         last OSPF failure which resulted in it being marked operationally down. 
         This object is used by the tmnxOspfFailureDisabled notification." 
    ::= { tmnxOspfNotifyObjs 8 } 

tmnxOspfBadPacketErrType OBJECT-TYPE 
    SYNTAX      INTEGER { 
                    wrongFormat (1), 
                    wrongChksum (2), 
                    ifOperDown  (3),
                    badDstAddr  (4),
                    badSrcAddr  (5),
                    badLlsBlock (6),
                    doubleLlsMtu (7)
                } 
    MAX-ACCESS  accessible-for-notify
    STATUS      current 
    DESCRIPTION 
        "" 
    ::= { tmnxOspfNotifyObjs 9 } 
  
--
-- OSPF Sham Links Table 
--

tmnxOspfShamIfTable OBJECT-TYPE 
    SYNTAX          SEQUENCE OF TmnxOspfShamIfEntry 
    MAX-ACCESS      not-accessible 
    STATUS          current 
    DESCRIPTION 
        "The tmnxOspfShamIfTable contains information about the sham links
         associated with OSPF." 
    REFERENCE 
        "OSPF Version 2, Appendix C.3 Router interface parameters"
    ::= { tmnxOspfObjects 25 } 
 
tmnxOspfShamIfEntry OBJECT-TYPE 
    SYNTAX          TmnxOspfShamIfEntry 
    MAX-ACCESS      not-accessible 
    STATUS          current 
    DESCRIPTION 
        "The tmnxOspfShamIfEntry contains information about a single
         Sham Link." 
    INDEX       {   vRtrID,
                    tmnxOspfVersion,
                    tmnxOspfInstance,
                    tmnxOspfShamIfIndex, 
                    tmnxOspfShamIfInstId,
                    tmnxOspfShamIfRemoteNbrAddrType,
                    tmnxOspfShamIfRemoteNbrAddress
                } 
    ::= { tmnxOspfShamIfTable 1 } 
 
TmnxOspfShamIfEntry ::= SEQUENCE { 
        tmnxOspfShamIfIndex                     InterfaceIndex, 
        tmnxOspfShamIfInstId                    TmnxOspfIfInstIdTc,
        tmnxOspfShamIfRemoteNbrAddrType         InetAddressType,
        tmnxOspfShamIfRemoteNbrAddress          InetAddress, 
        tmnxOspfShamIfStatus                    RowStatus,
        tmnxOspfShamIfLastChanged               TimeStamp, 
        tmnxOspfShamIfAreaId                    TmnxOspfAreaIdTc, 
        tmnxOspfShamIfAdminState                Status, 
        tmnxOspfShamIfTransitDelay              TmnxOspfUpToRefreshIntervalTc, 
        tmnxOspfShamIfRetransInterval           TmnxOspfUpToRefreshIntervalTc, 
        tmnxOspfShamIfHelloInterval             HelloRange, 
        tmnxOspfShamIfRtrDeadInterval           TmnxOspfDeadIntRangeTc, 
        tmnxOspfShamIfCfgMetric                 TmnxOspfShamIfMetricTc,
        tmnxOspfShamIfAuthType                  TmnxOspfAuthenticationType,
        tmnxOspfShamIfAuthKey                   OCTET STRING,
        tmnxOspfShamIfState                     INTEGER, 
        tmnxOspfShamIfLastEnabledTime           TimeStamp,
        tmnxOspfShamIfLinkLsaCount              Gauge32, 
        tmnxOspfShamIfLinkLsaCksumSum           Integer32, 
        tmnxOspfShamIfLinkUnkLsaCount           Gauge32, 
        tmnxOspfShamIfLinkUnkLsaCksumSum        Integer32, 
        tmnxOspfShamIfMD5TransmitKeyId          TmnxOspfIfMD5KeyId,
        tmnxOspfShamIfLocalIpAddressType        InetAddressType, 
        tmnxOspfShamIfLocalIpAddress            InetAddress,
        tmnxOspfShamIfMD5NumKeys                Gauge32,
        tmnxOspfShamIfAuthKeyChain              TNamedItemOrEmpty
    } 
 
tmnxOspfShamIfIndex OBJECT-TYPE 
    SYNTAX      InterfaceIndex 
    MAX-ACCESS  not-accessible 
    STATUS      current 
    DESCRIPTION 
        "The value of tmnxOspfShamIfIndex specifies the interface index of 
         the local OSPF interface.  It corresponds to the interface index of
         the IP interface which is configured as the local end of the
         sham link." 
    ::= { tmnxOspfShamIfEntry 1 } 
 
tmnxOspfShamIfInstId OBJECT-TYPE 
    SYNTAX      TmnxOspfIfInstIdTc 
    MAX-ACCESS  not-accessible 
    STATUS      current 
    DESCRIPTION 
        "The value of tmnxOspfShamIfInstId specifies the interface instance 
         ID to be used for the sham link.  This ID has local link 
         significance only."
    ::= { tmnxOspfShamIfEntry 2 } 

tmnxOspfShamIfRemoteNbrAddrType OBJECT-TYPE 
    SYNTAX      InetAddressType 
    MAX-ACCESS  not-accessible
    STATUS      current 
    DESCRIPTION 
        "The value of tmnxOspfShamIfRemoteNbrAddrType type indicates the IP
         address type of tmnxOspfShamIfRemoteNbrAddress. 

         tmnxOspfShamIfRemoteNbrAddrType supports only InetAddressType
         value 'ipv4'."
    ::= { tmnxOspfShamIfEntry 3 } 

tmnxOspfShamIfRemoteNbrAddress OBJECT-TYPE
    SYNTAX      InetAddress (SIZE (4|16))
    MAX-ACCESS  not-accessible
    STATUS      current
    DESCRIPTION
        "The value of tmnxOspfShamIfRemoteNbrAddress specifies the IP address 
         of the sham link Neighbor.  It corresponds to remote end of the sham 
         link."
    ::= { tmnxOspfShamIfEntry 4 }

tmnxOspfShamIfStatus OBJECT-TYPE 
    SYNTAX      RowStatus 
    MAX-ACCESS  read-create 
    STATUS      current 
    DESCRIPTION 
        "The value of tmnxOspfShamIfStatus controls creation and deletion of
         a row entry in this table." 
    ::= { tmnxOspfShamIfEntry 5 } 
 
tmnxOspfShamIfLastChanged  OBJECT-TYPE
    SYNTAX      TimeStamp
    MAX-ACCESS  read-only
    STATUS      current
    DESCRIPTION
        "The value of tmnxOspfShamIfLastChanged indicates the sysUpTime
         when a configurable object in this row was last modified."
    ::= { tmnxOspfShamIfEntry 6 } 

tmnxOspfShamIfAreaId OBJECT-TYPE 
    SYNTAX      TmnxOspfAreaIdTc 
    MAX-ACCESS  read-create 
    STATUS      current 
    DESCRIPTION 
        "The value of tmnxOspfShamIfAreaId specifies a 32-bit integer uniquely 
         identifying the area which the sham link belongs to. Area ID 0 is 
         used for the OSPF backbone." 
    DEFVAL { 0 } 
    ::= { tmnxOspfShamIfEntry 7 } 
 
tmnxOspfShamIfAdminState OBJECT-TYPE 
    SYNTAX      Status 
    MAX-ACCESS  read-create 
    STATUS      current 
    DESCRIPTION 
        "The value of tmnxOspfShamIfAdminState specifies the OSPF interface's
         administrative state on this sham link."
    DEFVAL { enabled } 
    ::= { tmnxOspfShamIfEntry 8 } 
 
tmnxOspfShamIfTransitDelay OBJECT-TYPE 
    SYNTAX      TmnxOspfUpToRefreshIntervalTc (1..1800)
    UNITS       "seconds" 
    MAX-ACCESS  read-create 
    STATUS      current 
    DESCRIPTION 
        "The value of tmnxOspfShamIfTransitDelay specifies the estimated 
         number of seconds it takes to transmit a link state update packet 
         over this sham link." 
    DEFVAL { 1 } 
    ::= { tmnxOspfShamIfEntry 9 } 
 
tmnxOspfShamIfRetransInterval OBJECT-TYPE 
    SYNTAX      TmnxOspfUpToRefreshIntervalTc (1..1800)
    UNITS       "seconds" 
    MAX-ACCESS  read-create 
    STATUS      current 
    DESCRIPTION 
        "The value of tmnxOspfShamIfRetransInterval specifies the number of 
         seconds between link state advertisement retransmissions, for 
         adjacencies belonging to this interface. This value is also used 
         when retransmitting database description and link state request 
         packets." 
    DEFVAL { 5 } 
    ::= { tmnxOspfShamIfEntry 10 } 
 
tmnxOspfShamIfHelloInterval OBJECT-TYPE 
    SYNTAX      HelloRange 
    UNITS       "seconds" 
    MAX-ACCESS  read-create 
    STATUS      current 
    DESCRIPTION 
        "The value of tmnxOspfShamIfHelloInterval specifies the length of
         time, in seconds, between the Hello packets that the router sends
         on the sham link.  This value MUST be same for all routers attached
         to a common network." 
    DEFVAL { 10 } 
    ::= { tmnxOspfShamIfEntry 11 } 
 
tmnxOspfShamIfRtrDeadInterval OBJECT-TYPE 
    SYNTAX      TmnxOspfDeadIntRangeTc 
    UNITS       "seconds" 
    MAX-ACCESS  read-create 
    STATUS      current 
    DESCRIPTION 
        "The value of tmnxOspfShamIfRtrDeadInterval specifies the number of 
         seconds that a router's Hello packets have not been seen before 
         its neighbors declare the router down on the sham link.  This 
         should be greater than or equal to (2 * tmnxOspfShamIfHelloInterval).  
         This value MUST be same for all routers attached to a common network."
    DEFVAL { 40 } 
    ::= { tmnxOspfShamIfEntry 12 } 

tmnxOspfShamIfCfgMetric OBJECT-TYPE 
    SYNTAX      TmnxOspfShamIfMetricTc 
    MAX-ACCESS  read-create 
    STATUS      current 
    DESCRIPTION 
        "The value of tmnxOspfShamIfCfgMetric specifies the desired 
         metric value assigned to this sham link."
    DEFVAL { 1 } 
    ::= { tmnxOspfShamIfEntry 13 } 
 
tmnxOspfShamIfAuthType OBJECT-TYPE 
    SYNTAX       TmnxOspfAuthenticationType 
    MAX-ACCESS   read-create 
    STATUS       current 
    DESCRIPTION 
        "The value of tmnxOspfShamIfAuthType specifies the authentication 
         type to use for a sham link. 
  
         Note that this object can be used to engage in significant attacks 
         against an OSPF router." 
    REFERENCE 
        "OSPF Version 2, Appendix D Authentication" 
    DEFVAL { none } -- no authentication, by default 
    ::= { tmnxOspfShamIfEntry 14 } 
  
tmnxOspfShamIfAuthKey OBJECT-TYPE 
    SYNTAX      OCTET STRING (SIZE (0..256)) 
    MAX-ACCESS  read-create 
    STATUS      current 
    DESCRIPTION 
        "The value of tmnxOspfShamIfAuthKey specifies the authentication key
         string.  The cleartext password is used as an OSPF Authentication 
         key when simplePassword security is enabled. This object does not 
         access any OSPF Cryptographic (e.g. MD5) Authentication Key under 
         any circumstance. 
  
         If the key length is shorter than 8 octets, the agent will left 
         adjust and zero fill to 8 octets. 
  
         Unauthenticated interfaces need no authentication key, and simple 
         password authentication cannot use a key of more than 8 octets. 
  
         Note that the use of simplePassword authentication is NOT recommended 
         when there is concern regarding attack upon the OSPF system. 
         This authentication is only sufficient to protect against 
         accidental misconfigurations because it re-uses cleartext passwords. 
         [RFC-1704] 
  
         When read, tmnxOspfShamIfAuthKey always returns an Octet String of 
         length zero.
         
         This object is valid only when tmnxOspfVersion has a value of
         'version2'." 
    REFERENCE 
        "OSPF Version 2, Section 9 The Interface Data Structure" 
    DEFVAL { '0000000000000000'H } -- 0.0.0.0.0.0.0.0 
    ::= { tmnxOspfShamIfEntry 15 } 

tmnxOspfShamIfState OBJECT-TYPE 
    SYNTAX      INTEGER { 
                    down(1), 
                    pointToPoint(4)
                } 
    MAX-ACCESS  read-only 
    STATUS      current 
    DESCRIPTION 
        "The value of tmnxOspfShamIfState indicates the operational state
         of this sham link." 
    ::= { tmnxOspfShamIfEntry 16 } 
 
tmnxOspfShamIfLastEnabledTime OBJECT-TYPE
    SYNTAX      TimeStamp
    MAX-ACCESS  read-only
    STATUS      current
    DESCRIPTION
        "The value of tmnxOspfShamIfLastEnabledTime indicates the sysUpTime
         value when ospfIfAdminStat was last set to enabled (1) to run the
         ospf on this interface."
    ::= { tmnxOspfShamIfEntry 17 }

tmnxOspfShamIfLinkLsaCount OBJECT-TYPE 
    SYNTAX      Gauge32 
    MAX-ACCESS  read-only 
    STATUS      current 
    DESCRIPTION 
        "The value of tmnxOspfShamIfLinkLsaCount indicates the total 
         number of Link-Scope link-state advertisements in this link's 
         link-state database." 
    ::= { tmnxOspfShamIfEntry 18 } 
 
tmnxOspfShamIfLinkLsaCksumSum OBJECT-TYPE 
    SYNTAX      Integer32 
    MAX-ACCESS  read-only 
    STATUS      current 
    DESCRIPTION 
        "The value of tmnxOspfShamIfLinkLsaCksumSum indicates the 32-bit 
         unsigned sum of the Link-Scope link-state advertisements' LS 
         checksums contained in this link's link-state database.  The 
         sum can be used to determine if there has been a change in a 
         router's link-state database, and to compare the link state 
         database of two routers." 
    ::= { tmnxOspfShamIfEntry 19 } 
 
tmnxOspfShamIfLinkUnkLsaCount OBJECT-TYPE 
    SYNTAX      Gauge32 
    MAX-ACCESS  read-only 
    STATUS      current 
    DESCRIPTION 
        "The value of tmnxOspfShamIfLinkUnkLsaCount indicates the total 
         number of unknown Link-Scope link-state advertisements in this 
         link's link-state database." 
    ::= { tmnxOspfShamIfEntry 20 } 
 
tmnxOspfShamIfLinkUnkLsaCksumSum OBJECT-TYPE 
    SYNTAX      Integer32 
    MAX-ACCESS  read-only 
    STATUS      current 
    DESCRIPTION 
        "The value of tmnxOspfShamIfLinkUnkLsaCksumSum indicates the 32-bit 
         unsigned sum of the unknown Link-Scope link-state advertisements' 
         LS checksums contained in this link's link-state database.  The 
         sum can be used to determine if there has been a change in a 
         router's link-state database, and to compare the link-state 
         database of two routers." 
    ::= { tmnxOspfShamIfEntry 21 } 
 
tmnxOspfShamIfMD5TransmitKeyId    OBJECT-TYPE
    SYNTAX      TmnxOspfIfMD5KeyId
    MAX-ACCESS  read-only
    STATUS      current
    DESCRIPTION
        "The value of tmnxOspfShamIfMD5TransmitKeyId indicates the index value
         used to access the row entry in the tmnxOspfShamIfMD5KeyTable that
         specifies the authentication type and key transmitted on this
         OSPF interface.  This object is valid only when tmnxOspfVersion
         has the value 'version2'.

         If tmnxOspfShamIfMD5TransmitKeyId has a value of 0, it means that no
         keys are configured."
    ::= { tmnxOspfShamIfEntry 22 }

tmnxOspfShamIfLocalIpAddressType OBJECT-TYPE 
    SYNTAX      InetAddressType 
    MAX-ACCESS  read-only 
    STATUS      current 
    DESCRIPTION 
        "The value of tmnxOspfShamIfLocalIpAddressType indicates the
         IP address type of tmnxOspfShamIfLocalIpAddress.

         tmnxOspfShamIfLocalIpAddressType supports only InetAddressType
         value 'ipv4'."
    ::= { tmnxOspfShamIfEntry 23 } 
 
tmnxOspfShamIfLocalIpAddress OBJECT-TYPE 
    SYNTAX      InetAddress (SIZE (0|4|16|20))  
    MAX-ACCESS  read-only 
    STATUS      current 
    DESCRIPTION 
        "The value of tmnxOspfShamIfLocalIpAddress indicates the IP address of 
         this OSPF local interface of the sham link." 
    ::= { tmnxOspfShamIfEntry 24 } 
 
tmnxOspfShamIfMD5NumKeys OBJECT-TYPE 
    SYNTAX      Gauge32 
    MAX-ACCESS  read-only 
    STATUS      current 
    DESCRIPTION 
        "The value of tmnxOspfShamIfMD5NumKeys indicates the number of MD5 Key
         entries for this OSPF sham link."
    ::= { tmnxOspfShamIfEntry 25 } 

tmnxOspfShamIfAuthKeyChain OBJECT-TYPE
    SYNTAX      TNamedItemOrEmpty
    MAX-ACCESS  read-create
    STATUS      current
    DESCRIPTION
        "The value of tmnxOspfShamIfAuthKeyChain specifies the
         keychain which will be used to sign and/or authenticate the OSPF
         protocol stream.

         The keychain name is defined by tmnxKeyChainName and is the index for
         TIMETRA-SECURITY-MIB::tmnxKeyChainTable."
    DEFVAL { ''H }
    ::= { tmnxOspfShamIfEntry 26 }

-- 
--  Augmentation of the tmnxOspfShamIfTable.
--  Use of AUGMENTS clause implies a one-to-one dependent relationship between
--  the base table, tmnxOspfShamIfTable, and the augmenting table, 
--  tmnxOspfShamIfStatsTable.
--
--  This in effect extends the tmnxOspfShamIfTable with additional columns.  
--  Creation (or deletion) of a row in the tmnxOspfShamIfTable results in 
--  the same fate for the row in the tmnxOspfShamIfStatsTable.
-- 

tmnxOspfShamIfStatsTable OBJECT-TYPE
    SYNTAX      SEQUENCE OF TmnxOspfShamIfStatsEntry
    MAX-ACCESS  not-accessible
    STATUS      current
    DESCRIPTION
        "The tmnxOspfShamIfStatsTable provides an extension of the 
         tmnxOspfShamIfTable for statistics for an OSPF sham link."
    ::= { tmnxOspfObjects 26 }

tmnxOspfShamIfStatsEntry OBJECT-TYPE
    SYNTAX      TmnxOspfShamIfStatsEntry
    MAX-ACCESS  not-accessible
    STATUS      current
    DESCRIPTION
        "Each row entry in the tmnxOspfShamIfStatsTable represents 
         additional columns for statistics for an OSPF sham link."
    AUGMENTS { tmnxOspfShamIfEntry }
   ::= { tmnxOspfShamIfStatsTable 1 }

TmnxOspfShamIfStatsEntry ::=
    SEQUENCE {
        tmnxOspfShamIfEvents                    Counter32, 
        tmnxOspfShamIfTxPackets                 Counter32,
        tmnxOspfShamIfTxHellos                  Counter32,
        tmnxOspfShamIfTxDBDs                    Counter32,
        tmnxOspfShamIfTxLSRs                    Counter32,
        tmnxOspfShamIfTxLSUs                    Counter32,
        tmnxOspfShamIfTxLSAcks                  Counter32,
        tmnxOspfShamIfRxPackets                 Counter32,
        tmnxOspfShamIfRxHellos                  Counter32,
        tmnxOspfShamIfRxDBDs                    Counter32,
        tmnxOspfShamIfRxLSRs                    Counter32,
        tmnxOspfShamIfRxLSUs                    Counter32,
        tmnxOspfShamIfRxLSAcks                  Counter32,
        tmnxOspfShamIfDiscardPackets            Counter32,
        tmnxOspfShamIfRetransmitOuts            Counter32,
        tmnxOspfShamIfBadVersions               Counter32,
        tmnxOspfShamIfBadNetworks               Counter32,
        tmnxOspfShamIfBadAreas                  Counter32,
        tmnxOspfShamIfBadDstAddrs               Counter32,
        tmnxOspfShamIfBadNeighbors              Counter32,
        tmnxOspfShamIfBadPacketTypes            Counter32,
        tmnxOspfShamIfLastEventTime             TimeStamp,
        tmnxOspfShamIfBadLengths                Counter32,
        tmnxOspfShamIfBadHelloIntervals         Counter32,
        tmnxOspfShamIfBadDeadIntervals          Counter32,
        tmnxOspfShamIfBadOptions                Counter32,
        tmnxOspfShamIfRxBadChecksums            Counter32,
        tmnxOspfShamIfBadAuthTypes              Counter32,
        tmnxOspfShamIfAuthFailures              Counter32
    }   

tmnxOspfShamIfEvents OBJECT-TYPE 
    SYNTAX      Counter32 
    MAX-ACCESS  read-only 
    STATUS      current 
    DESCRIPTION 
        "The value of tmnxOspfShamIfEvents indicates the number of 
         state changes or error events on this sham link." 
    ::= { tmnxOspfShamIfStatsEntry 1 } 
 
tmnxOspfShamIfTxPackets OBJECT-TYPE
    SYNTAX      Counter32
    MAX-ACCESS  read-only
    STATUS      current
    DESCRIPTION
        "The value of tmnxOspfShamIfTxPackets indicates the total number of
         OSPF packets transmitted on this sham link since tmnxOspfAdminState
         was last set to 'enabled'."
    ::= { tmnxOspfShamIfStatsEntry 2 }

tmnxOspfShamIfTxHellos OBJECT-TYPE
    SYNTAX      Counter32
    MAX-ACCESS  read-only
    STATUS      current
    DESCRIPTION
        "The value of tmnxOspfShamIfTxHellos indicates the total number
         of OSPF Hello packets transmitted on this sham link since
         tmnxOspfAdminState was last set to 'enabled'."
    ::= { tmnxOspfShamIfStatsEntry 3 }

tmnxOspfShamIfTxDBDs OBJECT-TYPE
    SYNTAX      Counter32
    MAX-ACCESS  read-only
    STATUS      current
    DESCRIPTION
        "The value of tmnxOspfShamIfTxDBDs indicates the total number
         of OSPF Database Description packets transmitted on this
         sham link since tmnxOspfAdminState was last set to 'enabled'."
    ::= { tmnxOspfShamIfStatsEntry 4 }

tmnxOspfShamIfTxLSRs OBJECT-TYPE
    SYNTAX      Counter32
    MAX-ACCESS  read-only
    STATUS      current
    DESCRIPTION
        "The value of tmnxOspfShamIfTxLSRs indicates the total number
         of OSPF Link State Requests (LSRs) transmitted on this
         sham link since tmnxOspfAdminState was last set to 'enabled'."
    ::= { tmnxOspfShamIfStatsEntry 5 }

tmnxOspfShamIfTxLSUs OBJECT-TYPE
    SYNTAX      Counter32
    MAX-ACCESS  read-only
    STATUS      current
    DESCRIPTION
        "The value of tmnxOspfShamIfTxLSUs indicates the total number
         of OSPF Link State Updates (LSUs) transmitted on this
         sham link since tmnxOspfAdminState was last set to 'enabled'."
    ::= { tmnxOspfShamIfStatsEntry 6 }

tmnxOspfShamIfTxLSAcks OBJECT-TYPE
    SYNTAX      Counter32
    MAX-ACCESS  read-only
    STATUS      current
    DESCRIPTION
        "The value of tmnxOspfShamIfTxLSAcks indicates the total number
         of OSPF Link State Acknowledgements transmitted on this
         sham link since tmnxOspfAdminState was last set to 'enabled'."
    ::= { tmnxOspfShamIfStatsEntry 7 }

tmnxOspfShamIfRxPackets OBJECT-TYPE
    SYNTAX      Counter32
    MAX-ACCESS  read-only
    STATUS      current
    DESCRIPTION
        "The value of tmnxOspfShamIfRxPackets indicates the total number of
         OSPF packets received on this sham link since tmnxOspfAdminState was
         last set to 'enabled'."
    ::= { tmnxOspfShamIfStatsEntry 8 }

tmnxOspfShamIfRxHellos OBJECT-TYPE
    SYNTAX      Counter32
    MAX-ACCESS  read-only
    STATUS      current
    DESCRIPTION
        "The value of tmnxOspfShamIfRxHellos indicates the total number of
         OSPF Hello packets received on this sham link since tmnxOspfAdminState
         was last set to 'enabled'."
    ::= { tmnxOspfShamIfStatsEntry 9 }

tmnxOspfShamIfRxDBDs OBJECT-TYPE
    SYNTAX      Counter32
    MAX-ACCESS  read-only
    STATUS      current
    DESCRIPTION
        "The value of tmnxOspfShamIfRxDBDs indicates the total number of
         OSPF Database Description packets  received on this sham link since
         tmnxOspfAdminState was last set to 'enabled'."
    ::= { tmnxOspfShamIfStatsEntry 10 }

tmnxOspfShamIfRxLSRs OBJECT-TYPE
    SYNTAX      Counter32
    MAX-ACCESS  read-only
    STATUS      current
    DESCRIPTION
        "The value of tmnxOspfShamIfRxLSRs indicates the total number of
         Link State Requests (LSRs) received on this sham link since
         tmnxOspfAdminState was last set to 'enabled'."
    ::= { tmnxOspfShamIfStatsEntry 11 }

tmnxOspfShamIfRxLSUs OBJECT-TYPE
    SYNTAX      Counter32
    MAX-ACCESS  read-only
    STATUS      current
    DESCRIPTION
        "The value of tmnxOspfShamIfRxLSUs indicates the total number of
         Link State Updates (LSUs) received on this sham link since
         tmnxOspfAdminState was last set to 'enabled'."
    ::= { tmnxOspfShamIfStatsEntry 12 }

tmnxOspfShamIfRxLSAcks OBJECT-TYPE
    SYNTAX      Counter32
    MAX-ACCESS  read-only
    STATUS      current
    DESCRIPTION
        "The value of tmnxOspfShamIfRxLSAcks indicates the total number of
         Link State Acknowledgements received on this sham link since
         tmnxOspfAdminState was last set to 'enabled'."
    ::= { tmnxOspfShamIfStatsEntry 13 }

tmnxOspfShamIfDiscardPackets OBJECT-TYPE
    SYNTAX      Counter32
    MAX-ACCESS  read-only
    STATUS      current
    DESCRIPTION
        "The value of tmnxOspfShamIfDiscardPackets indicates the total number
         of OSPF packets discarded on this sham link since tmnxOspfAdminState
         was last set to 'enabled'."
    ::= { tmnxOspfShamIfStatsEntry 14 }

tmnxOspfShamIfRetransmitOuts OBJECT-TYPE
    SYNTAX      Counter32
    MAX-ACCESS  read-only
    STATUS      current
    DESCRIPTION
        "The value of tmnxOspfShamIfRetransmitOuts indicates the total number
         of OSPF Retransmits sent on this sham link since tmnxOspfAdminState
         was last set to 'enabled'."
    ::= { tmnxOspfShamIfStatsEntry 15 }

tmnxOspfShamIfBadVersions OBJECT-TYPE
    SYNTAX      Counter32
    MAX-ACCESS  read-only
    STATUS      current
    DESCRIPTION
        "The value of tmnxOspfShamIfBadVersions indicates the total number of
         OSPF packets received with bad OSPF version numbers since
         tmnxOspfAdminState was last set to 'enabled'."
    ::= { tmnxOspfShamIfStatsEntry 16 }

tmnxOspfShamIfBadNetworks OBJECT-TYPE
    SYNTAX      Counter32
    MAX-ACCESS  read-only
    STATUS      current
    DESCRIPTION
        "The value of tmnxOspfShamIfBadNetworks indicates the total number of
         OSPF packets received with invalid network or mask since
         tmnxOspfAdminState was last set to 'enabled'."
    ::= { tmnxOspfShamIfStatsEntry 17 }

tmnxOspfShamIfBadAreas OBJECT-TYPE
    SYNTAX      Counter32
    MAX-ACCESS  read-only
    STATUS      current
    DESCRIPTION
        "The value of tmnxOspfShamIfBadAreas indicates the total number of OSPF
         packets received with an area mismatch since tmnxOspfAdminState
         was last set to 'enabled'."
    ::= { tmnxOspfShamIfStatsEntry 18 }

tmnxOspfShamIfBadDstAddrs OBJECT-TYPE
    SYNTAX      Counter32
    MAX-ACCESS  read-only
    STATUS      current
    DESCRIPTION
        "The value of tmnxOspfShamIfBadDstAddrs indicates the total number
         of OSPF packets received with the incorrect IP destination address
         since tmnxOspfAdminState was last set to 'enabled'."
    ::= { tmnxOspfShamIfStatsEntry 19 }

tmnxOspfShamIfBadNeighbors OBJECT-TYPE
    SYNTAX      Counter32
    MAX-ACCESS  read-only
    STATUS      current
    DESCRIPTION
        "The value of tmnxOspfShamIfBadNeighbors indicates the total number
         of OSPF packets received where the neighbor information does not
         match the information this router has for the neighbor since
         tmnxOspfAdminState was last set to 'enabled'."
    ::= { tmnxOspfShamIfStatsEntry 20 }

tmnxOspfShamIfBadPacketTypes OBJECT-TYPE
    SYNTAX      Counter32
    MAX-ACCESS  read-only
    STATUS      current
    DESCRIPTION
        "The value of tmnxOspfShamIfBadPacketTypes indicates the total number
         of OSPF packets received with an invalid OSPF packet type since
         tmnxOspfAdminState was last set to 'enabled'."
    ::= { tmnxOspfShamIfStatsEntry 21 }

tmnxOspfShamIfLastEventTime OBJECT-TYPE
    SYNTAX      TimeStamp
    MAX-ACCESS  read-only
    STATUS      current
    DESCRIPTION
        "The value of tmnxOspfShamIfLastEventTime indicates the value of
         sysUpTime when an event was last associated with this OSPF
         sham link."
    ::= { tmnxOspfShamIfStatsEntry 22 }

tmnxOspfShamIfBadLengths OBJECT-TYPE
    SYNTAX      Counter32
    MAX-ACCESS  read-only
    STATUS      current
    DESCRIPTION
        "The value of tmnxOspfShamIfBadLengths indicates the total number
         of OSPF packets received on this sham link with a total length
         not equal to the length given in the packet itself since
         tmnxOspfAdminState was last set to 'enabled'."
    ::= { tmnxOspfShamIfStatsEntry 23 }

tmnxOspfShamIfBadHelloIntervals OBJECT-TYPE
    SYNTAX      Counter32
    MAX-ACCESS  read-only
    STATUS      current
    DESCRIPTION
        "The value of tmnxOspfShamIfBadHelloIntervals indicates the
         total number of OSPF packets received where the hello interval
         given in packet was not equal to that configured on this sham link
         since tmnxOspfAdminState was last set to 'enabled'."
    ::= { tmnxOspfShamIfStatsEntry 24 }

tmnxOspfShamIfBadDeadIntervals OBJECT-TYPE
    SYNTAX      Counter32
    MAX-ACCESS  read-only
    STATUS      current
    DESCRIPTION
        "The value of tmnxOspfShamIfBadDeadIntervals indicates the
         total number of OSPF packets received where the dead interval
         given in the packet was not equal to that configured on this
         sham link since tmnxOspfAdminState was last set to 'enabled'."
    ::= { tmnxOspfShamIfStatsEntry 25 }

tmnxOspfShamIfBadOptions OBJECT-TYPE
    SYNTAX      Counter32
    MAX-ACCESS  read-only
    STATUS      current
    DESCRIPTION
        "The value of tmnxOspfShamIfBadOptions indicates the total number
         of OSPF packets received with an option that does not match
         those configured for this sham link or area since
         tmnxOspfAdminState was last set to 'enabled'."
    ::= { tmnxOspfShamIfStatsEntry 26 }

tmnxOspfShamIfRxBadChecksums OBJECT-TYPE
    SYNTAX      Counter32
    MAX-ACCESS  read-only
    STATUS      current
    DESCRIPTION
        "The value of tmnxOspfShamIfRxBadChecksums indicates the count
         of LSAs received with bad checksums."
    ::= { tmnxOspfShamIfStatsEntry 27 }

tmnxOspfShamIfBadAuthTypes OBJECT-TYPE
    SYNTAX      Counter32
    MAX-ACCESS  read-only
    STATUS      current
    DESCRIPTION
        "The value of tmnxOspfShamIfBadAuthTypes indicates the total 
         number of OSPF packets received with an invalid authorization
         type since tmnxOspfAdminState was last set to 'enabled'."
    ::= { tmnxOspfShamIfStatsEntry 28 }

tmnxOspfShamIfAuthFailures OBJECT-TYPE
    SYNTAX      Counter32
    MAX-ACCESS  read-only
    STATUS      current
    DESCRIPTION
        "The value of tmnxOspfShamIfAuthFailures indicates the total 
         number of OSPF packets received with an invalid authorization
         key since tmnxOspfAdminState was last set to 'enabled'."
    ::= { tmnxOspfShamIfStatsEntry 29 }


--
--  The MD5 Key table for OSPF MD5 authentication on sham links.
--

tmnxOspfShamIfMD5KeyTable    OBJECT-TYPE
    SYNTAX      SEQUENCE OF TmnxOspfShamIfMD5KeyEntry
    MAX-ACCESS  not-accessible
    STATUS      current
    DESCRIPTION
        "The tmnxOspfShamIfMD5KeyTable contains a list of MD5 keys to be used
         to authenticate OSPFv2 packets."
    ::= { tmnxOspfObjects 27 }

tmnxOspfShamIfMD5KeyEntry    OBJECT-TYPE
    SYNTAX      TmnxOspfShamIfMD5KeyEntry
    MAX-ACCESS  not-accessible
    STATUS      current
    DESCRIPTION
        "Each row entry represents a MD5 key to be used to authenticate
         an OSPFv2 packet addressed to a particular OSPF IP address.
         Entries can be created and deleted via SNMP SET operations.  
         Creation requires a SET request containing at least 
         tmnxOspfShamIfMD5KeyKey and tmnxOspfShamIfMD5KeyStatus."
    INDEX       {   vRtrID,
                    tmnxOspfVersion,
                    tmnxOspfInstance,
                    tmnxOspfShamIfIndex, 
                    tmnxOspfShamIfInstId,
                    tmnxOspfShamIfRemoteNbrAddrType,
                    tmnxOspfShamIfRemoteNbrAddress,
                    tmnxOspfShamIfMD5KeyIndex
                } 
    ::= { tmnxOspfShamIfMD5KeyTable 1 }

TmnxOspfShamIfMD5KeyEntry ::=
    SEQUENCE {
        tmnxOspfShamIfMD5KeyIndex           TmnxOspfIfMD5KeyId,
        tmnxOspfShamIfMD5KeyStatus          RowStatus,
        tmnxOspfShamIfMD5KeyKey             OCTET STRING,
        tmnxOspfShamIfMD5KeyStartTime       DateAndTime,
        tmnxOspfShamIfMD5KeyStopTime        DateAndTime
    }

tmnxOspfShamIfMD5KeyIndex    OBJECT-TYPE
    SYNTAX      TmnxOspfIfMD5KeyId
    MAX-ACCESS  not-accessible
    STATUS      current
    DESCRIPTION
        "The value of tmnxOspfShamIfMD5KeyIndex provides a unique identifier 
         for a key to be used for authentication on a specific OSPFv2
         IP address.

         If tmnxOspfShamIfMD5KeyIndex has a value of 0, it means that no
         keys are configured."
    ::= { tmnxOspfShamIfMD5KeyEntry 1 }

tmnxOspfShamIfMD5KeyStatus    OBJECT-TYPE
    SYNTAX      RowStatus
    MAX-ACCESS  read-create
    STATUS      current
    DESCRIPTION
        "The object tmnxOspfShamIfMD5KeyStatus is the RowStatus used for 
         creation, deletion, or control of tmnxOspfShamIfMD5KeyTable entries.  
         Before the row can be placed into the 'active' state 
         tmnxOspfShamIfMD5KeyKey must have been assigned a value."
    ::= { tmnxOspfShamIfMD5KeyEntry 2 }

tmnxOspfShamIfMD5KeyKey    OBJECT-TYPE
    SYNTAX      OCTET STRING (SIZE(0..16))
    MAX-ACCESS  read-create
    STATUS      current
    DESCRIPTION
        "The value of tmnxOspfShamIfMD5KeyKey specifies the MD5 authentication 
         key to be used on this OSPFv2 IP address. 
         
         When read, tmnxOspfShamIfMD5KeyKey always returns an OCTET STRING of 
         length zero."
    ::= { tmnxOspfShamIfMD5KeyEntry 3 }

tmnxOspfShamIfMD5KeyStartTime    OBJECT-TYPE
    SYNTAX      DateAndTime
    MAX-ACCESS  read-create
    STATUS      current
    DESCRIPTION
        "The value of tmnxOspfShamIfMD5KeyStartTime specifies the date and 
         time when this MD5 authentication key becomes valid for use. 
         If no date and time is set, represented by a DateAndTime string 
         with 0 length, the key is valid by default."
    DEFVAL { ''H }
    ::= { tmnxOspfShamIfMD5KeyEntry 4 }

tmnxOspfShamIfMD5KeyStopTime    OBJECT-TYPE
    SYNTAX      DateAndTime
    MAX-ACCESS  read-create
    STATUS      current
    DESCRIPTION
        "The value of tmnxOspfShamIfMD5KeyStopTime specifies the date and 
         time when this MD5 authentication key becomes invalid for use.  
         If no date and time is set, represented by a DateAndTime string 
         with 0 length, the key is valid indefinitely."
    DEFVAL { ''H }
    ::= { tmnxOspfShamIfMD5KeyEntry 5 } 


-- OSPF Sham link Neighbor Table 
-- This table describes all sham link neighbors. 
-- Since Sham Links are configured in the 
-- sham interface table, this table is read-only. 
 
tmnxOspfShamNbrTable OBJECT-TYPE 
    SYNTAX          SEQUENCE OF TmnxOspfShamNbrEntry 
    MAX-ACCESS      not-accessible 
    STATUS          current 
    DESCRIPTION 
        "The tmnxOspfShamNbrTable contains sham links neighbors information." 
    REFERENCE 
        "OSPF Version 2, Section 15 Sham Links" 
    ::= { tmnxOspfObjects 28 } 
 
tmnxOspfShamNbrEntry OBJECT-TYPE 
    SYNTAX          TmnxOspfShamNbrEntry 
    MAX-ACCESS      not-accessible 
    STATUS          current 
    DESCRIPTION 
        "The tmnxOspfShamNbrEntry contains information for a specific
         sham link neighbor." 
    INDEX       {   vRtrID,
                    tmnxOspfVersion,
                    tmnxOspfInstance,
                    tmnxOspfShamNbrIfIndex, 
                    tmnxOspfShamNbrIfInstId, 
                    tmnxOspfShamNbrAddressType,
                    tmnxOspfShamNbrAddress,
                    tmnxOspfShamNbrRtrId
                } 
    ::= { tmnxOspfShamNbrTable 1 } 
 
TmnxOspfShamNbrEntry ::= SEQUENCE { 
        tmnxOspfShamNbrIfIndex              InterfaceIndex,
        tmnxOspfShamNbrIfInstId             TmnxOspfIfInstIdTc,
        tmnxOspfShamNbrAddressType          InetAddressType, 
        tmnxOspfShamNbrAddress              InetAddress, 
        tmnxOspfShamNbrRtrId                TmnxOspfRouterIdTc,
        tmnxOspfShamNbrOptions              Integer32, 
        tmnxOspfShamNbrState                INTEGER, 
        tmnxOspfShamNbrHelloSuppressed      TruthValue, 
        tmnxOspfShamNbrIfId                 InterfaceIndexOrZero, 
        tmnxOspfShamNbrRestartHelperStatus  INTEGER,  
        tmnxOspfShamNbrRestartHelperAge     TmnxOspfUpToRefreshIntervalTc,  
        tmnxOspfShamNbrRestartHelperExitRc  INTEGER, 
        tmnxOspfShamNbrUpTime               TimeInterval,
        tmnxOspfShamNbrLastEventTime        TimeStamp,
        tmnxOspfShamNbrDeadTmeOutstng       Unsigned32,
        tmnxOspfShamNbrLastRestartTime      TimeStamp,
        tmnxOspfShamNbrRestartReason        TmnxOspfRestartReasonTc
    } 
 
tmnxOspfShamNbrIfIndex OBJECT-TYPE 
    SYNTAX      InterfaceIndex 
    MAX-ACCESS  not-accessible 
    STATUS      current 
    DESCRIPTION 
        "The value of tmnxOspfShamNbrIfIndex specifies the local link ID of 
         the link over which the sham link neighbor can be reached." 
    ::= { tmnxOspfShamNbrEntry 1 } 
 
tmnxOspfShamNbrIfInstId OBJECT-TYPE 
    SYNTAX      TmnxOspfIfInstIdTc 
    MAX-ACCESS  not-accessible 
    STATUS      current 
    DESCRIPTION 
        "The value of tmnxOspfShamNbrIfInstId specifies the interface instance 
         over which the sham link neighbor can be reached.  This ID has 
         local link significance only."
    ::= { tmnxOspfShamNbrEntry 2 } 
 
tmnxOspfShamNbrAddressType OBJECT-TYPE 
    SYNTAX      InetAddressType 
    MAX-ACCESS  not-accessible 
    STATUS      current 
    DESCRIPTION 
        "The value of tmnxOspfShamNbrAddressType indicates the address 
         type of tmnxOspfShamNbrAddress. For IPv6 address type only 
         addresses without zone index are expected." 
    ::= { tmnxOspfShamNbrEntry 3 } 
 
tmnxOspfShamNbrAddress OBJECT-TYPE 
    SYNTAX      InetAddress (SIZE (4|16))  
    MAX-ACCESS  not-accessible 
    STATUS      current 
    DESCRIPTION 
        "The value of tmnxOspfShamNbrAddress indicates the IP address 
         advertised by this Sham link Neighbor. It must be a Global scope 
         address." 
    ::= { tmnxOspfShamNbrEntry 4 } 

tmnxOspfShamNbrRtrId OBJECT-TYPE
    SYNTAX      TmnxOspfRouterIdTc
    MAX-ACCESS  not-accessible
    STATUS      current
    DESCRIPTION
        "The value of tmnxOspfShamNbrRtrId specifies a 32-bit integer uniquely
         identifying the neighboring router in the Autonomous System."
    ::= { tmnxOspfShamNbrEntry 5 }
 
tmnxOspfShamNbrOptions OBJECT-TYPE 
    SYNTAX      Integer32 
    MAX-ACCESS  read-only 
    STATUS      current 
    DESCRIPTION 
        "The value of tmnxOspfShamNbrOptions indicates a Bit Mask 
         corresponding to the sham link neighbor's options field." 
    REFERENCE 
        "OSPF Version 3, Appendix A.2 the Options field" 
    ::= { tmnxOspfShamNbrEntry 6 } 
 
tmnxOspfShamNbrState OBJECT-TYPE 
    SYNTAX      INTEGER { 
                    down            (1), 
                    attempt         (2), 
                    init            (3), 
                    twoWay          (4), 
                    exchangeStart   (5), 
                    exchange        (6), 
                    loading         (7), 
                    full            (8) 
                } 
    MAX-ACCESS  read-only 
    STATUS      current 
    DESCRIPTION 
        "The value of tmnxOspfShamNbrState indicates the state of the 
         Sham link Neighbor Relationship." 
    ::= { tmnxOspfShamNbrEntry 7 } 
 
tmnxOspfShamNbrHelloSuppressed OBJECT-TYPE 
    SYNTAX      TruthValue 
    MAX-ACCESS  read-only 
    STATUS      current 
    DESCRIPTION 
        "The value of tmnxOspfShamNbrHelloSuppressed indicates whether 
         Hellos are being suppressed to the sham link neighbor" 
    ::= { tmnxOspfShamNbrEntry 8 } 
 
tmnxOspfShamNbrIfId OBJECT-TYPE 
    SYNTAX      InterfaceIndexOrZero 
    MAX-ACCESS  read-only 
    STATUS      current 
    DESCRIPTION 
        "The value of tmnxOspfShamNbrIfId indicates the interface ID that 
         the neighbor advertises in its Hello Packets on this sham link, 
         that is, the neighbor's local interface ID." 
    ::= { tmnxOspfShamNbrEntry 9 } 
 
tmnxOspfShamNbrRestartHelperStatus OBJECT-TYPE  
    SYNTAX      INTEGER { 
                    notHelping (1),  
                    helping (2)  
                }  
    MAX-ACCESS  read-only  
    STATUS      current  
    DESCRIPTION  
        "The value of tmnxOspfShamNbrRestartHelperStatus indicates whether 
         the router is acting as a Graceful restart helper for the sham 
         link neighbor."  
    ::= { tmnxOspfShamNbrEntry 10 }  
        
tmnxOspfShamNbrRestartHelperAge OBJECT-TYPE  
    SYNTAX      TmnxOspfUpToRefreshIntervalTc 
    UNITS       "seconds"  
    MAX-ACCESS  read-only  
    STATUS      current  
    DESCRIPTION  
        "The value of tmnxOspfShamNbrRestartHelperAge indicates the 
         remaining time in current OSPF Graceful restart interval, 
         if the router is acting as a restart helper for the sham link
         neighbor."  
    ::= { tmnxOspfShamNbrEntry 11 }  
        
tmnxOspfShamNbrRestartHelperExitRc OBJECT-TYPE  
    SYNTAX      INTEGER { 
                    none (1),  
                    inProgress (2),  
                    completed (3),  
                    timedOut (4),  
                    topologyChanged (5)  
                }  
    MAX-ACCESS  read-only  
    STATUS      current  
    DESCRIPTION  
        "The value of tmnxOspfShamNbrRestartHelperExitRc indicates the 
         outcome of the last attempt at acting as a Graceful restart 
         helper for the sham link neighbor. 
    
              none             No restart has yet been attempted. 
              inProgress       A restart attempt is currently underway. 
              completed        The last restart completed successfully. 
              timedOut         The last restart timed out. 
              topologyChanged  The last restart was aborted due to 
                               a topology change."  
    ::= { tmnxOspfShamNbrEntry 12 }

tmnxOspfShamNbrUpTime OBJECT-TYPE
    SYNTAX      TimeInterval
    MAX-ACCESS  read-only
    STATUS      current
    DESCRIPTION
        "The value of tmnxOspfShamNbrUpTime indicates the uninterrupted time,
         in hundredths of seconds, the adjacency to this sham link neighbour
         has been up."
    ::= { tmnxOspfShamNbrEntry 13 }

tmnxOspfShamNbrLastEventTime OBJECT-TYPE
    SYNTAX      TimeStamp
    MAX-ACCESS  read-only
    STATUS      current
    DESCRIPTION
        "The value of tmnxOspfShamNbrLastEventTime indicates the value of
         sysUpTime when the last event occurred that affected the adjacency
         to the sham link neighbour."
    ::= { tmnxOspfShamNbrEntry 14 }

tmnxOspfShamNbrDeadTmeOutstng  OBJECT-TYPE
    SYNTAX      Unsigned32 (0..'7FFFFFFF'h)
    UNITS       "seconds"
    MAX-ACCESS  read-only
    STATUS      current
    DESCRIPTION
        "The value of tmnxOspfShamNbrDeadTmeOutstng indicates the amount 
         of time in seconds until the dead-router interval expires.
         Normally, this value should not be significantly smaller than the
         configured dead router interval minus one hello interval."
    ::= { tmnxOspfShamNbrEntry 15 }

tmnxOspfShamNbrLastRestartTime OBJECT-TYPE
    SYNTAX      TimeStamp
    MAX-ACCESS  read-only
    STATUS      current
    DESCRIPTION
        "The value of tmnxOspfShamNbrLastRestartTime indicates the 
        last time the sham link neighbor attempted restart."
    ::= { tmnxOspfShamNbrEntry 16 }

tmnxOspfShamNbrRestartReason OBJECT-TYPE
    SYNTAX      TmnxOspfRestartReasonTc
    MAX-ACCESS  read-only
    STATUS      current
    DESCRIPTION
        "The value of tmnxOspfShamNbrRestartReason indicates the OSPF 
         sham link neighbor's graceful restart reason." 
    ::= { tmnxOspfShamNbrEntry 17 } 


-- 
--  Augmentation of the tmnxOspfShamNbrTable.
--  Use of AUGMENTS clause implies a one-to-one dependent relationship 
--  between the base table, tmnxOspfShamNbrTable, and the augmenting table, 
--  tmnxOspfShamNbrStatsTable.
--
--  This in effect extends the tmnxOspfShamNbrTable with additional columns.  
--  Creation (or deletion) of a row in the tmnxOspfShamNbrTable results in 
--  the same fate for the row in the tmnxOspfShamNbrStatsTable.
-- 

tmnxOspfShamNbrStatsTable OBJECT-TYPE
    SYNTAX      SEQUENCE OF TmnxOspfShamNbrStatsEntry
    MAX-ACCESS  not-accessible
    STATUS      current
    DESCRIPTION
        "The tmnxOspfShamNbrStatsTable provides an extension of the 
         tmnxOspfShamNbrTable for statistics for an OSPF sham link neighbor."
    ::= { tmnxOspfObjects 29 }

tmnxOspfShamNbrStatsEntry OBJECT-TYPE
    SYNTAX      TmnxOspfShamNbrStatsEntry
    MAX-ACCESS  not-accessible
    STATUS      current
    DESCRIPTION
        "Each row entry in the tmnxOspfShamNbrStatsTable represents 
         additional columns for statistics for an OSPF sham link neighbor."
    AUGMENTS { tmnxOspfShamNbrEntry }
   ::= { tmnxOspfShamNbrStatsTable 1 }

TmnxOspfShamNbrStatsEntry ::=
    SEQUENCE {
        tmnxOspfShamNbrEvents               Counter32, 
        tmnxOspfShamNbrLsRetransQLen        Gauge32, 
        tmnxOspfShamNbrBadNbrStates         Counter32,
        tmnxOspfShamNbrLsaInstallFail       Counter32,
        tmnxOspfShamNbrBadSeqNums           Counter32,
        tmnxOspfShamNbrBadMTUs              Counter32,
        tmnxOspfShamNbrBadPackets           Counter32,
        tmnxOspfShamNbrLsaNotInLsdbs        Counter32,
        tmnxOspfShamNbrOptionMismatch       Counter32,
        tmnxOspfShamNbrDuplicates           Counter32,
        tmnxOspfShamNbrNumRestarts          Counter32
    }

tmnxOspfShamNbrEvents OBJECT-TYPE 
    SYNTAX      Counter32 
    MAX-ACCESS  read-only 
    STATUS      current 
    DESCRIPTION 
        "The value of tmnxOspfShamNbrEvents indicates the number of times 
         this sham link has changed its state, or an error has occurred." 
    ::= { tmnxOspfShamNbrStatsEntry 1 } 
 
tmnxOspfShamNbrLsRetransQLen OBJECT-TYPE 
    SYNTAX      Gauge32 
    MAX-ACCESS  read-only 
    STATUS      current 
    DESCRIPTION 
        "The value of tmnxOspfShamNbrLsRetransQLen indicates the current 
         length of the retransmission queue." 
    ::= { tmnxOspfShamNbrStatsEntry 2 } 
 
tmnxOspfShamNbrBadNbrStates OBJECT-TYPE
    SYNTAX      Counter32
    MAX-ACCESS  read-only
    STATUS      current
    DESCRIPTION
        "The value of tmnxOspfShamNbrBadNbrStates indicates the total
         number of OSPF packets received when the sham link neighbor state 
         was not expecting to receive this packet type since
         tmnxOspfAdminState was last set to 'enabled'."
    ::= { tmnxOspfShamNbrStatsEntry 3 }

tmnxOspfShamNbrLsaInstallFail OBJECT-TYPE
    SYNTAX      Counter32
    MAX-ACCESS  read-only
    STATUS      current
    DESCRIPTION
        "The value of tmnxOspfShamNbrLsaInstallFail indicates the total
         number of times when an LSA could not be installed into the LSDB
         due to a resource allocation issue since tmnxOspfAdminState was 
         last set to 'enabled'."
    ::= { tmnxOspfShamNbrStatsEntry 4 }

tmnxOspfShamNbrBadSeqNums OBJECT-TYPE
    SYNTAX      Counter32
    MAX-ACCESS  read-only
    STATUS      current
    DESCRIPTION
        "The value of tmnxOspfShamNbrBadSeqNums indicates the total number 
         of times when a database description packet was received with a
         sequence number mismatch since tmnxOspfAdminState was last set to
         'enabled'."
    ::= { tmnxOspfShamNbrStatsEntry 5 }

tmnxOspfShamNbrBadMTUs OBJECT-TYPE
    SYNTAX      Counter32
    MAX-ACCESS  read-only
    STATUS      current
    DESCRIPTION
        "The value of tmnxOspfShamNbrBadMTUs indicates the total number
         of times when the MTU in a received database description packet
         was larger than the MTU of the receiving interface since
         tmnxOspfAdminState was last set to 'enabled'."
    ::= { tmnxOspfShamNbrStatsEntry 6 }

tmnxOspfShamNbrBadPackets OBJECT-TYPE
    SYNTAX      Counter32
    MAX-ACCESS  read-only
    STATUS      current
    DESCRIPTION
        "The value of tmnxOspfShamNbrBadPackets indicates the total number of
         times when an LS update was received with an illegal LS type or
         an option mismatch since tmnxOspfAdminState was last set to 
         'enabled'."
    ::= { tmnxOspfShamNbrStatsEntry 7 }

tmnxOspfShamNbrLsaNotInLsdbs OBJECT-TYPE
    SYNTAX      Counter32
    MAX-ACCESS  read-only
    STATUS      current
    DESCRIPTION
        "The value of tmnxOspfShamNbrLsaNotInLsdbs indicates the total
         number of times when an LS request was received for an LSA not
         installed in the LSDB of this router since tmnxOspfAdminState was
         last set to 'enabled'."
    ::= { tmnxOspfShamNbrStatsEntry 8 }

tmnxOspfShamNbrOptionMismatch OBJECT-TYPE
    SYNTAX      Counter32
    MAX-ACCESS  read-only
    STATUS      current
    DESCRIPTION
        "The value of tmnxOspfShamNbrOptionMismatch indicates the total
         number of times when a LS update was received with an option mismatch
         since tmnxOspfAdminState was last set to 'enabled'."
    ::= { tmnxOspfShamNbrStatsEntry 9 }

tmnxOspfShamNbrDuplicates OBJECT-TYPE
    SYNTAX      Counter32
    MAX-ACCESS  read-only
    STATUS      current
    DESCRIPTION
        "The value of tmnxOspfShamNbrDuplicates indicates the total number of
         times when a duplicate database description packet was received
         during the Exchange state since tmnxOspfAdminState was last set to
         'enabled'."
    ::= { tmnxOspfShamNbrStatsEntry 10 }

tmnxOspfShamNbrNumRestarts OBJECT-TYPE
    SYNTAX      Counter32
    MAX-ACCESS  read-only
    STATUS      current
    DESCRIPTION
        "The value of tmnxOspfShamNbrNumRestarts indicates the number
         of times the sham link neighbor has attempted restart since 
         tmnxOspfAdminState was last set to 'enabled'."
    ::= { tmnxOspfShamNbrStatsEntry 11 } 

-- OSPF Link-Scope Link State Database - next generation
--
-- The Link State Database contains the Link-Scope Link State
-- Advertisements from the links that the device is attached to.
-- This table supports multi-area adj OSPF (RFC 5185)

tmnxOspfNgLinkLsdbTable OBJECT-TYPE
    SYNTAX      SEQUENCE OF TmnxOspfNgLinkLsdbEntry
    MAX-ACCESS  not-accessible
    STATUS      current
    DESCRIPTION
        "The tmnxOspfNgLinkLsdbTable contains the OSPF Process's Link-Scope
         Link State Database."
    ::= { tmnxOspfObjects 30 }

tmnxOspfNgLinkLsdbEntry OBJECT-TYPE
    SYNTAX      TmnxOspfNgLinkLsdbEntry
    MAX-ACCESS  not-accessible
    STATUS      current
    DESCRIPTION
        "The tmnxOspfNgLinkLsdbEntry contains information for a single
         Link-Scope Link State Advertisement."
    INDEX       {   vRtrID,
                    tmnxOspfVersion,
                    tmnxOspfInstance,
                    tmnxOspfNgLinkLsdbIfIndex,
                    tmnxOspfNgLinkLsdbIfInstId,
                    tmnxOspfNgLinkLsdbIfAreaId,
                    tmnxOspfNgLinkLsdbType,
                    tmnxOspfNgLinkLsdbRouterId,
                    tmnxOspfNgLinkLsdbLsid
                }
    ::= { tmnxOspfNgLinkLsdbTable 1 }

TmnxOspfNgLinkLsdbEntry ::= SEQUENCE {
        tmnxOspfNgLinkLsdbIfIndex       InterfaceIndex,
        tmnxOspfNgLinkLsdbIfInstId      TmnxOspfIfInstIdTc,
        tmnxOspfNgLinkLsdbIfAreaId      TmnxOspfAreaIdTc,
        tmnxOspfNgLinkLsdbType          Unsigned32,
        tmnxOspfNgLinkLsdbRouterId      TmnxOspfRouterIdTc,
        tmnxOspfNgLinkLsdbLsid          Unsigned32,
        tmnxOspfNgLinkLsdbSequence      Integer32,
        tmnxOspfNgLinkLsdbAge           Integer32,
        tmnxOspfNgLinkLsdbChecksum      Integer32,
        tmnxOspfNgLinkLsdbAdvertisement OCTET STRING,
        tmnxOspfNgLinkLsdbTypeKnown     TruthValue
    }

tmnxOspfNgLinkLsdbIfIndex OBJECT-TYPE
    SYNTAX      InterfaceIndex
    MAX-ACCESS  not-accessible
    STATUS      current
    DESCRIPTION
        "The value of tmnxOspfNgLinkLsdbIfIndex specifies the identifier
         of the link from which the LSA was received."
    ::= { tmnxOspfNgLinkLsdbEntry 1 }

tmnxOspfNgLinkLsdbIfInstId OBJECT-TYPE
    SYNTAX      TmnxOspfIfInstIdTc
    MAX-ACCESS  not-accessible
    STATUS      current
    DESCRIPTION
        "The value of tmnxOspfNgLinkLsdbIfInstId specifies the identifier
         of the interface instance from which the LSA was received."
    ::= { tmnxOspfNgLinkLsdbEntry 2 }

tmnxOspfNgLinkLsdbIfAreaId  OBJECT-TYPE
    SYNTAX      TmnxOspfAreaIdTc
    MAX-ACCESS  not-accessible
    STATUS      current
    DESCRIPTION
        "The value of tmnxOspfNgLinkLsdbIfAreaId specifies
         specifies the OSPF Area Identifier."
    ::= { tmnxOspfNgLinkLsdbEntry 3 }

tmnxOspfNgLinkLsdbType OBJECT-TYPE
    SYNTAX      Unsigned32(0..'FFFFFFFF'h)
    MAX-ACCESS  not-accessible
    STATUS      current
    DESCRIPTION
        "The value of tmnxOspfNgLinkLsdbType specifies the type of the
         link state advertisement.  Each link state type has a separate
         advertisement format. Link-Scope LSAs unrecognized by the router
         are also stored in this database."
    ::= { tmnxOspfNgLinkLsdbEntry 4 }

tmnxOspfNgLinkLsdbRouterId OBJECT-TYPE
    SYNTAX      TmnxOspfRouterIdTc
    MAX-ACCESS  not-accessible
    STATUS      current
    DESCRIPTION
        "The value of tmnxOspfNgLinkLsdbRouterId specifies the 32-bit number
         that uniquely identifies the originating router in the Autonomous
         System."
    REFERENCE
        "OSPF Version 2, Appendix C.1 Global parameters"
    ::= { tmnxOspfNgLinkLsdbEntry 5 }

tmnxOspfNgLinkLsdbLsid OBJECT-TYPE
    SYNTAX      Unsigned32
    MAX-ACCESS  not-accessible
    STATUS      current
    DESCRIPTION
        "The value of tmnxOspfNgLinkLsdbLsid specifies the Link State ID that
         is an LS Type Specific field containing a unique identifier;
         it identifies the piece of the routing domain that is being
         described by the advertisement. In OSPFv3, the LSID has no
         addressing semantics."
    ::= { tmnxOspfNgLinkLsdbEntry 6 }

    -- Note that the OSPF Sequence Number is a 32 bit signed
    -- integer.  It starts with the value '80000001'h,
    -- or -'7FFFFFFF'h, and increments until '7FFFFFFF'h
    -- Thus, a typical sequence number will be very negative.

tmnxOspfNgLinkLsdbSequence OBJECT-TYPE
    SYNTAX      Integer32
    MAX-ACCESS  read-only
    STATUS      current
    DESCRIPTION
        "The value of tmnxOspfNgLinkLsdbSequence indicates the signed
         32-bit integer sequence number field. It is used to detect
         old and duplicate link-state advertisements. The space of
         sequence numbers is linearly ordered. The larger the sequence
         number the more recent the advertisement."
    REFERENCE
        "OSPF Version  2,  Section  12.1.6  LS  sequence
         number"
    ::= { tmnxOspfNgLinkLsdbEntry 7 }

tmnxOspfNgLinkLsdbAge OBJECT-TYPE
    SYNTAX      Integer32 -- Should be 0..'MaxAge'
                          -- unless 'DoNotAge' bit is set
    UNITS       "seconds"
    MAX-ACCESS  read-only
    STATUS      current
    DESCRIPTION
        "The value of tmnxOspfNgLinkLsdbAge indicates the age of the
         link-state advertisement in seconds."
    REFERENCE
        "OSPF Version 2, Section 12.1.1 LS age"
    ::= { tmnxOspfNgLinkLsdbEntry 8 }

tmnxOspfNgLinkLsdbChecksum OBJECT-TYPE
    SYNTAX      Integer32
    MAX-ACCESS  read-only
    STATUS      current
    DESCRIPTION
        "The value of tmnxOspfNgLinkLsdbChecksum indicates the checksum
         of the complete contents of the advertisement, excepting the
         age field. The age field is excepted so that an advertisement's
         age can be incremented without updating the checksum.  The
         checksum used is the same that is used for ISO connectionless
         datagrams; it is commonly referred to as the Fletcher checksum."
    REFERENCE
        "OSPF Version 2, Section 12.1.7 LS checksum"
    ::= { tmnxOspfNgLinkLsdbEntry 9 }

tmnxOspfNgLinkLsdbAdvertisement OBJECT-TYPE
    SYNTAX      OCTET STRING (SIZE (1..65535))
    MAX-ACCESS  read-only
    STATUS      current
    DESCRIPTION
        "The value of tmnxOspfNgLinkLsdbAdvertisement indicates the entire
         Link State Advertisement, including its header."
    ::= { tmnxOspfNgLinkLsdbEntry 10 }

tmnxOspfNgLinkLsdbTypeKnown OBJECT-TYPE
    SYNTAX      TruthValue
    MAX-ACCESS  read-only
    STATUS      current
    DESCRIPTION
        "The value of tmnxOspfNgLinkLsdbTypeKnown indicates whether the
         LSA type is recognized by this Router."
    ::= { tmnxOspfNgLinkLsdbEntry 11 }

--
-- OSPF Interface Table
-- This table supports multi-area adj OSPF (RFC 5185)
--

tmnxOspfNgIfTable OBJECT-TYPE
    SYNTAX          SEQUENCE OF TmnxOspfNgIfEntry
    MAX-ACCESS      not-accessible
    STATUS          current
    DESCRIPTION
        "The tmnxOspfNgIfTable contains information about the interfaces
         associated with OSPF."
    REFERENCE
        "OSPF Version 2, Appendix C.3 Router interface parameters"
    ::= { tmnxOspfObjects 31 }

tmnxOspfNgIfEntry OBJECT-TYPE
    SYNTAX          TmnxOspfNgIfEntry
    MAX-ACCESS      not-accessible
    STATUS          current
    DESCRIPTION
        "The tmnxOspfNgIfEntry contains information about one interface
         associated with OSPF."
    INDEX       {   vRtrID,
                    tmnxOspfVersion,
                    tmnxOspfInstance,
                    tmnxOspfNgIfIndex,
                    tmnxOspfNgIfInstId,
                    tmnxOspfNgIfAreaId
                }
    ::= { tmnxOspfNgIfTable 1 }

TmnxOspfNgIfEntry ::= SEQUENCE {
        tmnxOspfNgIfIndex                   InterfaceIndex,
        tmnxOspfNgIfInstId                  TmnxOspfIfInstIdTc,
        tmnxOspfNgIfAreaId                  TmnxOspfAreaIdTc,
        tmnxOspfNgIfStatus                  RowStatus,
        tmnxOspfNgIfLastChanged             TimeStamp,
        tmnxOspfNgIfCfgType                 TmnxOspfIfTypeTc,
        tmnxOspfNgIfAdminState              Status,
        tmnxOspfNgIfRtrPriority             DesignatedRouterPriority,
        tmnxOspfNgIfTransitDelay            TmnxOspfUpToRefreshIntervalTc,
        tmnxOspfNgIfRetransInterval         TmnxOspfUpToRefreshIntervalTc,
        tmnxOspfNgIfHelloInterval           HelloRange,
        tmnxOspfNgIfRtrDeadInterval         TmnxOspfDeadIntRangeTc,
        tmnxOspfNgIfPollInterval            Unsigned32,
        tmnxOspfNgIfCfgMTU                  Integer32,
        tmnxOspfNgIfCfgMetric               Metric,
        tmnxOspfNgIfPassive                 TruthValue,
        tmnxOspfNgIfAdvtSubnet              TruthValue,
        tmnxOspfNgIfAuthType                TmnxOspfAuthenticationType,
        tmnxOspfNgIfAuthKey                 OCTET STRING,
        tmnxOspfNgIfEnableBfd               TruthValue,
        tmnxOspfNgIfRemainDownOnFail        TruthValue,
        tmnxOspfNgIfInboundSAName           TNamedItemOrEmpty,
        tmnxOspfNgIfOutboundSAName          TNamedItemOrEmpty,
        tmnxOspfNgIfLoopfreeAltExclude      TruthValue,
        tmnxOspfNgIfLsaFilterOut            TmnxOspfLsaFilterOutTc,
        tmnxOspfNgIfAdvRtrCapability        TruthValue,
        tmnxOspfNgIfAuthKeyChain            TNamedItemOrEmpty,
        tmnxOspfNgIfRouteNHTemplate         TNamedItemOrEmpty
    }

tmnxOspfNgIfIndex OBJECT-TYPE
    SYNTAX      InterfaceIndex
    MAX-ACCESS  not-accessible
    STATUS      current
    DESCRIPTION
        "The value of tmnxOspfNgIfIndex specifies the interface index of
         this OSPF interface.  It corresponds to the interface index of the
         IP interface on which OSPF is configured."
    ::= { tmnxOspfNgIfEntry 1 }

tmnxOspfNgIfInstId OBJECT-TYPE
    SYNTAX      TmnxOspfIfInstIdTc
    MAX-ACCESS  not-accessible
    STATUS      current
    DESCRIPTION
        "The value of tmnxOspfNgIfInstId specifies the OSPF instance.  It
         enables multiple interface instances of OSPF to be run over a
         single link. Each protocol instance would be assigned a separate
         ID. This ID has local link significance only."
    ::= { tmnxOspfNgIfEntry 2 }

tmnxOspfNgIfAreaId OBJECT-TYPE
    SYNTAX      TmnxOspfAreaIdTc
    MAX-ACCESS  not-accessible
    STATUS      current
    DESCRIPTION
        "The value of tmnxOspfNgIfAreaId specifies a 32-bit integer uniquely
         identifying the area to which the interface connects. Area ID
         0 is used for the OSPF backbone."
    ::= { tmnxOspfNgIfEntry 3 }

tmnxOspfNgIfStatus OBJECT-TYPE
    SYNTAX      RowStatus
    MAX-ACCESS  read-create
    STATUS      current
    DESCRIPTION
        "The value of tmnxOspfNgIfStatus controls creation and deletion of
         a row entry in this table."
    ::= { tmnxOspfNgIfEntry 4 }

tmnxOspfNgIfLastChanged  OBJECT-TYPE
    SYNTAX      TimeStamp
    MAX-ACCESS  read-only
    STATUS      current
    DESCRIPTION
        "The value of tmnxOspfNgIfLastChanged indicates the sysUpTime
         when a configurable object in this row was last modified."
    ::= { tmnxOspfNgIfEntry 5 }

tmnxOspfNgIfCfgType OBJECT-TYPE
    SYNTAX      TmnxOspfIfTypeTc
    MAX-ACCESS  read-create
    STATUS      current
    DESCRIPTION
        "The value of tmnxOspfNgIfCfgType specifies the OSPF interface type.

         The value of 'unspecified' sets the interface type to its
         default value based on the underlying physical interface type."
    ::= { tmnxOspfNgIfEntry 6 }

tmnxOspfNgIfAdminState OBJECT-TYPE
    SYNTAX      Status
    MAX-ACCESS  read-create
    STATUS      current
    DESCRIPTION
        "The value of tmnxOspfNgIfAdminState specifies the OSPF interface's
         administrative status.  The value formed on the interface, and the
         interface will be advertised as an internal route to some area.
         The value 'disabled' denotes that the interface is external to OSPF."
    DEFVAL { enabled }
    ::= { tmnxOspfNgIfEntry 7 }

tmnxOspfNgIfRtrPriority OBJECT-TYPE
    SYNTAX      DesignatedRouterPriority
    MAX-ACCESS  read-create
    STATUS      current
    DESCRIPTION
        "The value of tmnxOspfNgIfRtrPriority specifies the priority of
         this interface.  Used in multi-access networks, this field is
         used in the designated router election algorithm. The value 0
         signifies that the router is not eligible to become the designated
         router on this particular network. In the event of a tie in
         this value, routers will use their Router ID as a tie breaker."
    DEFVAL { 1 }
    ::= { tmnxOspfNgIfEntry 8 }

tmnxOspfNgIfTransitDelay OBJECT-TYPE
    SYNTAX      TmnxOspfUpToRefreshIntervalTc (1..1800)
    UNITS       "seconds"
    MAX-ACCESS  read-create
    STATUS      current
    DESCRIPTION
        "The value of tmnxOspfNgIfTransitDelay specifies the estimated
         number of seconds it takes to transmit a link state update packet
         over this interface."
    DEFVAL { 1 }
    ::= { tmnxOspfNgIfEntry 9 }

tmnxOspfNgIfRetransInterval OBJECT-TYPE
    SYNTAX      TmnxOspfUpToRefreshIntervalTc (1..1800)
    UNITS       "seconds"
    MAX-ACCESS  read-create
    STATUS      current
    DESCRIPTION
        "The value of tmnxOspfNgIfRetransInterval specifies the number of
         seconds between link state advertisement retransmissions, for
         adjacencies belonging to this interface. This value is also used
         when retransmitting database description and link state request
         packets."
    DEFVAL { 5 }
    ::= { tmnxOspfNgIfEntry 10 }

tmnxOspfNgIfHelloInterval OBJECT-TYPE
    SYNTAX      HelloRange
    UNITS       "seconds"
    MAX-ACCESS  read-create
    STATUS      current
    DESCRIPTION
        "The value of tmnxOspfNgIfHelloInterval specifies the length of time,
         in seconds, between the Hello packets that the router sends on the
         interface.  This value MUST be the same for all routers attached to
         a common network."
    DEFVAL { 10 }
    ::= { tmnxOspfNgIfEntry 11 }

tmnxOspfNgIfRtrDeadInterval OBJECT-TYPE
    SYNTAX      TmnxOspfDeadIntRangeTc
    UNITS       "seconds"
    MAX-ACCESS  read-create
    STATUS      current
    DESCRIPTION
        "The value of tmnxOspfNgIfRtrDeadInterval specifies the number of
         seconds that a router's Hello packets have not been seen before
         its neighbors declare the router down on the interface.  This
         should be some multiple of the Hello interval."
    DEFVAL { 40 }
    ::= { tmnxOspfNgIfEntry 12 }

tmnxOspfNgIfPollInterval OBJECT-TYPE
    SYNTAX      Unsigned32
    UNITS       "seconds"
    MAX-ACCESS  read-create
    STATUS      current
    DESCRIPTION
        "The value of tmnxOspfNgIfPollInterval specifies the larger time
         interval, in seconds, between the Hello packets sent to an inactive
         non-broadcast multi-access neighbor."
    DEFVAL { 120 }
    ::= { tmnxOspfNgIfEntry 13 }

tmnxOspfNgIfCfgMTU OBJECT-TYPE
    SYNTAX      Integer32 (0 | 512..9198)
    MAX-ACCESS  read-create
    STATUS      current
    DESCRIPTION
        "The value of tmnxOspfNgIfCfgMTU specifies the desired size of the
         largest packet which can be sent/received on this OSPF interface,
         specified in octets. This size DOES include the underlying IP
         header length, but not the underlying layer headers/trailers.

         Setting tmnxOspfNgIfCfgMTU to a value of zero (0), causes the agent
         to recalculate the default MTU size which can vary based on the
         current setting of tmnxPortMode and tmnxPortEncapType variables
         for the port to which this OSPF interface is bound."
    DEFVAL { 0 }
    ::= { tmnxOspfNgIfEntry 14 }

tmnxOspfNgIfCfgMetric OBJECT-TYPE
    SYNTAX      Metric
    MAX-ACCESS  read-create
    STATUS      current
    DESCRIPTION
        "The value of tmnxOspfNgIfCfgMetric specifies the desired
         metric value assigned to this interface.  The default value
         '0' causes the value of the Metric to be calculated as
         (Reference Bandwidth / ifSpeed).  The value of the reference
         bandwidth is configured by the tmnxOspfReferenceBandwidth object."
    DEFVAL { 0 }
    ::= { tmnxOspfNgIfEntry 15 }

tmnxOspfNgIfPassive OBJECT-TYPE
    SYNTAX      TruthValue
    MAX-ACCESS  read-create
    STATUS      current
    DESCRIPTION
        "The value of tmnxOspfNgIfPassive specifies whether or or not HELLOs
         are to be sent out on this interface and whether or not the router
         advertises it as STUB network/link in its router LSAs.  If true, no
         HELLOs will be sent, and the interface is advertised as a STUB link."
    DEFVAL { false }
    ::= { tmnxOspfNgIfEntry 16 }

tmnxOspfNgIfAdvtSubnet OBJECT-TYPE
    SYNTAX      TruthValue
    MAX-ACCESS  read-create
    STATUS      current
    DESCRIPTION
        "The value of tmnxOspfNgIfAdvtSubnet specifies the advertisement
         method.  When tmnxOspfNgIfAdvtSubnet is set to 'true', OSPF will
         advertise the network number and netmask instead of the
         individual host-routes of an active point-to-point interface."
    REFERENCE
        "RFC2328 OSPF Version 2, s12.4.1.1 pg130"
    DEFVAL { true }
    ::= { tmnxOspfNgIfEntry 17 }

tmnxOspfNgIfAuthType OBJECT-TYPE
    SYNTAX       TmnxOspfAuthenticationType
    MAX-ACCESS   read-create
    STATUS       current
    DESCRIPTION
        "The value of tmnxOspfNgIfAuthType specifies the authentication
         type to use for an interface.

         Note that this object can be used to engage in significant attacks
         against an OSPF router."
    REFERENCE
        "OSPF Version 2, Appendix D Authentication"
    DEFVAL { none } -- no authentication, by default
    ::= { tmnxOspfNgIfEntry 18 }

tmnxOspfNgIfAuthKey OBJECT-TYPE
    SYNTAX      OCTET STRING (SIZE (0..8))
    MAX-ACCESS  read-create
    STATUS      current
    DESCRIPTION
        "The value of tmnxOspfNgIfAuthKey specifies the authentication key
         string.  The cleartext password is used as an OSPF Authentication
         key when simplePassword security is enabled. This object does not
         access any OSPF Cryptographic (e.g. MD5) Authentication Key under
         any circumstance.

         If the key length is shorter than 8 octets, the agent will left
         adjust and zero fill to 8 octets.

         Unauthenticated interfaces need no authentication key, and simple
         password authentication cannot use a key of more than 8 octets.

         Note that the use of simplePassword authentication is NOT recommended
         when there is concern regarding attack upon the OSPF system.
         This authentication is only sufficient to protect against
         accidental misconfigurations because it re-uses cleartext passwords.
         [RFC-1704]

         When read, tmnxOspfNgIfAuthKey always returns an Octet String of
         length zero.

         This object is valid only when tmnxOspfVersion has a value of
         'version2'."
    REFERENCE
        "OSPF Version 2, Section 9 The Interface Data Structure"
    DEFVAL { '0000000000000000'H } -- 0.0.0.0.0.0.0.0
    ::= { tmnxOspfNgIfEntry 19 }

tmnxOspfNgIfEnableBfd       OBJECT-TYPE
    SYNTAX      TruthValue
    MAX-ACCESS  read-create
    STATUS      current
    DESCRIPTION
        "The value of tmnxOspfNgIfEnableBfd specifies whether Bi-directional
         Forwarding Detection is enabled for Ipv4 in this OSPF interface.

         When the value is 'true', this interface can establish BFD sessions
         and use BFD as a signalling mechanism. When it is 'false', it cannot
         use BFD for Ipv4."
    DEFVAL { false }
    ::= { tmnxOspfNgIfEntry 20 }

tmnxOspfNgIfRemainDownOnFail      OBJECT-TYPE
    SYNTAX      TruthValue
    MAX-ACCESS  read-create
    STATUS      current
    DESCRIPTION
        "The value of tmnxOspfNgIfRemainDownOnFail specifies whether an OSPF
         adjacency should go down when the BFD session to the peer goes
         down."
    DEFVAL { false }
    ::= { tmnxOspfNgIfEntry 21 }

tmnxOspfNgIfInboundSAName  OBJECT-TYPE
    SYNTAX      TNamedItemOrEmpty
    MAX-ACCESS  read-create
    STATUS      current
    DESCRIPTION
        "The value of tmnxOspfNgIfInboundSAName specifies the manually
         configured IPsec Security Association name in case the Ospfv3 traffic
         on the [interface] has to be authenticated.

         This object is only valid when tmnxOspfVersion has a value of
         'version3'."
    DEFVAL { ''H }   -- the empty string
    ::= { tmnxOspfNgIfEntry 22 }

tmnxOspfNgIfOutboundSAName  OBJECT-TYPE
    SYNTAX      TNamedItemOrEmpty
    MAX-ACCESS  read-create
    STATUS      current
    DESCRIPTION
        "The value of tmnxOspfNgIfOutboundSAName specifies the manually
         configured IPsec Security Association name in case the Ospfv3 traffic
         on the [interface] has to be authenticated.

         This object is only valid when tmnxOspfVersion has a value of
         'version3'."
    DEFVAL { ''H }   -- the empty string
    ::= { tmnxOspfNgIfEntry 23 }

tmnxOspfNgIfLoopfreeAltExclude OBJECT-TYPE
    SYNTAX      TruthValue
    MAX-ACCESS  read-create
    STATUS      current
    DESCRIPTION
        "The value of tmnxOspfNgIfLoopfreeAltExclude specifies whether or not
         the OSPF interface should be excluded during LFA calculations. If the 
         value is 'true', the OSPF interface is excluded from LFA calculations. 
         If the value is 'false', the OSPF interface is included in LFA 
         calculations. 
         
         The value of tmnxOspfNgIfLoopfreeAltExclude is only valid when 
         tmnxOspfLoopfreeAlternate has a value of 'true'."
    DEFVAL { false }
    ::= { tmnxOspfNgIfEntry 24 }

tmnxOspfNgIfLsaFilterOut OBJECT-TYPE
    SYNTAX      TmnxOspfLsaFilterOutTc
    MAX-ACCESS  read-create
    STATUS      current
    DESCRIPTION
        "The value of tmnxOspfNgIfLsaFilterOut specifies whether or not
         flooded LSA's should be sent to any adjacent neighbor on the OSPF
         interface.
         
         If the value is 'none', then flooded LSA's are sent out on the 
         OSPF interface.
         
         If the value is 'all', then flooded LSA's are not sent out on the 
         OSPF interface.
         
         If the value is 'exceptOwnRtrLsa', then no LSA's other than own router
         LSA's are sent out on the OSPF interface.
         
         If the value is 'exceptOwnRtrLsaAndDefaults', then no LSA's other than
         type-3-default, type-5-default, type-7-default and own router LSA's are
         sent out on the OSPF interface."
    DEFVAL { none }
    ::= { tmnxOspfNgIfEntry 25 }

tmnxOspfNgIfAdvRtrCapability OBJECT-TYPE
    SYNTAX      TruthValue
    MAX-ACCESS  read-create
    STATUS      current
    DESCRIPTION
        "The value of tmnxOspfNgIfAdvRtrCapability specifies whether or not
         advertise-router-capabilities are enabled at interface level."
    DEFVAL { true }
    ::= { tmnxOspfNgIfEntry 26 }

tmnxOspfNgIfAuthKeyChain OBJECT-TYPE
    SYNTAX      TNamedItemOrEmpty
    MAX-ACCESS  read-create
    STATUS      current
    DESCRIPTION
        "The value of tmnxOspfNgIfAuthKeyChain specifies the
         keychain which will be used to sign and/or authenticate the OSPF
         protocol stream.

         The keychain name is defined by tmnxKeyChainName and is the index for
         TIMETRA-SECURITY-MIB::tmnxKeyChainTable."
    DEFVAL { ''H }
    ::= { tmnxOspfNgIfEntry 27 }

tmnxOspfNgIfRouteNHTemplate  OBJECT-TYPE
    SYNTAX      TNamedItemOrEmpty
    MAX-ACCESS  read-create
    STATUS      current
    DESCRIPTION
        "The value of tmnxOspfNgIfRouteNHTemplate specifies the
         next-hop template that must be applied to the prefixes
         which primary next-hop uses this interface name.

         The next-hop template name is defined by tmnxRouteNHTemplateName
         and is the index for 
         TIMETRA-ROUTE-NEXT-HOP-TEMPLATE-MIB::tmnxRouteNHTemplateTable."
    DEFVAL { ''H }
    ::= { tmnxOspfNgIfEntry 28 }

--
--  Augmentation of the tmnxOspfNgIfTable.
--  Use of AUGMENTS clause implies a one-to-one dependent relationship between
--  the base table, tmnxOspIfTable, and the augmenting table,
--  tmnxOspfNgIfOperTable.
--
--  This in effect extends the tmnxOspfNgIfTable with additional columns.
--  Creation (or deletion) of a row in the tmnxOspfNgIfTable results in
--  the same fate for the row in the tmnxOspfNgIfOperTable.
--
tmnxOspfNgIfOperTable OBJECT-TYPE
    SYNTAX      SEQUENCE OF TmnxOspfNgIfOperEntry
    MAX-ACCESS  not-accessible
    STATUS      current
    DESCRIPTION
        "The tmnxOspfNgIfOperTable provides an extension of the
         tmnxOspfNgIfTable for operational states of an OSPF interface."
    ::= { tmnxOspfObjects 32 }

tmnxOspfNgIfOperEntry OBJECT-TYPE
    SYNTAX      TmnxOspfNgIfOperEntry
    MAX-ACCESS  not-accessible
    STATUS      current
    DESCRIPTION
        "Each row entry in the tmnxOspfNgIfOperTable represents
         additional columns for statistics for an OSPF interface."
    AUGMENTS { tmnxOspfNgIfEntry }
   ::= { tmnxOspfNgIfOperTable 1 }

TmnxOspfNgIfOperEntry ::=
    SEQUENCE {
        tmnxOspfNgIfState                   INTEGER,
        tmnxOspfNgIfLastEnabledTime         TimeStamp,
        tmnxOspfNgIfOperMTU                 Integer32,
        tmnxOspfNgIfMetricValue             Metric,
        tmnxOspfNgIfDRId                    TmnxOspfRouterIdTc,
        tmnxOspfNgIfDRIpAddrType            InetAddressType,
        tmnxOspfNgIfDRIpAddr                InetAddress,
        tmnxOspfNgIfBDRId                   TmnxOspfRouterIdTc,
        tmnxOspfNgIfBDRIpAddrType           InetAddressType,
        tmnxOspfNgIfBDRIpAddr               InetAddress,
        tmnxOspfNgIfLinkLsaCount            Gauge32,
        tmnxOspfNgIfLinkLsaCksumSum         Integer32,
        tmnxOspfNgIfMD5TransmitKeyId        TmnxOspfIfMD5KeyId,
        tmnxOspfNgIfLocalIpAddressType      InetAddressType,
        tmnxOspfNgIfLocalIpAddress          InetAddress,
        tmnxOspfNgIfMD5NumKeys              Gauge32,
        tmnxOspfNgIfType                    TmnxOspfIfTypeTc,
        tmnxOspfNgIfTeMetric                Unsigned32,
        tmnxOspfNgIfTeState                 TmnxOperState,
        tmnxOspfNgIfAdminGroup              Unsigned32,
        tmnxOspfNgIfLdpSyncState            TmnxOperState,
        tmnxOspfNgIfLdpSyncMaxMetric        TruthValue,
        tmnxOspfNgIfLdpSyncTimerState       INTEGER,
        tmnxOspfNgIfLdpSyncTimeLeft         Unsigned32,
        tmnxOspfNgIfOperInbSAName           TNamedItemOrEmpty,
        tmnxOspfNgIfOperInbSANameTemp       TNamedItemOrEmpty,
        tmnxOspfNgIfOperOutbSAName          TNamedItemOrEmpty
    }

tmnxOspfNgIfState OBJECT-TYPE
    SYNTAX      INTEGER {
                    down(1),
                    loopback(2),
                    waiting(3),
                    pointToPoint(4),
                    designatedRouter(5),
                    backupDesignatedRouter(6),
                    otherDesignatedRouter(7)
                }
    MAX-ACCESS  read-only
    STATUS      current
    DESCRIPTION
        "The OSPF Interface State."
    ::= { tmnxOspfNgIfOperEntry 1 }

tmnxOspfNgIfLastEnabledTime OBJECT-TYPE
    SYNTAX      TimeStamp
    MAX-ACCESS  read-only
    STATUS      current
    DESCRIPTION
        "The value of tmnxOspfNgIfLastEnabledTime indicates the sysUpTime
         value when ospfIfAdminStat was last set to enabled (1) to
         run the ospf on this interface."
    ::= { tmnxOspfNgIfOperEntry 2 }

tmnxOspfNgIfOperMTU OBJECT-TYPE
    SYNTAX      Integer32
    MAX-ACCESS  read-only
    STATUS      current
    DESCRIPTION
        "The value of tmnxOspfNgIfOperMTU indicates the operational size
         of the largest packet which can be sent/received on this OSPF
         interface, specified in octets.
         This size DOES include the underlying IP header length,
         but not the underlying layer headers/trailers."
    ::= { tmnxOspfNgIfOperEntry 3 }

tmnxOspfNgIfMetricValue OBJECT-TYPE
    SYNTAX      Metric
    MAX-ACCESS  read-only
    STATUS      current
    DESCRIPTION
        "The value of tmnxOspfNgIfMetricValue indicates the metric value
         this interface is using.  The default value of the Metric is
         (Reference Bandwidth / ifSpeed).  The value of the reference
         bandwidth is configured by the tmnxOspfReferenceBandwidth object."
    ::= { tmnxOspfNgIfOperEntry 4 }

tmnxOspfNgIfDRId      OBJECT-TYPE
    SYNTAX      TmnxOspfRouterIdTc
    MAX-ACCESS  read-only
    STATUS      current
    DESCRIPTION
        "The value of tmnxOspfNgIfDRId indicates the Router ID of the
         Designated Router."
    ::= { tmnxOspfNgIfOperEntry 5 }

tmnxOspfNgIfDRIpAddrType OBJECT-TYPE
    SYNTAX      InetAddressType
    MAX-ACCESS  read-only
    STATUS      current
    DESCRIPTION
        "The value of tmnxOspfNgIfDRIpAddrType type indicates the IP address
         type of tmnxOspfNgIfDRIpAddr. For IPv6 type addresses only addresses
         with zone index are expected."
    ::= { tmnxOspfNgIfOperEntry 6 }

tmnxOspfNgIfDRIpAddr    OBJECT-TYPE
    SYNTAX      InetAddress (SIZE (0|4|20))
    MAX-ACCESS  read-only
    STATUS      current
    DESCRIPTION
        "The value of tmnxOspfNgIfDRIpAddr indicates the IP address of
         the Designated Router."
    ::= { tmnxOspfNgIfOperEntry 7 }

tmnxOspfNgIfBDRId     OBJECT-TYPE
    SYNTAX      TmnxOspfRouterIdTc
    MAX-ACCESS  read-only
    STATUS      current
    DESCRIPTION
        "The value of tmnxOspfNgIfBDRId indicates the Router ID of the
         Backup Designated Router."
    ::= { tmnxOspfNgIfOperEntry 8 }

tmnxOspfNgIfBDRIpAddrType OBJECT-TYPE
    SYNTAX      InetAddressType
    MAX-ACCESS  read-only
    STATUS      current
    DESCRIPTION
        "The value of tmnxOspfNgIfBDRIpAddrType indicates the IP address
         type of the Backup Designated Router. For IPv6 type addresses
         only addresses with zone index are expected."
    ::= { tmnxOspfNgIfOperEntry 9 }

tmnxOspfNgIfBDRIpAddr     OBJECT-TYPE
    SYNTAX      InetAddress (SIZE (0|4|20))
    MAX-ACCESS  read-only
    STATUS      current
    DESCRIPTION
        "The value of tmnxOspfNgIfBDRIpAddr indicates the IP address of
         the Backup Designated Router."
    ::= { tmnxOspfNgIfOperEntry 10 }

tmnxOspfNgIfLinkLsaCount OBJECT-TYPE
    SYNTAX      Gauge32
    MAX-ACCESS  read-only
    STATUS      current
    DESCRIPTION
        "The value of tmnxOspfNgIfLinkLsaCount indicates the total
         number of Link-Scope link-state advertisements in this link's
         link-state database."
    ::= { tmnxOspfNgIfOperEntry 11 }

tmnxOspfNgIfLinkLsaCksumSum OBJECT-TYPE
    SYNTAX      Integer32
    MAX-ACCESS  read-only
    STATUS      current
    DESCRIPTION
        "The value of tmnxOspfNgIfLinkLsaCksumSum indicates the 32-bit
         unsigned sum of the Link-Scope link-state advertisements' LS
         checksums contained in this link's link-state database.  The
         sum can be used to determine if there has been a change in a
         router's link-state database, and to compare the link state
         database of two routers."
    ::= { tmnxOspfNgIfOperEntry 12 }

tmnxOspfNgIfMD5TransmitKeyId    OBJECT-TYPE
    SYNTAX      TmnxOspfIfMD5KeyId
    MAX-ACCESS  read-only
    STATUS      current
    DESCRIPTION
        "The value of tmnxOspfNgIfMD5TransmitKeyId indicates the index value
         used to access the row entry in the tmnxOspfNgIfMD5KeyTable that
         specifies the authentication type and key transmitted on this
         OSPF interface.  This object is valid only when tmnxOspfVersion
         has the value 'version2'.

         If tmnxOspfNgIfMD5TransmitKeyId has a value of 0, it means that no
         keys are configured."
    ::= { tmnxOspfNgIfOperEntry 13 }

tmnxOspfNgIfLocalIpAddressType OBJECT-TYPE
    SYNTAX      InetAddressType
    MAX-ACCESS  read-only
    STATUS      current
    DESCRIPTION
        "The value of tmnxOspfNgIfLocalIpAddressType indicates the IP address
         type of tmnxOspfNgIfLocalIpAddress. For IPv6 type addresses only
         addresses with zone index are expected."
    ::= { tmnxOspfNgIfOperEntry 14 }

tmnxOspfNgIfLocalIpAddress OBJECT-TYPE
    SYNTAX      InetAddress (SIZE (0|4|20))
    MAX-ACCESS  read-only
    STATUS      current
    DESCRIPTION
        "The value of tmnxOspfNgIfLocalIpAddress indicates the IP address of
         this OSPF local link interface."
    ::= { tmnxOspfNgIfOperEntry 15 }

tmnxOspfNgIfMD5NumKeys OBJECT-TYPE
    SYNTAX      Gauge32
    MAX-ACCESS  read-only
    STATUS      current
    DESCRIPTION
        "The value of tmnxOspfNgIfMD5NumKeys indicates the number of MD5 Key
         entries for this OSPF interface."
    ::= { tmnxOspfNgIfOperEntry 16 }

tmnxOspfNgIfType OBJECT-TYPE
    SYNTAX      TmnxOspfIfTypeTc
    MAX-ACCESS  read-only
    STATUS      current
    DESCRIPTION
        "The value of tmnxOspfNgIfType indicates the operational
         OSPF interface type."
    ::= { tmnxOspfNgIfOperEntry 17 }

tmnxOspfNgIfTeMetric  OBJECT-TYPE
    SYNTAX      Unsigned32 (0..16777215)
    MAX-ACCESS  read-only
    STATUS      current
    DESCRIPTION
        "The value of tmnxOspfNgIfTeMetric indicates
         the MPLS TE metric configured for this interface. This metric is
         flooded out in the TE metric sub-tlv in the OSPF TE LSAs.
         Depending on the configuration, either the TE metric
         value or the native OSPF metric value is used in CSPF computations."
    ::= { tmnxOspfNgIfOperEntry 18 }

tmnxOspfNgIfTeState  OBJECT-TYPE
    SYNTAX      TmnxOperState
    MAX-ACCESS  read-only
    STATUS      current
    DESCRIPTION
        "The value of tmnxOspfNgIfTeState indicates the MPLS interface TE status
         from OSPF standpoint."
    ::= { tmnxOspfNgIfOperEntry 19 }

tmnxOspfNgIfAdminGroup  OBJECT-TYPE
    SYNTAX      Unsigned32
    MAX-ACCESS  read-only
    STATUS      current
    DESCRIPTION
        "The value of tmnxOspfNgIfAdminGroup indicates the bit-map inherited
         from MPLS interface that identifies the admin groups to which this
         interface belongs. If bit 'n' is set, then the interface belongs to
         the admin group with value 'n'."
    ::= { tmnxOspfNgIfOperEntry 20 }

tmnxOspfNgIfLdpSyncState  OBJECT-TYPE
    SYNTAX      TmnxOperState
    MAX-ACCESS  read-only
    STATUS      current
    DESCRIPTION
        "The value of tmnxOspfNgIfLdpSyncState indicates if IGP-LDP
         synchronization is enabled on this interface. tmnxOspfNgIfLdpSyncState
         is derived from tmnxOspfLdpSyncAdminState and also whether it was
         enabled at the IP layer from OSPF standpoint."
    ::= { tmnxOspfNgIfOperEntry 21 }

tmnxOspfNgIfLdpSyncMaxMetric   OBJECT-TYPE
    SYNTAX      TruthValue
    MAX-ACCESS  read-only
    STATUS      current
    DESCRIPTION
        "The value of tmnxOspfNgIfLdpSyncMaxMetric indicates if OSPF
         advertised maximum metric value for the interface, depending on
         whether tmnxOspfNgIfLdpSyncState is enabled on this interface."
    ::= { tmnxOspfNgIfOperEntry 22 }

tmnxOspfNgIfLdpSyncTimerState   OBJECT-TYPE
    SYNTAX      INTEGER {
                    waitForLdpAdj (1), -- Waiting for LDP adj to come up
                    timerActive (2),   -- LDP adj up (sync timer running)
                    ldpExchgDone (3),  -- LDP label exchange done
                    timerExpired (4),  -- Sync timer expired
                    manualExit (5),    -- User intervened for sync termination
                    disabled (6)       -- LDP Sync is not being done
                }
    MAX-ACCESS  read-only
    STATUS      current
    DESCRIPTION
        "The value of tmnxOspfNgIfLdpSyncTimerState indicates the state of the
         tmnxOspfNgIfLdpSyncTimeLeft on this OSPF interface."
    ::= { tmnxOspfNgIfOperEntry 23 }

tmnxOspfNgIfLdpSyncTimeLeft  OBJECT-TYPE
    SYNTAX      Unsigned32 (0|1..1800)
    UNITS       "seconds"
    MAX-ACCESS  read-only
    STATUS      current
    DESCRIPTION
        "The value of tmnxOspfNgIfLdpSyncTimeLeft indicates the time left
         before OSPF reverts back to advertising normal metric for this
         interface. This is applicable only when tmnxOspfNgIfLdpSyncMaxMetric
         is 'true'."
    ::= { tmnxOspfNgIfOperEntry 24 }

tmnxOspfNgIfOperInbSAName  OBJECT-TYPE
    SYNTAX      TNamedItemOrEmpty
    MAX-ACCESS  read-only
    STATUS      current
    DESCRIPTION
        "The value of tmnxOspfNgIfOperInbSAName indicates the name of the
         operational inbound manual IPsec Security Association, used for
         authenticating inbound Ospfv3 traffic."
    DEFVAL { ''H }   -- the empty string
    ::= { tmnxOspfNgIfOperEntry 25 }

tmnxOspfNgIfOperInbSANameTemp  OBJECT-TYPE
    SYNTAX      TNamedItemOrEmpty
    MAX-ACCESS  read-only
    STATUS      current
    DESCRIPTION
        "The value of tmnxOspfNgIfOperInbSANameTemp indicates the name of a
         temporary operational inbound manual IPsec Security Association, used
         for authenticating inbound Ospfv3 traffic.

         This field can only contain a value when the key-rollover mechanism is
         ongoing."
    DEFVAL { ''H }   -- the empty string
    ::= { tmnxOspfNgIfOperEntry 26 }

tmnxOspfNgIfOperOutbSAName  OBJECT-TYPE
    SYNTAX      TNamedItemOrEmpty
    MAX-ACCESS  read-only
    STATUS      current
    DESCRIPTION
        "The value of tmnxOspfNgIfOperOutbSAName indicates the name of the
         operational outbound manual IPsec Security Association, used for
         authenticating outbound Ospfv3 traffic. When the key-rollover mechanism
         is ongoing, the value can temporarely be different from the value of
         the tmnxOspfNgIfOutboundSAName field."
    DEFVAL { ''H }   -- the empty string
    ::= { tmnxOspfNgIfOperEntry 27 }

--
--  Augmentation of the tmnxOspfNgIfTable.
--  Use of AUGMENTS clause implies a one-to-one dependent relationship between
--  the base table, tmnxOspIfTable, and the augmenting table,
--  tmnxOspfNgIfStatsTable.
--
--  This in effect extends the tmnxOspfNgIfTable with additional columns.
--  Creation (or deletion) of a row in the tmnxOspfNgIfTable results in
--  the same fate for the row in the tmnxOspfNgIfStatsTable.
--
tmnxOspfNgIfStatsTable OBJECT-TYPE
    SYNTAX      SEQUENCE OF TmnxOspfNgIfStatsEntry
    MAX-ACCESS  not-accessible
    STATUS      current
    DESCRIPTION
        "The tmnxOspfNgIfStatsTable provides an extension of the
         tmnxOspfNgIfTable for statistics for an OSPF interface."
    ::= { tmnxOspfObjects 33 }

tmnxOspfNgIfStatsEntry OBJECT-TYPE
    SYNTAX      TmnxOspfNgIfStatsEntry
    MAX-ACCESS  not-accessible
    STATUS      current
    DESCRIPTION
        "Each row entry in the tmnxOspfNgIfStatsTable represents
         additional columns for statistics for an OSPF interface."
    AUGMENTS { tmnxOspfNgIfEntry }
   ::= { tmnxOspfNgIfStatsTable 1 }

TmnxOspfNgIfStatsEntry ::=
    SEQUENCE {
        tmnxOspfNgIfEvents                  Counter32,
        tmnxOspfNgIfTxPackets               Counter32,
        tmnxOspfNgIfTxHellos                Counter32,
        tmnxOspfNgIfTxDBDs                  Counter32,
        tmnxOspfNgIfTxLSRs                  Counter32,
        tmnxOspfNgIfTxLSUs                  Counter32,
        tmnxOspfNgIfTxLSAcks                Counter32,
        tmnxOspfNgIfRxPackets               Counter32,
        tmnxOspfNgIfRxHellos                Counter32,
        tmnxOspfNgIfRxDBDs                  Counter32,
        tmnxOspfNgIfRxLSRs                  Counter32,
        tmnxOspfNgIfRxLSUs                  Counter32,
        tmnxOspfNgIfRxLSAcks                Counter32,
        tmnxOspfNgIfDiscardPackets          Counter32,
        tmnxOspfNgIfRetransmitOuts          Counter32,
        tmnxOspfNgIfBadVersions             Counter32,
        tmnxOspfNgIfBadNetworks             Counter32,
        tmnxOspfNgIfBadVirtualLinks         Counter32,
        tmnxOspfNgIfBadAreas                Counter32,
        tmnxOspfNgIfBadDstAddrs             Counter32,
        tmnxOspfNgIfBadNeighbors            Counter32,
        tmnxOspfNgIfBadPacketTypes          Counter32,
        tmnxOspfNgIfNeighborCount           Integer32,
        tmnxOspfNgIfLastEventTime           TimeStamp,
        tmnxOspfNgIfBadLengths              Counter32,
        tmnxOspfNgIfBadHelloIntervals       Counter32,
        tmnxOspfNgIfBadDeadIntervals        Counter32,
        tmnxOspfNgIfBadOptions              Counter32,
        tmnxOspfNgIfRxBadChecksums          Counter32,
        tmnxOspfNgIfBadAuthTypes            Counter32,
        tmnxOspfNgIfAuthFailures            Counter32
    }

tmnxOspfNgIfEvents OBJECT-TYPE
    SYNTAX      Counter32
    MAX-ACCESS  read-only
    STATUS      current
    DESCRIPTION
        "The value of tmnxOspfNgIfEvents indicates the number of times
         this OSPF interface has changed its state, or an error has occurred."
    ::= { tmnxOspfNgIfStatsEntry 1 }

tmnxOspfNgIfTxPackets OBJECT-TYPE
    SYNTAX      Counter32
    MAX-ACCESS  read-only
    STATUS      current
    DESCRIPTION
        "The value of tmnxOspfNgIfTxPackets indicates the total number of
         OSPF packets transmitted on this interface since tmnxOspfAdminState
         was last set to 'enabled'."
    ::= { tmnxOspfNgIfStatsEntry 2 }

tmnxOspfNgIfTxHellos OBJECT-TYPE
    SYNTAX      Counter32
    MAX-ACCESS  read-only
    STATUS      current
    DESCRIPTION
        "The value of tmnxOspfNgIfTxHellos indicates the total number
         of OSPF Hello packets transmitted on this interface since
         tmnxOspfAdminState was last set to 'enabled'."
    ::= { tmnxOspfNgIfStatsEntry 3 }

tmnxOspfNgIfTxDBDs OBJECT-TYPE
    SYNTAX      Counter32
    MAX-ACCESS  read-only
    STATUS      current
    DESCRIPTION
        "The value of tmnxOspfNgIfTxDBDs indicates the total number
         of OSPF Database Description packets transmitted on this
         interface since tmnxOspfAdminState was last set to 'enabled'."
    ::= { tmnxOspfNgIfStatsEntry 4 }

tmnxOspfNgIfTxLSRs OBJECT-TYPE
    SYNTAX      Counter32
    MAX-ACCESS  read-only
    STATUS      current
    DESCRIPTION
        "The value of tmnxOspfNgIfTxLSRs indicates the total number
         of OSPF Link State Requests (LSRs)transmitted on this
         interface since tmnxOspfAdminState was last set to 'enabled'."
    ::= { tmnxOspfNgIfStatsEntry 5 }

tmnxOspfNgIfTxLSUs OBJECT-TYPE
    SYNTAX      Counter32
    MAX-ACCESS  read-only
    STATUS      current
    DESCRIPTION
        "The value of tmnxOspfNgIfTxLSUs indicates the total number
         of OSPF Link State Updates (LSUs) transmitted on this
         interface since tmnxOspfAdminState was last set to 'enabled'."
    ::= { tmnxOspfNgIfStatsEntry 6 }

tmnxOspfNgIfTxLSAcks OBJECT-TYPE
    SYNTAX      Counter32
    MAX-ACCESS  read-only
    STATUS      current
    DESCRIPTION
        "The value of tmnxOspfNgIfTxLSAcks indicates the total number
         of OSPF Link State Acknowledgements transmitted on this
         interface since tmnxOspfAdminState was last set to 'enabled'."
    ::= { tmnxOspfNgIfStatsEntry 7 }

tmnxOspfNgIfRxPackets OBJECT-TYPE
    SYNTAX      Counter32
    MAX-ACCESS  read-only
    STATUS      current
    DESCRIPTION
        "The value of tmnxOspfNgIfRxPackets indicates the total number of
         OSPF packets received on this interface since tmnxOspfAdminState was
         last set to 'enabled'."
    ::= { tmnxOspfNgIfStatsEntry 8 }

tmnxOspfNgIfRxHellos OBJECT-TYPE
    SYNTAX      Counter32
    MAX-ACCESS  read-only
    STATUS      current
    DESCRIPTION
        "The value of tmnxOspfNgIfRxHellos indicates the total number of
         OSPF Hello packets received on this interface since tmnxOspfAdminState
         was last set to 'enabled'."
    ::= { tmnxOspfNgIfStatsEntry 9 }

tmnxOspfNgIfRxDBDs OBJECT-TYPE
    SYNTAX      Counter32
    MAX-ACCESS  read-only
    STATUS      current
    DESCRIPTION
        "The value of tmnxOspfNgIfRxDBDs indicates the total number of
         OSPF Database Description packets  received on this interface since
         tmnxOspfAdminState was last set to 'enabled'."
    ::= { tmnxOspfNgIfStatsEntry 10 }

tmnxOspfNgIfRxLSRs OBJECT-TYPE
    SYNTAX      Counter32
    MAX-ACCESS  read-only
    STATUS      current
    DESCRIPTION
        "The value of tmnxOspfNgIfRxLSRs indicates the total number of
         Link State Requests (LSRs) received on this interface since
         tmnxOspfAdminState was last set to 'enabled'."
    ::= { tmnxOspfNgIfStatsEntry 11 }

tmnxOspfNgIfRxLSUs OBJECT-TYPE
    SYNTAX      Counter32
    MAX-ACCESS  read-only
    STATUS      current
    DESCRIPTION
        "The value of tmnxOspfNgIfRxLSUs indicates the total number of
         Link State Updates (LSUs) received on this interface since
         tmnxOspfAdminState was last set to 'enabled'."
    ::= { tmnxOspfNgIfStatsEntry 12 }

tmnxOspfNgIfRxLSAcks OBJECT-TYPE
    SYNTAX      Counter32
    MAX-ACCESS  read-only
    STATUS      current
    DESCRIPTION
        "The value of tmnxOspfNgIfRxLSAcks indicates the total number of
         Link State Acknowledgements received on this interface since
         tmnxOspfAdminState was last set to 'enabled'."
    ::= { tmnxOspfNgIfStatsEntry 13 }

tmnxOspfNgIfDiscardPackets OBJECT-TYPE
    SYNTAX      Counter32
    MAX-ACCESS  read-only
    STATUS      current
    DESCRIPTION
        "The value of tmnxOspfNgIfDiscardPackets indicates the total number
         of OSPF packets discarded on this interface since tmnxOspfAdminState
         was last set to 'enabled'."
    ::= { tmnxOspfNgIfStatsEntry 14 }

tmnxOspfNgIfRetransmitOuts OBJECT-TYPE
    SYNTAX      Counter32
    MAX-ACCESS  read-only
    STATUS      current
    DESCRIPTION
        "The value of tmnxOspfNgIfRetransmitOuts indicates the total number
         of OSPF Retransmits sent on this interface since tmnxOspfAdminState was
         last set to 'enabled'."
    ::= { tmnxOspfNgIfStatsEntry 15 }

tmnxOspfNgIfBadVersions OBJECT-TYPE
    SYNTAX      Counter32
    MAX-ACCESS  read-only
    STATUS      current
    DESCRIPTION
        "The value of tmnxOspfNgIfBadVersions indicates the total number of
         OSPF packets received with bad OSPF version numbers since
         tmnxOspfAdminState was last set to 'enabled'."
    ::= { tmnxOspfNgIfStatsEntry 16 }

tmnxOspfNgIfBadNetworks OBJECT-TYPE
    SYNTAX      Counter32
    MAX-ACCESS  read-only
    STATUS      current
    DESCRIPTION
        "The value of tmnxOspfNgIfBadNetworks indicates the total number of
         OSPF packets received with invalid network or mask since
         tmnxOspfAdminState was last set to 'enabled'."
    ::= { tmnxOspfNgIfStatsEntry 17 }

tmnxOspfNgIfBadVirtualLinks OBJECT-TYPE
    SYNTAX      Counter32
    MAX-ACCESS  read-only
    STATUS      current
    DESCRIPTION
        "The value of tmnxOspfNgIfBadVirtualLinks indicates the total number
         of OSPF packets received on this interface that are destined to a
         virtual link that does not exist since tmnxOspfAdminState was last set
         to 'enabled'."
    ::= { tmnxOspfNgIfStatsEntry 18 }

tmnxOspfNgIfBadAreas OBJECT-TYPE
    SYNTAX      Counter32
    MAX-ACCESS  read-only
    STATUS      current
    DESCRIPTION
        "The value of tmnxOspfNgIfBadAreas indicates the total number of OSPF
         packets received with an area mismatch
         since tmnxOspfAdminState was last set to 'enabled'."
    ::= { tmnxOspfNgIfStatsEntry 19 }

tmnxOspfNgIfBadDstAddrs OBJECT-TYPE
    SYNTAX      Counter32
    MAX-ACCESS  read-only
    STATUS      current
    DESCRIPTION
        "The value of tmnxOspfNgIfBadDstAddrs indicates the total number
         of OSPF packets received with the incorrect IP destination address
         since tmnxOspfAdminState was last set to 'enabled'."
    ::= { tmnxOspfNgIfStatsEntry 20 }

tmnxOspfNgIfBadNeighbors OBJECT-TYPE
    SYNTAX      Counter32
    MAX-ACCESS  read-only
    STATUS      current
    DESCRIPTION
        "The value of tmnxOspfNgIfBadNeighbors indicates the total number
         of OSPF packets received where the neighbor
         information does not match the information this router has
         for the neighbor since tmnxOspfAdminState was last set to 'enabled'."
    ::= { tmnxOspfNgIfStatsEntry 21 }

tmnxOspfNgIfBadPacketTypes OBJECT-TYPE
    SYNTAX      Counter32
    MAX-ACCESS  read-only
    STATUS      current
    DESCRIPTION
        "The value of tmnxOspfNgIfBadPacketTypes indicates the total number
         of OSPF packets received with an invalid OSPF packet type since
         tmnxOspfAdminState was last set to 'enabled'."
    ::= { tmnxOspfNgIfStatsEntry 22 }

tmnxOspfNgIfNeighborCount OBJECT-TYPE
    SYNTAX      Integer32
    MAX-ACCESS  read-only
    STATUS      current
    DESCRIPTION
        "The value of tmnxOspfNgIfNeighborCount indicates the total number of
         OSPF neighbors adjacent on this interface, in a state of INIT or
         greater, since tmnxOspfAdminState was last set to 'enabled'."
    ::= { tmnxOspfNgIfStatsEntry 23 }

tmnxOspfNgIfLastEventTime OBJECT-TYPE
    SYNTAX      TimeStamp
    MAX-ACCESS  read-only
    STATUS      current
    DESCRIPTION
        "The value of tmnxOspfNgIfLastEventTime indicates the value of
         sysUpTime when an event was last associated with this OSPF
         interface."
    ::= { tmnxOspfNgIfStatsEntry 24 }

tmnxOspfNgIfBadLengths OBJECT-TYPE
    SYNTAX      Counter32
    MAX-ACCESS  read-only
    STATUS      current
    DESCRIPTION
        "The value of tmnxOspfNgIfBadLengths indicates the total number
         of OSPF packets received on this interface with a total length
         not equal to the length given in the packet itself since
         tmnxOspfAdminState was last set to 'enabled'."
    ::= { tmnxOspfNgIfStatsEntry 25 }

tmnxOspfNgIfBadHelloIntervals OBJECT-TYPE
    SYNTAX      Counter32
    MAX-ACCESS  read-only
    STATUS      current
    DESCRIPTION
        "The value of tmnxOspfNgIfBadHelloIntervals indicates the
         total number of OSPF packets received where the hello interval
         given in packet was not equal to that configured on this interface
         since tmnxOspfAdminState was last set to 'enabled'."
    ::= { tmnxOspfNgIfStatsEntry 26 }

tmnxOspfNgIfBadDeadIntervals OBJECT-TYPE
    SYNTAX      Counter32
    MAX-ACCESS  read-only
    STATUS      current
    DESCRIPTION
        "The value of tmnxOspfNgIfBadDeadIntervals indicates the
         total number of OSPF packets received where the dead interval
         given in the packet was not equal to that configured on this
         interface since tmnxOspfAdminState was last set to 'enabled'."
    ::= { tmnxOspfNgIfStatsEntry 27 }

tmnxOspfNgIfBadOptions OBJECT-TYPE
    SYNTAX      Counter32
    MAX-ACCESS  read-only
    STATUS      current
    DESCRIPTION
        "The value of tmnxOspfNgIfBadOptions indicates the total number
         of OSPF packets received with an option that does not match
         those configured for this interface or area since
         tmnxOspfAdminState was last set to 'enabled'."
    ::= { tmnxOspfNgIfStatsEntry 28 }

tmnxOspfNgIfRxBadChecksums OBJECT-TYPE
    SYNTAX      Counter32
    MAX-ACCESS  read-only
    STATUS      current
    DESCRIPTION
        "The value of tmnxOspfNgIfRxBadChecksums indicates the count
         of LSAs received with bad checksums."
    ::= { tmnxOspfNgIfStatsEntry 29 }

tmnxOspfNgIfBadAuthTypes OBJECT-TYPE
    SYNTAX      Counter32
    MAX-ACCESS  read-only
    STATUS      current
    DESCRIPTION
        "The value of tmnxOspfNgIfBadAuthTypes indicates the total
         number of OSPF packets received with an invalid authorization
         type since tmnxOspfAdminState was last set to 'enabled'."
    ::= { tmnxOspfNgIfStatsEntry 30 }

tmnxOspfNgIfAuthFailures OBJECT-TYPE
    SYNTAX      Counter32
    MAX-ACCESS  read-only
    STATUS      current
    DESCRIPTION
        "The value of tmnxOspfNgIfAuthFailures indicates the total
         number of OSPF packets received with an invalid authorization
         key since tmnxOspfAdminState was last set to 'enabled'."
    ::= { tmnxOspfNgIfStatsEntry 31 }

-- OSPF Neighbor Table - next generation
--
-- The OSPF Neighbor Table describes all neighbors in
-- the locality of the subject router.
-- This table supports multi-area adj OSPF (RFC 5185)

tmnxOspfNgNbrTable OBJECT-TYPE
    SYNTAX      SEQUENCE OF TmnxOspfNgNbrEntry
    MAX-ACCESS  not-accessible
    STATUS      current
    DESCRIPTION
        "The tmnxOspfNgNbrTable contains information about non-virtual
         neighbors."
    REFERENCE
        "OSPF Version 2, Section 10 The Neighbor Data
         Structure"
    ::= { tmnxOspfObjects 34 }

tmnxOspfNgNbrEntry OBJECT-TYPE 
    SYNTAX          TmnxOspfNgNbrEntry 
    MAX-ACCESS      not-accessible 
    STATUS          current 
    DESCRIPTION 
        "The tmnxOspfNgNbrEntry contains information regarding a single 
         non-virtual neighbor." 
    REFERENCE 
        "OSPF Version 2, Section 10 The Neighbor Data 
         Structure" 
    INDEX       {   vRtrID,
                    tmnxOspfVersion,
                    tmnxOspfInstance,
                    tmnxOspfNgNbrIfIndex, 
                    tmnxOspfNgNbrIfInstId,
                    tmnxOspfNgNbrIfAreaId,
                    tmnxOspfNgNbrRtrId
                } 
    ::= { tmnxOspfNgNbrTable 1 } 

TmnxOspfNgNbrEntry ::= SEQUENCE { 
    tmnxOspfNgNbrIfIndex              InterfaceIndex, 
    tmnxOspfNgNbrIfInstId             TmnxOspfIfInstIdTc, 
    tmnxOspfNgNbrIfAreaId             TmnxOspfAreaIdTc, 
    tmnxOspfNgNbrRtrId                TmnxOspfRouterIdTc, 
    tmnxOspfNgNbrAddressType          InetAddressType, 
    tmnxOspfNgNbrAddress              InetAddress,             
    tmnxOspfNgNbrOptions              Integer32, 
    tmnxOspfNgNbrPriority             DesignatedRouterPriority, 
    tmnxOspfNgNbrState                INTEGER, 
    tmnxOspfNgNbrHelloSuppressed      TruthValue, 
    tmnxOspfNgNbrIfId                 InterfaceIndexOrZero, 
    tmnxOspfNgNbrRestartHelperStatus  INTEGER,  
    tmnxOspfNgNbrRestartHelperAge     TmnxOspfUpToRefreshIntervalTc,  
    tmnxOspfNgNbrRestartHelperExitRc  INTEGER,
    tmnxOspfNgNbrUpTime               TimeInterval,
    tmnxOspfNgNbrLastEventTime        TimeStamp,
    tmnxOspfNgNbrDeadTimeOutstanding  Unsigned32,
    tmnxOspfNgNbrLastRestartTime      TimeStamp,
    tmnxOspfNgNbrRestartReason        TmnxOspfRestartReasonTc,
    tmnxOspfNgNbrBfdTracking          TruthValue,
    tmnxOspfNgNbrDrId                 TmnxOspfRouterIdTc,
    tmnxOspfNgNbrBdrId                TmnxOspfRouterIdTc
} 

tmnxOspfNgNbrIfIndex OBJECT-TYPE 
    SYNTAX      InterfaceIndex 
    MAX-ACCESS  not-accessible 
    STATUS      current 
    DESCRIPTION 
        "The value of tmnxOspfNgNbrIfIndex specifies the local link ID of 
         the link over which the neighbor can be reached." 
    ::= { tmnxOspfNgNbrEntry 1 } 

tmnxOspfNgNbrIfInstId OBJECT-TYPE 
    SYNTAX      TmnxOspfIfInstIdTc 
    MAX-ACCESS  not-accessible 
    STATUS      current 
    DESCRIPTION 
        "The value of tmnxOspfNgNbrIfInstId specifies the interface instance 
         over which the neighbor can be reached.  This ID has local link 
         significance only." 
    ::= { tmnxOspfNgNbrEntry 2 } 

tmnxOspfNgNbrIfAreaId OBJECT-TYPE 
    SYNTAX      TmnxOspfAreaIdTc 
    MAX-ACCESS  not-accessible 
    STATUS      current 
    DESCRIPTION 
        "The value of tmnxOspfNgNbrIfAreaId specifies the OSPF Area Identifier." 
    ::= { tmnxOspfNgNbrEntry 3 } 

tmnxOspfNgNbrRtrId OBJECT-TYPE 
    SYNTAX      TmnxOspfRouterIdTc 
    MAX-ACCESS  not-accessible 
    STATUS      current 
    DESCRIPTION 
        "The value of tmnxOspfNgNbrRtrId specifies a 32-bit integer uniquely 
         identifying the neighboring router in the Autonomous System." 
    ::= { tmnxOspfNgNbrEntry 4 } 

tmnxOspfNgNbrAddressType OBJECT-TYPE 
    SYNTAX      InetAddressType 
    MAX-ACCESS  read-only 
    STATUS      current 
    DESCRIPTION 
        "The value of tmnxOspfNgNbrAddressType indicates the address type of 
         tmnxOspfNgNbrAddress. For addresses of IPv6 type only addresses 
         with zone index are expected." 
    ::= { tmnxOspfNgNbrEntry 5 } 

tmnxOspfNgNbrAddress OBJECT-TYPE 
    SYNTAX      InetAddress (SIZE (4|20)) 
    MAX-ACCESS  read-only 
    STATUS      current 
    DESCRIPTION 
        "The value of tmnxOspfNgNbrAddress indicates the IP address of the 
         neighbor associated with the local link." 
    ::= { tmnxOspfNgNbrEntry 6 } 
    
tmnxOspfNgNbrOptions OBJECT-TYPE 
    SYNTAX      Integer32 
    MAX-ACCESS  read-only 
    STATUS      current 
    DESCRIPTION 
        "The value of tmnxOspfNgNbrOptions indicates a Bit Mask corresponding 
         to the neighbor's options field." 
    REFERENCE 
        "OSPF Version 3, Appendix A.2 the Options field" 
    ::= { tmnxOspfNgNbrEntry 7 } 
    
tmnxOspfNgNbrPriority OBJECT-TYPE 
    SYNTAX      DesignatedRouterPriority 
    MAX-ACCESS  read-only 
    STATUS      current 
    DESCRIPTION 
        "The value of tmnxOspfNgNbrPriority indicates the priority of this 
         neighbor in the designated router election algorithm.  The value 
         0 signifies that the neighbor is not eligible to become the 
         designated router on this particular network." 
    ::= { tmnxOspfNgNbrEntry 8 } 
    
tmnxOspfNgNbrState OBJECT-TYPE 
    SYNTAX      INTEGER { 
                    down            (1), 
                    attempt         (2), 
                    init            (3), 
                    twoWay          (4), 
                    exchangeStart   (5), 
                    exchange        (6), 
                    loading         (7), 
                    full            (8) 
                } 
    MAX-ACCESS  read-only 
    STATUS      current 
    DESCRIPTION 
        "The value of tmnxOspfNgNbrState indicates the State of the 
         relationship with this Neighbor." 
    REFERENCE 
        "OSPF Version 2, Section 10.1 Neighbor States" 
    ::= { tmnxOspfNgNbrEntry 9 } 
    
tmnxOspfNgNbrHelloSuppressed OBJECT-TYPE 
    SYNTAX      TruthValue 
    MAX-ACCESS  read-only 
    STATUS      current 
    DESCRIPTION 
        "The value of tmnxOspfNgNbrHelloSuppressed indicates whether Hellos 
         are being suppressed to the neighbor." 
    ::= { tmnxOspfNgNbrEntry 10 } 
    
tmnxOspfNgNbrIfId OBJECT-TYPE 
    SYNTAX      InterfaceIndexOrZero 
    MAX-ACCESS  read-only 
    STATUS      current 
    DESCRIPTION 
        "The value of tmnxOspfNgNbrIfId indicates the interface ID that the 
         neighbor advertises in its Hello Packets on this link, that is, the 
         neighbor's local interface index." 
    ::= { tmnxOspfNgNbrEntry 11 } 
    
tmnxOspfNgNbrRestartHelperStatus OBJECT-TYPE  
    SYNTAX      INTEGER { 
                    notHelping (1),  
                    helping (2)  
                }  
    MAX-ACCESS  read-only  
    STATUS      current  
    DESCRIPTION  
        "The value of tmnxOspfNgNbrRestartHelperStatus indicates whether 
         the router is acting as a Graceful restart helper for the neighbor."  
    ::= { tmnxOspfNgNbrEntry 12 }  
        
tmnxOspfNgNbrRestartHelperAge OBJECT-TYPE  
    SYNTAX      TmnxOspfUpToRefreshIntervalTc 
    UNITS       "seconds"  
    MAX-ACCESS  read-only  
    STATUS      current  
    DESCRIPTION  
        "The value of tmnxOspfNgNbrRestartHelperAge indicates the remaining 
         time in the current OSPF Graceful restart interval, if the router 
         is acting as a restart helper for the neighbor."  
    ::= { tmnxOspfNgNbrEntry 13 }  
        
tmnxOspfNgNbrRestartHelperExitRc OBJECT-TYPE  
    SYNTAX      INTEGER {
                    none (1), 
                    inProgress (2),  
                    completed (3),  
                    timedOut (4),  
                    topologyChanged (5) 
                }  
    MAX-ACCESS  read-only  
    STATUS      current  
    DESCRIPTION  
        "The value of tmnxOspfNgNbrRestartHelperExitRc indicates the outcome 
         of the last attempt at acting as a Graceful restart helper for the 
         neighbor. 
    
              none             No restart has yet been attempted. 
              inProgress       A restart attempt is currently underway. 
              completed        The last restart completed successfully. 
              timedOut         The last restart timed out. 
              topologyChanged  The last restart was aborted due to 
                               a topology change."  
    ::= { tmnxOspfNgNbrEntry 14 } 
    
tmnxOspfNgNbrUpTime OBJECT-TYPE
    SYNTAX      TimeInterval
    MAX-ACCESS  read-only
    STATUS      current
    DESCRIPTION
        "The value of tmnxOspfNgNbrUpTime indicates the uninterrupted time,
         in hundredths of seconds, the adjacency to this neighbour
         has been up."
    ::= { tmnxOspfNgNbrEntry 15 }
    
tmnxOspfNgNbrLastEventTime OBJECT-TYPE
    SYNTAX      TimeStamp
    MAX-ACCESS  read-only
    STATUS      current
    DESCRIPTION
        "The value of tmnxOspfNgNbrLastEventTime indicates the value of
         sysUpTime when the last event occurred that affected the adjacency
         to the neighbour."
    ::= { tmnxOspfNgNbrEntry 16 }
    
tmnxOspfNgNbrDeadTimeOutstanding OBJECT-TYPE
    SYNTAX      Unsigned32 (0..'7FFFFFFF'h)
    UNITS       "seconds"
    MAX-ACCESS  read-only
    STATUS      current
    DESCRIPTION
        "The value of tmnxOspfNgNbrDeadTimeOutstanding indicates the amount
         of time in seconds until the  dead-router interval expires. Normally,
         this value should not be significantly smaller than the configured
         dead router interval minus one hello interval."
    ::= { tmnxOspfNgNbrEntry 17 }
    
tmnxOspfNgNbrLastRestartTime OBJECT-TYPE
    SYNTAX      TimeStamp
    MAX-ACCESS  read-only
    STATUS      current
    DESCRIPTION
        "The value of tmnxOspfNgNbrLastRestartTime indicates the last time the 
         neighbor attempted restart."
    ::= { tmnxOspfNgNbrEntry 18 } 
    
tmnxOspfNgNbrRestartReason OBJECT-TYPE
    SYNTAX      TmnxOspfRestartReasonTc
    MAX-ACCESS  read-only
    STATUS      current
    DESCRIPTION
        "The value of tmnxOspfNgNbrRestartReason indicates the OSPF 
         neighbor's graceful restart reason." 
    ::= { tmnxOspfNgNbrEntry 19 } 
    
tmnxOspfNgNbrBfdTracking OBJECT-TYPE
    SYNTAX      TruthValue
    MAX-ACCESS  read-only
    STATUS      current
    DESCRIPTION
        "The value of tmnxOspfNgNbrBfdTracking indicates whether a BFD
        session is being maintained to track the forwarding path to
        this neighbor or not."
    ::= { tmnxOspfNgNbrEntry 20 } 
    
tmnxOspfNgNbrDrId OBJECT-TYPE 
    SYNTAX      TmnxOspfRouterIdTc 
    MAX-ACCESS  read-only 
    STATUS      current 
    DESCRIPTION 
        "The value of tmnxOspfNgNbrDrId indicates the DR value advertised 
         in the HELLO packets received from the OSPF neighbor.
         If it is not a broadcast interface tmnxOspfNgNbrDrId will be zero."
    ::= { tmnxOspfNgNbrEntry 21 } 
    
tmnxOspfNgNbrBdrId  OBJECT-TYPE 
    SYNTAX      TmnxOspfRouterIdTc 
    MAX-ACCESS  read-only 
    STATUS      current 
    DESCRIPTION 
        "The value of tmnxOspfNgNbrBdrId indicates the BDR value advertised
         in the HELLO packets received from the OSPF neighbor.
         If it is not a broadcast interface tmnxOspfNgNbrBdrId will be zero."
    ::= { tmnxOspfNgNbrEntry 22 } 

--
--  Augmentation of the tmnxOspfNgNbrTable.
--  Use of AUGMENTS clause implies a one-to-one dependent relationship
--  between the base table, tmnxOspfNgNbrTable, and the augmenting table,
--  tmnxOspfNgNbrStatsTable.
--
--  This in effect extends the tmnxOspfNgNbrTable with additional columns. 
--  Creation (or deletion) of a row in the tmnxOspfNgNbrTable results in
--  the same fate for the row in the tmnxOspfNgNbrStatsTable.
--
tmnxOspfNgNbrStatsTable OBJECT-TYPE
    SYNTAX      SEQUENCE OF TmnxOspfNgNbrStatsEntry
    MAX-ACCESS  not-accessible
    STATUS      current
    DESCRIPTION
        "The tmnxOspfNgNbrStatsTable provides an extension of the
         tmnxOspfNgNbrTable for statistics for an OSPF neighbor."
    ::= { tmnxOspfObjects 35 }

tmnxOspfNgNbrStatsEntry OBJECT-TYPE
    SYNTAX      TmnxOspfNgNbrStatsEntry
    MAX-ACCESS  not-accessible
    STATUS      current
    DESCRIPTION
        "Each row entry in the tmnxOspfNgNbrStatsTable represents
         additional columns for statistics for an OSPF neighbor."
    AUGMENTS { tmnxOspfNgNbrEntry }
   ::= { tmnxOspfNgNbrStatsTable 1 }

TmnxOspfNgNbrStatsEntry ::=
    SEQUENCE {
        tmnxOspfNgNbrEvents             Counter32,
        tmnxOspfNgNbrLsRetransQLen      Gauge32,
        tmnxOspfNgNbrBadNbrStates       Counter32,
        tmnxOspfNgNbrLsaInstallFailed   Counter32,
        tmnxOspfNgNbrBadSeqNums         Counter32,
        tmnxOspfNgNbrBadMTUs            Counter32,
        tmnxOspfNgNbrBadPackets         Counter32,
        tmnxOspfNgNbrLsaNotInLsdbs      Counter32,
        tmnxOspfNgNbrOptionMismatches   Counter32,
        tmnxOspfNgNbrDuplicates         Counter32,
        tmnxOspfNgNbrNumRestarts        Counter32
    }

tmnxOspfNgNbrEvents OBJECT-TYPE
    SYNTAX      Counter32
    MAX-ACCESS  read-only
    STATUS      current
    DESCRIPTION
        "The value of tmnxOspfNgNbrEvents indicates the number of times
         this neighbor relationship has changed state, or an error has
         occurred."
    ::= { tmnxOspfNgNbrStatsEntry 1 }

tmnxOspfNgNbrLsRetransQLen OBJECT-TYPE
    SYNTAX      Gauge32
    MAX-ACCESS  read-only
    STATUS      current
    DESCRIPTION
        "The value of tmnxOspfNgNbrLsRetransQLen indicates the current
         length of the retransmission queue."
    ::= { tmnxOspfNgNbrStatsEntry 2 }

tmnxOspfNgNbrBadNbrStates OBJECT-TYPE
    SYNTAX      Counter32
    MAX-ACCESS  read-only
    STATUS      current
    DESCRIPTION
        "The value of tmnxOspfNgNbrBadNbrStates indicates the total number
         of OSPF packets received when the neighbor state was not
         expecting to receive this packet type since tmnxOspfAdminState
         was last set to 'enabled'."
    ::= { tmnxOspfNgNbrStatsEntry 3 }

tmnxOspfNgNbrLsaInstallFailed OBJECT-TYPE
    SYNTAX      Counter32
    MAX-ACCESS  read-only
    STATUS      current
    DESCRIPTION
        "The value of tmnxOspfNgNbrLsaInstallFailed indicates the total number
         of times an LSA could not be installed into the LSDB due to
         a resource allocation issue since tmnxOspfAdminState was last set
         to 'enabled'."
    ::= { tmnxOspfNgNbrStatsEntry 4 }

tmnxOspfNgNbrBadSeqNums OBJECT-TYPE
    SYNTAX      Counter32
    MAX-ACCESS  read-only
    STATUS      current
    DESCRIPTION
        "The value of tmnxOspfNgNbrBadSeqNums indicates the total number
         of times when a database description packet was received with a
         sequence number mismatch since tmnxOspfAdminState was last
         set to 'enabled'."
    ::= { tmnxOspfNgNbrStatsEntry 5 }

tmnxOspfNgNbrBadMTUs OBJECT-TYPE
    SYNTAX      Counter32
    MAX-ACCESS  read-only
    STATUS      current
    DESCRIPTION
        "The value of tmnxOspfNgNbrBadMTUs indicates the total number of times
         when the MTU in a received database description packet was
         larger than the MTU of the receiving interface since
         tmnxOspfAdminState was last set to 'enabled'."
    ::= { tmnxOspfNgNbrStatsEntry 6 }

tmnxOspfNgNbrBadPackets OBJECT-TYPE
    SYNTAX      Counter32
    MAX-ACCESS  read-only
    STATUS      current
    DESCRIPTION
        "The value of tmnxOspfNgNbrBadPackets indicates the total number
         of times when an LS update was received with an illegal LS type or an
         option mismatch since tmnxOspfAdminState was last set to 'enabled'."
    ::= { tmnxOspfNgNbrStatsEntry 7 }

tmnxOspfNgNbrLsaNotInLsdbs OBJECT-TYPE
    SYNTAX      Counter32
    MAX-ACCESS  read-only
    STATUS      current
    DESCRIPTION
        "The value of tmnxOspfNgNbrLsaNotInLsdbs indicates the total number of
         times when an LS request was received for an LSA not installed in the
         LSDB of this router since tmnxOspfAdminState was last set to
         'enabled'."
    ::= { tmnxOspfNgNbrStatsEntry 8 }

tmnxOspfNgNbrOptionMismatches OBJECT-TYPE
    SYNTAX      Counter32
    MAX-ACCESS  read-only
    STATUS      current
    DESCRIPTION
        "The value of tmnxOspfNgNbrOptionMismatches indicates the total
         number of times when a LS update was received with an option mismatch
         since tmnxOspfAdminState was last set to 'enabled'."
    ::= { tmnxOspfNgNbrStatsEntry 9 }

tmnxOspfNgNbrDuplicates OBJECT-TYPE
    SYNTAX      Counter32
    MAX-ACCESS  read-only
    STATUS      current
    DESCRIPTION
        "The value of tmnxOspfNgNbrDuplicates indicates the total number
         of times when a duplicate database description packet was received
         during the Exchange state since tmnxOspfAdminState was last set
         to 'enabled'."
    ::= { tmnxOspfNgNbrStatsEntry 10 }

tmnxOspfNgNbrNumRestarts OBJECT-TYPE
    SYNTAX      Counter32
    MAX-ACCESS  read-only
    STATUS      current
    DESCRIPTION
        "The value of tmnxOspfNgNbrNumRestarts indicates the number of times
         the neighbor has attempted restart."
    ::= { tmnxOspfNgNbrStatsEntry 11 }

--
--  The MD5 Key table for OSPF MD5 authentication
--  This table supports multi-area adj OSPF (RFC 5185)
--

tmnxOspfNgIfMD5KeyTable OBJECT-TYPE
    SYNTAX      SEQUENCE OF TmnxOspfNgIfMD5KeyEntry
    MAX-ACCESS  not-accessible
    STATUS      current
    DESCRIPTION
        "The tmnxOspfNgIfMD5KeyTable contains a list of MD5 keys to be used
         to authenticate OSPFv2 packets."
    ::= { tmnxOspfObjects 36 }

tmnxOspfNgIfMD5KeyEntry OBJECT-TYPE
    SYNTAX      TmnxOspfNgIfMD5KeyEntry
    MAX-ACCESS  not-accessible
    STATUS      current
    DESCRIPTION
        "Each row entry represents a MD5 key to be used to authenticate
         a OSPFv2 packet addressed to a particular OSPF IP address.
         Entries can be created and deleted via SNMP SET operations.
         Creation requires a SET request containing at least
         tmnxOspfNgIfMD5KeyKey and tmnxOspfNgIfMD5KeyStatus."
    INDEX       {   vRtrID,
                    tmnxOspfVersion,
                    tmnxOspfInstance,
                    tmnxOspfNgIfIndex,
                    tmnxOspfNgIfInstId,
                    tmnxOspfNgIfAreaId,
                    tmnxOspfNgIfMD5KeyIndex
                }
    ::= { tmnxOspfNgIfMD5KeyTable 1 }

TmnxOspfNgIfMD5KeyEntry ::=
    SEQUENCE {
        tmnxOspfNgIfMD5KeyIndex           TmnxOspfIfMD5KeyId,
        tmnxOspfNgIfMD5KeyStatus          RowStatus,
        tmnxOspfNgIfMD5KeyKey             OCTET STRING,
        tmnxOspfNgIfMD5KeyStartTime       DateAndTime,
        tmnxOspfNgIfMD5KeyStopTime        DateAndTime
    }

tmnxOspfNgIfMD5KeyIndex OBJECT-TYPE
    SYNTAX      TmnxOspfIfMD5KeyId
    MAX-ACCESS  not-accessible
    STATUS      current
    DESCRIPTION
        "The value of tmnxOspfNgIfMD5KeyIndex provides a unique identifier
         for a key to be used for authentication on a specific OSPFv2
         IP address.

         If tmnxOspfNgIfMD5KeyIndex has a value of 0, it means that no
         keys are configured."
    ::= { tmnxOspfNgIfMD5KeyEntry 1 }

tmnxOspfNgIfMD5KeyStatus OBJECT-TYPE
    SYNTAX      RowStatus
    MAX-ACCESS  read-create
    STATUS      current
    DESCRIPTION
        "The object tmnxOspfNgIfMD5KeyStatus is the RowStatus used for
         creation, deletion, or control of tmnxOspfNgIfMD5KeyTable entries.
         Before the row can be placed into the 'active' state,
         tmnxOspfNgIfMD5KeyKey must have been assigned a value."
    ::= { tmnxOspfNgIfMD5KeyEntry 2 }

tmnxOspfNgIfMD5KeyKey OBJECT-TYPE
    SYNTAX      OCTET STRING (SIZE(0..16))
    MAX-ACCESS  read-create
    STATUS      current
    DESCRIPTION
        "The value of tmnxOspfNgIfMD5KeyKey specifies the MD5 authentication
         key to be used on this OSPFv2 IP address.

         When read, tmnxOspfNgIfMD5KeyKey always returns an OCTET STRING of
         length zero."
    ::= { tmnxOspfNgIfMD5KeyEntry 3 }

tmnxOspfNgIfMD5KeyStartTime OBJECT-TYPE
    SYNTAX      DateAndTime
    MAX-ACCESS  read-create
    STATUS      current
    DESCRIPTION
        "The value of tmnxOspfNgIfMD5KeyStartTime specifies the date and
         time when this MD5 authentication key becomes valid for use.
         If no date and time is set, represented by a DateAndTime string
         with 0 length, the key is valid by default."
    DEFVAL { ''H }
    ::= { tmnxOspfNgIfMD5KeyEntry 4 }

tmnxOspfNgIfMD5KeyStopTime OBJECT-TYPE
    SYNTAX      DateAndTime
    MAX-ACCESS  read-create
    STATUS      current
    DESCRIPTION
        "The value of tmnxOspfNgIfMD5KeyStopTime specifies the date and
         time when this MD5 authentication key becomes invalid for use.
         If no date and time is set, represented by a DateAndTime string
         with 0 length, the key is valid indefinitely."
    DEFVAL { ''H }
    ::= { tmnxOspfNgIfMD5KeyEntry 5 }

--
-- tmnxOspfLfaStatsTable
--

tmnxOspfLfaStatsTable OBJECT-TYPE
    SYNTAX      SEQUENCE OF TmnxOspfLfaStatsEntry
    MAX-ACCESS  not-accessible
    STATUS      current
    DESCRIPTION
        "The tmnxOspfLfaStatsTable maintains information on loopfree-alternate 
        (LFA) coverage for each instance of OSPF protocol."
    ::= { tmnxOspfObjects 37 }

tmnxOspfLfaStatsEntry OBJECT-TYPE
    SYNTAX      TmnxOspfLfaStatsEntry
    MAX-ACCESS  not-accessible
    STATUS      current
    DESCRIPTION
        "Each row entry in the tmnxOspfLfaStatsTable represents information on 
         LFA coverage for a given OSPF area"
    INDEX       {  
                    vRtrID,
                    tmnxOspfVersion,
                    tmnxOspfInstance,
                    tmnxOspfAreaId
                }
    ::= { tmnxOspfLfaStatsTable 1 }

TmnxOspfLfaStatsEntry ::=
    SEQUENCE {
        tmnxOspfLfaNodesCovered         Gauge32,
        tmnxOspfLfaTotalNodes           Gauge32,
        tmnxOspfLfaCoverage             Gauge32,
        tmnxOspfLfaPfxCovered           Gauge32,
        tmnxOspfLfaTotalPfx             Gauge32,
        tmnxOspfLfaPfxCoverage          Gauge32     
    }

tmnxOspfLfaNodesCovered OBJECT-TYPE
    SYNTAX       Gauge32  
    MAX-ACCESS   read-only
    STATUS       current
    DESCRIPTION
        "The value of tmnxOspfLfaNodesCovered indicates in absolute numbers the 
         number of nodes for which an LFA is found."
    ::= { tmnxOspfLfaStatsEntry 1 }

tmnxOspfLfaTotalNodes OBJECT-TYPE
    SYNTAX       Gauge32 
    MAX-ACCESS   read-only
    STATUS       current
    DESCRIPTION
        "The value of tmnxOspfLfaTotalNodes indicates in absolute numbers the 
         number of nodes eligible for LFA calculation."
    ::= { tmnxOspfLfaStatsEntry 2 }

tmnxOspfLfaCoverage OBJECT-TYPE
    SYNTAX       Gauge32  (0..10000)
    UNITS        "hundredths of a percent"
    MAX-ACCESS   read-only
    STATUS       current
    DESCRIPTION
        "The value of tmnxOspfLfaCoverage indicates how much LFA coverage 
         is being obtained for the set of  available LFA eligible nodes."
    ::= { tmnxOspfLfaStatsEntry 3 }

tmnxOspfLfaPfxCovered OBJECT-TYPE
    SYNTAX       Gauge32  
    MAX-ACCESS   read-only
    STATUS       current
    DESCRIPTION
        "The value of tmnxOspfLfaPfxCovered indicates in absolute numbers the 
         number of prefixes for which an LFA is found."
    ::= { tmnxOspfLfaStatsEntry 4 }

tmnxOspfLfaTotalPfx OBJECT-TYPE
    SYNTAX       Gauge32 
    MAX-ACCESS   read-only
    STATUS       current
    DESCRIPTION
        "The value of tmnxOspfLfaTotalPfx indicates in absolute numbers the 
            number of prefixes eligible for LFA calculation."
    ::= { tmnxOspfLfaStatsEntry 5 }

tmnxOspfLfaPfxCoverage OBJECT-TYPE
    SYNTAX       Gauge32  (0..10000)
    UNITS        "hundredths of a percent"
    MAX-ACCESS   read-only
    STATUS       current
    DESCRIPTION
        "The value of tmnxOspfLfaPfxCoverage indicates how much LFA prefix 
         coverage is being obtained for the set of  available LFA eligible 
         prefixes."
    ::= { tmnxOspfLfaStatsEntry 6 }

--
-- tmnxOspfPathTable
--

tmnxOspfPathTable OBJECT-TYPE
    SYNTAX      SEQUENCE OF TmnxOspfPathEntry
    MAX-ACCESS  not-accessible
    STATUS      current
    DESCRIPTION
        "The tmnxOspfPathTable maintains information regarding LFA calculations 
         for each instance of OSPF protocol."
    ::= { tmnxOspfObjects 38 }
 
tmnxOspfPathEntry OBJECT-TYPE
    SYNTAX      TmnxOspfPathEntry
    MAX-ACCESS  not-accessible
    STATUS      current
    DESCRIPTION
        "Each row entry in the tmnxOspfPathTable"
    INDEX       {  
                    vRtrID,
                    tmnxOspfVersion,
                    tmnxOspfInstance,
                    tmnxOspfAreaId,
                    tmnxOspfPathDestRouterId,
                    tmnxOspfPathIfIndex,
                    tmnxOspfPathNhopRouterId
                }
    ::= { tmnxOspfPathTable 1 }
 
TmnxOspfPathEntry ::=
    SEQUENCE {
        tmnxOspfPathDestRouterId        TmnxOspfRouterIdTc,
        tmnxOspfPathIfIndex             InterfaceIndex,
        tmnxOspfPathNhopRouterId        TmnxOspfRouterIdTc,
        tmnxOspfPathMetric              Unsigned32,
        tmnxOspfPathLfaIfIndex          InterfaceIndex,
        tmnxOspfPathLfaType             INTEGER,
        tmnxOspfPathLfaNhopRouterId     TmnxOspfRouterIdTc,
        tmnxOspfPathLfaMetric           Unsigned32,
        tmnxOspfPathNhOwner             TmnxInetCidrNextHopOwner,
        tmnxOspfPathLfaNhOwner          TmnxInetCidrNextHopOwner
    }

tmnxOspfPathDestRouterId    OBJECT-TYPE
    SYNTAX       TmnxOspfRouterIdTc  
    MAX-ACCESS   not-accessible
    STATUS       current
    DESCRIPTION
        "The value of tmnxOspfPathDestRouterId indicates the destination node 
         associated with this entry." 
    ::= { tmnxOspfPathEntry 1 }
 
tmnxOspfPathIfIndex    OBJECT-TYPE
    SYNTAX       InterfaceIndex  
    MAX-ACCESS   not-accessible
    STATUS       current
    DESCRIPTION
        "The value of tmnxOspfPathIfIndex indicates the ifIndex of the outgoing 
         interface for the route."
    ::= { tmnxOspfPathEntry 2 }
 
tmnxOspfPathNhopRouterId    OBJECT-TYPE
    SYNTAX       TmnxOspfRouterIdTc  
    MAX-ACCESS   not-accessible
    STATUS       current
    DESCRIPTION
        "The value of tmnxOspfPathNhopRouterId indicates the next hop through 
         which this route is reachable."
    ::= { tmnxOspfPathEntry 3 }
 
tmnxOspfPathMetric    OBJECT-TYPE
    SYNTAX       Unsigned32  
    MAX-ACCESS   read-only
    STATUS       current
    DESCRIPTION
        "The value of tmnxOspfPathMetric indicates the metric assigned to this 
         entry after SPF calculations. The lower the metric value, the shorter 
         is the path and hence more preferred by the protocol."
    ::= { tmnxOspfPathEntry 4 }
 
tmnxOspfPathLfaIfIndex    OBJECT-TYPE
    SYNTAX       InterfaceIndex  
    MAX-ACCESS   read-only
    STATUS       current
    DESCRIPTION
        "The value of tmnxOspfPathLfaIfIndex indicates the loopfree-alternate 
         ifIndex of the outgoing interface for the LFA path."
    ::= { tmnxOspfPathEntry 5 }

tmnxOspfPathLfaType OBJECT-TYPE
    SYNTAX       INTEGER {
                    noProtection(0),
                    nodeProtection(1),
                    linkProtection(2)
                   }
    MAX-ACCESS   read-only
    STATUS       current
    DESCRIPTION
        "The value of tmnxOspfPathLfaType indicates the level of LFA protection 
         represented by this row entry."
    ::= { tmnxOspfPathEntry 6 }

tmnxOspfPathLfaNhopRouterId    OBJECT-TYPE
    SYNTAX       TmnxOspfRouterIdTc  
    MAX-ACCESS   read-only
    STATUS       current
    DESCRIPTION
        "The value of tmnxOspfPathLfaNhopRouterId indicates the next-hop node in
         this loopfree-alternate path to reach a given destination node. The 
         value of tmnxOspfPathLfaNhopRouterId is valid only if 
         tmnxOspfPathLfaType has a non-zero value."
    ::= { tmnxOspfPathEntry 7 }
 
tmnxOspfPathLfaMetric    OBJECT-TYPE
    SYNTAX       Unsigned32  
    MAX-ACCESS   read-only
    STATUS       current
    DESCRIPTION
        "The value of tmnxOspfPathLfaMetric indicates the metric assigned to 
         this entry after LFA calculations. The lower the metric value, the 
         shorter is the path and hence more preferred by the protocol. The 
         value of tmnxOspfPathLfaMetric is valid only if tmnxOspfPathLfaType 
         has a non-zero value."
    ::= { tmnxOspfPathEntry 8 }

tmnxOspfPathNhOwner    OBJECT-TYPE
    SYNTAX       TmnxInetCidrNextHopOwner
    MAX-ACCESS   read-only
    STATUS       current
    DESCRIPTION
        "The value of tmnxOspfPathNhOwner indicates the owner of next hop
         for this route."
    ::= { tmnxOspfPathEntry 9 }
 
tmnxOspfPathLfaNhOwner    OBJECT-TYPE
    SYNTAX       TmnxInetCidrNextHopOwner
    MAX-ACCESS   read-only
    STATUS       current
    DESCRIPTION
        "The value of tmnxOspfPathLfaNhOwner indicates the owner of next
         hop for this loopfree-alternate route."
    ::= { tmnxOspfPathEntry 10 }

--
--  Augmentation of the tmnxOspfGeneralTable.
--  Use of AUGMENTS clause implies a one-to-one dependent relationship between
--  the base table, tmnxOspfGeneralTable, and the augmenting table,
--  tmnxOspfGeneralExTable.
--  This in effect extends the tmnxOspfGeneralTable with additional columns.
--  Creation (or deletion) of a row in the tmnxOspfGeneralTable results in
--  the same fate for the row in the tmnxOspfGeneralExTable.
--
tmnxOspfGeneralExTable OBJECT-TYPE
    SYNTAX      SEQUENCE OF TmnxOspfGeneralExEntry
    MAX-ACCESS  not-accessible
    STATUS      current
    DESCRIPTION
        "The tmnxOspfGeneralExTable provides an extension of the
         tmnxOspfGeneralTable."
    ::= { tmnxOspfObjects 39 }

tmnxOspfGeneralExEntry OBJECT-TYPE
    SYNTAX      TmnxOspfGeneralExEntry
    MAX-ACCESS  not-accessible
    STATUS      current
    DESCRIPTION
        "Each row entry in the tmnxOspfGeneralExTable represents additional
         columns for an OSPF instance."
    AUGMENTS { tmnxOspfGeneralEntry }
   ::= { tmnxOspfGeneralExTable 1 }

TmnxOspfGeneralExEntry ::=
    SEQUENCE {
        tmnxOspfGeneralExLastChanged    TimeStamp,
        tmnxOspfAdvRtrCapability        INTEGER,
        tmnxOspfLFAExcludePolicy1       TNamedItemOrEmpty,
        tmnxOspfLFAExcludePolicy2       TNamedItemOrEmpty,
        tmnxOspfLFAExcludePolicy3       TNamedItemOrEmpty,
        tmnxOspfLFAExcludePolicy4       TNamedItemOrEmpty,
        tmnxOspfLFAExcludePolicy5       TNamedItemOrEmpty
    }

tmnxOspfGeneralExLastChanged  OBJECT-TYPE
    SYNTAX      TimeStamp
    MAX-ACCESS  read-only
    STATUS      current
    DESCRIPTION
        "The value of tmnxOspfGeneralExLastChanged indicates the sysUpTime
         when a configurable object in this row was last modified."
    ::= { tmnxOspfGeneralExEntry 1 }

tmnxOspfAdvRtrCapability OBJECT-TYPE
    SYNTAX      INTEGER {
                    disable (0),
                    link    (1),
                    area    (2),
                    as      (3)
                }
    MAX-ACCESS  read-create
    STATUS      current
    DESCRIPTION
        "The value of tmnxOspfAdvRtrCapability specifies the OSPF
         advertise router capabilities."
    DEFVAL { disable }
    ::= { tmnxOspfGeneralExEntry 2 }

tmnxOspfLFAExcludePolicy1   OBJECT-TYPE
        SYNTAX      TNamedItemOrEmpty
        MAX-ACCESS  read-create
        STATUS      current
        DESCRIPTION
            "The value of tmnxOspfLFAExcludePolicy1 is the name of the first
             policy from which prefixes are excluded which match on the OSPF
             tag. Prefixes excluded from LFA (Loopfree Alternative) this way
             will not be used in the LFA calculation, regardless of its
             priority."
        DEFVAL { ''H }
        ::= { tmnxOspfGeneralExEntry 3 }

tmnxOspfLFAExcludePolicy2   OBJECT-TYPE
        SYNTAX      TNamedItemOrEmpty
        MAX-ACCESS  read-create
        STATUS      current
        DESCRIPTION
            "The value of tmnxOspfLFAExcludePolicy2 is the name of the second
             policy from which prefixes are excluded which match on the OSPF
             tag. Prefixes excluded from LFA (Loopfree Alternative) this way
             will not be used in the LFA calculation, regardless of its
             priority."
        DEFVAL { ''H }
        ::= { tmnxOspfGeneralExEntry 4 }

tmnxOspfLFAExcludePolicy3   OBJECT-TYPE
        SYNTAX      TNamedItemOrEmpty
        MAX-ACCESS  read-create
        STATUS      current
        DESCRIPTION
            "The value of tmnxOspfLFAExcludePolicy3 is the name of the third
             policy from which prefixes are excluded which match on the OSPF
             tag. Prefixes excluded from LFA (Loopfree Alternative) this way
             will not be used in the LFA calculation, regardless of its
             priority."
        DEFVAL { ''H }
        ::= { tmnxOspfGeneralExEntry 5 }

tmnxOspfLFAExcludePolicy4   OBJECT-TYPE
        SYNTAX      TNamedItemOrEmpty
        MAX-ACCESS  read-create
        STATUS      current
        DESCRIPTION
            "The value of tmnxOspfLFAExcludePolicy4 is the name of the fourth
             policy from which prefixes are excluded which match on the OSPF
             tag. Prefixes excluded from LFA (Loopfree Alternative) this way
             will not be used in the LFA calculation, regardless of its
             priority."
        DEFVAL { ''H }
        ::= { tmnxOspfGeneralExEntry 6 }

tmnxOspfLFAExcludePolicy5   OBJECT-TYPE
        SYNTAX      TNamedItemOrEmpty
        MAX-ACCESS  read-create
        STATUS      current
        DESCRIPTION
            "The value of tmnxOspfLFAExcludePolicy5 is the name of the fifth
             policy from which prefixes are excluded which match on the OSPF
             tag. Prefixes excluded from LFA (Loopfree Alternative) this way
             will not be used in the LFA calculation, regardless of its
             priority."
        DEFVAL { ''H }
        ::= { tmnxOspfGeneralExEntry 7 }

-- 
-- OSPF Notifications 
--  

tmnxOspfVirtIfStateChange NOTIFICATION-TYPE 
    OBJECTS { 
        tmnxOspfRouterId,       -- The originator of the notification 
        tmnxOspfVirtIfState     -- The new state 
    } 
    STATUS      current 
    DESCRIPTION 
        "A tmnxOspfVirtIfStateChange notification is generated when there 
         has been a change in the state of an OSPF virtual interface. 
  
         This notification should be generated when the interface state 
         regresses (e.g., goes from Point-to-Point to Down) or progresses 
         to a terminal state (i.e., Point-to-Point)." 
    ::= { tmnxOspfNotifications 1 } 
  
tmnxOspfNbrStateChange NOTIFICATION-TYPE 
    OBJECTS { 
        tmnxOspfRouterId,       -- The originator of the notification 
        tmnxOspfNbrState        -- The new state 
    } 
    STATUS       obsolete
    DESCRIPTION 
        "This notification is obsoleted in release 9.0. It is replaced with
         tmnxOspfNgNbrStateChange." 
         ::= { tmnxOspfNotifications 2 } 
  
tmnxOspfVirtNbrStateChange NOTIFICATION-TYPE 
    OBJECTS { 
        tmnxOspfRouterId,           -- The originator of the notification 
        tmnxOspfVirtNbrState        -- The new state 
    } 
    STATUS      current 
    DESCRIPTION 
        "A tmnxOspfVirtNbrStateChange notification is generated when there 
         has been a change in the state of an OSPF virtual neighbor. This 
         notification should be generated when the neighbor state regresses 
         (e.g., goes from Attempt or Full to 1-Way or Down) or progresses to 
         a terminal state (e.g., Full)." 
    ::= { tmnxOspfNotifications 3 } 
  
tmnxOspfIfConfigError NOTIFICATION-TYPE 
    OBJECTS { 
        tmnxOspfRouterId,           -- The originator of the notification 
        tmnxOspfPacketSrcAddressType,
        tmnxOspfPacketSrcAddress,   -- The source IP address 
        tmnxOspfConfigErrorType,    -- Type of error 
        tmnxOspfPacketType,
        tmnxOspfIfRxPackets
    } 
    STATUS      obsolete
    DESCRIPTION 
        "This notification is obsoleted in release 9.0. It is replaced with
         tmnxOspfNgIfConfigError." 
    ::= { tmnxOspfNotifications 4 } 
  
tmnxOspfVirtIfConfigError NOTIFICATION-TYPE 
    OBJECTS { 
        tmnxOspfRouterId,           -- The originator of the notification
        tmnxOspfPacketSrcAddressType,
        tmnxOspfPacketSrcAddress,   -- The source IP address 
        tmnxOspfConfigErrorType,    -- Type of error 
        tmnxOspfPacketType,
        tmnxOspfVirtIfRxPackets
    } 
    STATUS      current 
    DESCRIPTION 
        "A tmnxOspfVirtIfConfigError notification is generated when a 
         packet has been received on a virtual interface from a router whose 
         configuration parameters conflict with this router's configuration 
         parameters.  Note that the event 'optionMismatch' should cause a 
         notification only if it prevents an adjacency from forming." 
    ::= { tmnxOspfNotifications 5 } 
 
tmnxOspfIfAuthFailure NOTIFICATION-TYPE 
    OBJECTS { 
        tmnxOspfRouterId,           -- The originator of the notification 
        tmnxOspfPacketSrcAddressType,
        tmnxOspfPacketSrcAddress,   -- The source IP address 
        tmnxOspfConfigErrorType,    -- authTypeMismatch or authFailure 
        tmnxOspfPacketType,
        tmnxOspfIfAuthFailures
    } 
    STATUS      obsolete
    DESCRIPTION 
        "This notification is obsoleted in release 9.0. It is replaced with
         tmnxOspfNgIfAuthFailure." 
    ::= { tmnxOspfNotifications 6 } 
  
tmnxOspfVirtIfAuthFailure NOTIFICATION-TYPE 
    OBJECTS { 
        tmnxOspfRouterId,           -- The originator of the notification 
        tmnxOspfPacketSrcAddressType,
        tmnxOspfPacketSrcAddress,   -- The source IP address 
        tmnxOspfConfigErrorType,    -- authTypeMismatch or authFailure 
        tmnxOspfPacketType,
        tmnxOspfVirtIfAuthFailures
    } 
    STATUS      current 
    DESCRIPTION 
        "A tmnxOspfVirtIfAuthFailure notification is generated when a 
         packet has been received on a virtual interface from a router 
         whose authentication key or authentication type conflicts with 
         this router's authentication key or authentication type." 
     ::= { tmnxOspfNotifications 7 } 
  
tmnxOspfIfRxBadPacket NOTIFICATION-TYPE 
    OBJECTS {
        tmnxOspfRouterId,               -- The originator of the notification 
        tmnxOspfPacketSrcAddressType,
        tmnxOspfPacketSrcAddress,       -- The source IP address 
        tmnxOspfPacketType,
        tmnxOspfIfBadPacketTypes,
        tmnxOspfBadPacketErrType        -- Type of error
    } 
    STATUS      obsolete
    DESCRIPTION 
        "This notification is obsoleted in release 9.0. It is replaced with
         tmnxOspfNgIfRxBadPacket." 
    ::= { tmnxOspfNotifications 8 } 
  
tmnxOspfVirtIfRxBadPacket NOTIFICATION-TYPE 
    OBJECTS { 
        tmnxOspfRouterId,           -- The originator of the notification 
        tmnxOspfPacketSrcAddressType,
        tmnxOspfPacketSrcAddress,       -- The source IP address 
        tmnxOspfPacketType,
        tmnxOspfVirtIfBadPacketTypes,
        tmnxOspfBadPacketErrType        -- Type of error
    } 
    STATUS       current 
    DESCRIPTION 
        "A tmnxOspfVirtIfRxBadPacket notification is generated when an OSPF 
         packet that cannot be parsed has been received on a virtual 
         interface." 
    ::= { tmnxOspfNotifications 9 } 
  
tmnxOspfIfTxRetransmit NOTIFICATION-TYPE 
    OBJECTS { 
        tmnxOspfRouterId,           -- The originator of the notification 
        tmnxOspfPacketType,
        tmnxOspfNbrLsRetransQLen
    } 
    STATUS       obsolete
    DESCRIPTION 
        "This notification is obsoleted in release 9.0. It is replaced with
         tmnxOspfNgIfTxRetransmit." 
    ::= { tmnxOspfNotifications 10 } 
  
tmnxOspfVirtIfTxRetransmit NOTIFICATION-TYPE 
    OBJECTS {
        tmnxOspfRouterId,           -- The originator of the notification 
        tmnxOspfPacketType,
        tmnxOspfVirtNbrLsRetransQLen
    } 
    STATUS       current 
    DESCRIPTION 
        "A tmnxOspfVirtIfTxRetransmit notification is generated when an 
         OSPF packet has been retransmitted on a virtual interface." 
::= { tmnxOspfNotifications 11 } 
  
tmnxOspfAreaOriginateLsa NOTIFICATION-TYPE 
    OBJECTS {
        tmnxOspfRouterId,
        tmnxOspfAreaLsdbAge
    } 
    STATUS       current 
    DESCRIPTION 
        "A tmnxOspfAreaOriginateLsa notification is generated when a new 
         LSA has been originated by this router.  This notification should 
         not be invoked for simple refreshes of LSAs (which happens every 
         30 minutes), but instead will only be invoked when an LSA is 
         (re)originated due to a topology change.  Additionally, this 
         notification does not include LSAs that are  being flushed because 
         they have reached 'MaxAge'." 
    ::= { tmnxOspfNotifications 12 } 
  
tmnxOspfAreaMaxAgeLsa NOTIFICATION-TYPE 
    OBJECTS {
        tmnxOspfRouterId,       -- The originator of the notification 
        tmnxOspfAreaLsdbAge
    } 
    STATUS       current 
    DESCRIPTION 
        "A tmnxOspfAreaMaxAgeLsa notification is generated when one of 
         the LSAs in the router's link-state database has aged to 'MaxAge'." 
    ::= { tmnxOspfNotifications 13 } 
  
tmnxOspfLsdbOverflow NOTIFICATION-TYPE 
    OBJECTS {
        tmnxOspfRouterId,       -- The originator of the notification 
        tmnxOspfExtLsdbLimit
    } 
    STATUS       current 
    DESCRIPTION 
        "A tmnxOspfLsdbOverflow notification is generated when the 
         number of LSAs in the router's link-state database has 
         exceeded limit indicated by tmnxOspfExtLsdbLimit." 
    ::= { tmnxOspfNotifications 14 } 
  
tmnxOspfLsdbApproachingOverflow NOTIFICATION-TYPE 
    OBJECTS {
        tmnxOspfRouterId,       -- The originator of the notification 
        tmnxOspfExtLsdbLimit
   } 
    STATUS       current 
    DESCRIPTION 
        "A tmnxOspfLsdbApproachingOverflow notification is generated 
         when the number of LSAs in the router's link-state database 
         has exceeded ninety percent of the value indicated by 
         tmnxOspfExtLsdbLimit." 
    ::= { tmnxOspfNotifications 15 } 
  
tmnxOspfIfStateChange NOTIFICATION-TYPE 
    OBJECTS {
        tmnxOspfRouterId,       -- The originator of the notification 
        tmnxOspfIfState,        -- The new state 
        tmnxOspfIfIpName,       -- The OSPF interface IP address
        tmnxOspfIfEvent         -- The root cause for state change
    } 
    STATUS       obsolete
    DESCRIPTION 
        "This notification is obsoleted in release 9.0. It is replaced with
         tmnxOspfNgIfStateChange." 
    ::= { tmnxOspfNotifications 16 } 
  
tmnxOspfNssaTranslatorStatusChg NOTIFICATION-TYPE 
    OBJECTS {
        tmnxOspfRouterId,               -- The originator of the notification 
        tmnxOspfAreaNssaTranslatorState -- The current translation status 
    } 
    STATUS       current 
    DESCRIPTION 
        "A tmnxOspfNssaTranslatorStatusChg notification is generated
         when there has been a change in the router's ability to translate 
         OSPF type-7 LSAs into OSPF type-5 LSAs.  This notification should be   
         generated when the Translator Status transitions from or to any 
         defined status on a per area basis." 
    ::= { tmnxOspfNotifications 17 } 
  
tmnxOspfRestartStatusChange NOTIFICATION-TYPE 
    OBJECTS { 
        tmnxOspfRouterId,           -- The originator of the notification 
        tmnxOspfRestartStatus, 
        tmnxOspfRestartInterval, 
        tmnxOspfRestartExitRc
    } 
    STATUS       current 
    DESCRIPTION 
        "A tmnxOspfRestartStatusChange notification is generated when 
         there has been a change in the graceful restart state for the 
         router.  This notification should be generated when the router 
         restart status changes." 
    ::= { tmnxOspfNotifications 18 } 
     
tmnxOspfNbrRestartHlprStsChg NOTIFICATION-TYPE 
    OBJECTS {
        tmnxOspfRouterId,           -- The originator of the notification 
        tmnxOspfNbrRestartHelperStatus, 
        tmnxOspfNbrRestartHelperAge, 
        tmnxOspfNbrRestartHelperExitRc
    } 
    STATUS       obsolete
    DESCRIPTION 
        "This notification is obsoleted in release 9.0. It is replaced with
         tmnxOspfNgNbrRestartHlprStsChg." 
    ::= { tmnxOspfNotifications 19 } 
     
tmnxOspfVirtNbrRestartHlprStsChg NOTIFICATION-TYPE 
    OBJECTS { 
        tmnxOspfRouterId,           -- The originator of the notification 
        tmnxOspfVirtNbrRestartHelperStatus, 
        tmnxOspfVirtNbrRestartHelperAge, 
        tmnxOspfVirtNbrRestartHelperExitRc 
    } 
    STATUS       current 
    DESCRIPTION 
        "An tmnxOspfVirtNbrRestartHlprStsChg notification is 
         generated when there has been a change in the graceful restart 
         helper state for the virtual neighbor.  This notification should 
         be generated when the virtual neighbor restart helper status 
         transitions for a virtual neighbor." 
    ::= { tmnxOspfNotifications 20 } 
  
tmnxOspfSpfRunsStopped  NOTIFICATION-TYPE
    OBJECTS {
        tmnxOspfRouterId
    }
    STATUS      current
    DESCRIPTION
        "A tmnxOspfSpfRunsStopped trap signifies that there
         are insufficient memory resources on the system to
         run the SPF to completion. Consequently, OSPF will
         stop running SPFs until enough memory resources become
         available."
    ::= { tmnxOspfNotifications 21 }

tmnxOspfSpfRunsRestarted  NOTIFICATION-TYPE
    OBJECTS {
        tmnxOspfRouterId
    }
    STATUS      current
    DESCRIPTION
        "A tmnxOspfSpfRunsRestarted trap signifies that there
         are sufficient memory resources on the system to start
         running the SPF to completion. Consequently, OSPF will
         resume running the SPFs as required."
    ::= { tmnxOspfNotifications 22 }

tmnxOspfOverloadEntered NOTIFICATION-TYPE
    OBJECTS {
        tmnxOspfRouterId,
        tmnxOspfLastOverloadEnterCode
    }
    STATUS      current
    DESCRIPTION
        "A tmnxOspfOverloadEntered trap is sent out when OSPF
         enters the overload state. tmnxOspfLastOverloadEnterCode
         holds the condition which caused OSPF to get into overload"
    ::= { tmnxOspfNotifications 23 }

tmnxOspfOverloadExited NOTIFICATION-TYPE
    OBJECTS {
        tmnxOspfRouterId,
        tmnxOspfLastOverloadExitCode
    }
    STATUS      current
    DESCRIPTION
        "A tmnxOspfOverloadExited trap is sent out when OSPF
         exits the overload state. tmnxOspfLastOverloadExitCode
         holds the condition which caused OSPF to get out of overload"
    ::= { tmnxOspfNotifications 24 }

tmnxOspfAsOriginateLsa NOTIFICATION-TYPE 
    OBJECTS {
        tmnxOspfRouterId,
        tmnxOspfAsLsdbAge
    } 
    STATUS       current 
    DESCRIPTION 
        "A tmnxOspfAsOriginateLsa notification is generated when a new 
         LSA has been originated by this router.  This notification should 
         not be invoked for simple refreshes of LSAs (which happens every 
         30 minutes), but instead will only be invoked when an LSA is 
         (re)originated due to a topology change.  Additionally, this 
         notification does not include LSAs that are  being flushed because 
         they have reached 'MaxAge'." 
    ::= { tmnxOspfNotifications 25 } 
  
tmnxOspfAsMaxAgeLsa NOTIFICATION-TYPE 
    OBJECTS {
        tmnxOspfRouterId,       -- The originator of the notification 
        tmnxOspfAsLsdbAge
    } 
    STATUS       current 
    DESCRIPTION 
        "A tmnxOspfAsMaxAgeLsa notification is generated when one of 
         the LSAs in the router's link-state database has aged to 'MaxAge'." 
    ::= { tmnxOspfNotifications 26 }

tmnxOspfLinkOriginateLsa NOTIFICATION-TYPE 
    OBJECTS {
        tmnxOspfRouterId,
        tmnxOspfLinkLsdbAge
    } 
    STATUS       obsolete
    DESCRIPTION 
        "This notification is obsoleted in release 9.0. It is replaced with
         tmnxOspfNgLinkOriginateLsa." 
    ::= { tmnxOspfNotifications 27 } 
  
tmnxOspfLinkMaxAgeLsa NOTIFICATION-TYPE 
    OBJECTS {
        tmnxOspfRouterId,       -- The originator of the notification 
        tmnxOspfLinkLsdbAge
    } 
    STATUS       obsolete
    DESCRIPTION 
        "This notification is obsoleted in release 9.0. It is replaced with
         tmnxOspfNgLinkMaxAgeLsa." 
    ::= { tmnxOspfNotifications 28 }

tmnxOspfLdpSyncTimerStarted NOTIFICATION-TYPE
    OBJECTS {
        tmnxOspfRouterId,
        tmnxOspfIfLdpSyncTimerState
    }
    STATUS  obsolete
    DESCRIPTION
        "This notification is obsoleted in release 9.0. It is replaced with
         tmnxOspfNgLdpSyncTimerStarted."
    ::= { tmnxOspfNotifications 29 }

tmnxOspfLdpSyncExit NOTIFICATION-TYPE
    OBJECTS {
        tmnxOspfRouterId,
        tmnxOspfIfLdpSyncTimerState
    }
    STATUS  obsolete
    DESCRIPTION
        "This notification is obsoleted in release 9.0. It is replaced with
         tmnxOspfNgLdpSyncExit."
    ::= { tmnxOspfNotifications 30 }

tmnxOspfShamIfStateChange NOTIFICATION-TYPE 
    OBJECTS { 
        tmnxOspfRouterId,       -- The originator of the notification 
        tmnxOspfShamIfState     -- The new state 
    } 
    STATUS      current 
    DESCRIPTION 
        "A tmnxOspfShamIfStateChange notification is generated when there 
         has been a change in the state of an OSPF sham link. 
  
         This notification should be generated when the interface state 
         regresses (e.g., goes from Point-to-Point to Down) or progresses 
         to a terminal state (i.e., Point-to-Point)." 
    ::= { tmnxOspfNotifications 31 } 

tmnxOspfShamNbrStateChange NOTIFICATION-TYPE 
    OBJECTS { 
        tmnxOspfRouterId,           -- The originator of the notification 
        tmnxOspfShamNbrState        -- The new state 
    } 
    STATUS      current 
    DESCRIPTION 
        "A tmnxOspfShamNbrStateChange notification is generated when there 
         has been a change in the state of an OSPF sham link neighbor. This 
         notification should be generated when the neighbor state regresses 
         (e.g., goes from Attempt or Full to 1-Way or Down) or progresses to 
         a terminal state (e.g., Full)." 
    ::= { tmnxOspfNotifications 32 } 

tmnxOspfShamIfConfigError NOTIFICATION-TYPE 
    OBJECTS { 
        tmnxOspfRouterId,           -- The originator of the notification
        tmnxOspfPacketSrcAddressType,
        tmnxOspfPacketSrcAddress,   -- The source IP address 
        tmnxOspfConfigErrorType,    -- Type of error 
        tmnxOspfPacketType,
        tmnxOspfShamIfRxPackets
    } 
    STATUS      current 
    DESCRIPTION 
        "A tmnxOspfShamIfConfigError notification is generated when a 
         packet has been received on a sham link from a router whose 
         configuration parameters conflict with this router's configuration 
         parameters.  Note that the event 'optionMismatch' should cause a 
         notification only if it prevents an adjacency from forming." 
    ::= { tmnxOspfNotifications 33 } 

tmnxOspfShamIfAuthFailure NOTIFICATION-TYPE 
    OBJECTS { 
        tmnxOspfRouterId,           -- The originator of the notification 
        tmnxOspfPacketSrcAddressType,
        tmnxOspfPacketSrcAddress,   -- The source IP address 
        tmnxOspfConfigErrorType,    -- authTypeMismatch or authFailure 
        tmnxOspfPacketType,
        tmnxOspfShamIfAuthFailures
    } 
    STATUS      current 
    DESCRIPTION 
        "A tmnxOspfShamIfAuthFailure notification is generated when a 
         packet has been received on a sham link from a router 
         whose authentication key or authentication type conflicts with 
         this router's authentication key or authentication type." 
     ::= { tmnxOspfNotifications 34 } 

tmnxOspfShamIfRxBadPacket NOTIFICATION-TYPE 
    OBJECTS { 
        tmnxOspfRouterId,           -- The originator of the notification 
        tmnxOspfPacketSrcAddressType,
        tmnxOspfPacketSrcAddress,       -- The source IP address 
        tmnxOspfPacketType,
        tmnxOspfShamIfBadPacketTypes,
        tmnxOspfBadPacketErrType        -- Type of error
    } 
    STATUS       current 
    DESCRIPTION 
        "A tmnxOspfShamIfRxBadPacket notification is generated when an OSPF 
         packet that cannot be parsed has been received on a sham link."
    ::= { tmnxOspfNotifications 35 } 

tmnxOspfShamIfTxRetransmit NOTIFICATION-TYPE 
    OBJECTS {
        tmnxOspfRouterId,           -- The originator of the notification 
        tmnxOspfPacketType,
        tmnxOspfShamNbrLsRetransQLen
    } 
    STATUS       current 
    DESCRIPTION 
        "A tmnxOspfShamIfTxRetransmit notification is generated when an 
         OSPF packet has been retransmitted on a sham link." 
    ::= { tmnxOspfNotifications 36 } 

tmnxOspfShamNbrRestartHlprStsChg NOTIFICATION-TYPE 
    OBJECTS { 
        tmnxOspfRouterId,           -- The originator of the notification 
        tmnxOspfShamNbrRestartHelperStatus, 
        tmnxOspfShamNbrRestartHelperAge, 
        tmnxOspfShamNbrRestartHelperExitRc 
    } 
    STATUS       current 
    DESCRIPTION 
        "An tmnxOspfShamNbrRestartHlprStsChg notification is 
         generated when there has been a change in the graceful restart 
         helper state for the sham link neighbor.  This notification should 
         be generated when the sham link neighbor restart helper status 
         transitions for a sham link neighbor." 
    ::= { tmnxOspfNotifications 37 } 

tmnxOspfFailureDisabled  NOTIFICATION-TYPE
    OBJECTS {
        tmnxOspfRouterId,
        tmnxOspfFailureReasonCode
    }
    STATUS      current
    DESCRIPTION
        "A tmnxOspfFailureDisabled notification is generated when OSPF is 
         operationally brought down. Reason for the failure is indicated by 
         tmnxOspfFailureReasonCode."
    ::= { tmnxOspfNotifications 38 }

tmnxOspfExportLimitReached  NOTIFICATION-TYPE
    OBJECTS {
        tmnxOspfRouterId,
        tmnxOspfExportLimit
    }
    STATUS  current
    DESCRIPTION
        "A tmnxOspfExportLimitReached notification is generated when the 
         configured value of exported routes, tmnxOspfExportLimit is reached. 
         Additional routes would not be exported into OSPF or OSPF3 from the 
         route table."
    ::= { tmnxOspfNotifications 39 }

tmnxOspfExportLimitWarning  NOTIFICATION-TYPE
    OBJECTS {
        tmnxOspfRouterId,
        tmnxOspfExportLimit,
        tmnxOspfExportLimitLogPercent
    }
    STATUS  current
    DESCRIPTION
        "A tmnxOspfExportLimitWarning notification is generated when the number 
         of exported routes is equal to the configured percent, 
         tmnxOspfExportLimitLogPercent of the export limit, tmnxOspfExportLimit.
         Additional routes will continue to be exported into OSPF or OSPF3 from 
         the route table till the export limit is reached."
    ::= { tmnxOspfNotifications 40 }

tmnxOspfRoutesExpLmtDropped  NOTIFICATION-TYPE
    OBJECTS {
        tmnxOspfRouterId,
        tmnxOspfExportLimit
    }
    STATUS  current
    DESCRIPTION
        "A tmnxOspfRoutesExpLmtDropped notification is generated when the 
         number of exported routes drops below the export limit, 
         tmnxOspfExportLimit."
    ::= { tmnxOspfNotifications 41 }

tmnxOspfNgNbrStateChange NOTIFICATION-TYPE
    OBJECTS {
        tmnxOspfRouterId,       -- The originator of the notification
        tmnxOspfNgNbrState      -- The new state
    }
    STATUS       current
    DESCRIPTION
        "A tmnxOspfNgNbrStateChange notification is generated when there has
         been a change in the state of a non-virtual OSPF neighbor. This
         notification should be generated when the neighbor state regresses
         (e.g., goes from Attempt or Full to 1-Way or Down) or progresses
         to a terminal state (e.g., 2-Way or Full). When an neighbor
         transitions from or to Full on non-broadcast multi-access and
         broadcast networks, the notification should be generated by the
         designated router.  A designated router transitioning to Down will
         be noted by the tmnxOspfNgIfStateChange notification."
    ::= { tmnxOspfNotifications 42 }

tmnxOspfNgIfConfigError NOTIFICATION-TYPE
    OBJECTS {
        tmnxOspfRouterId,           -- The originator of the notification
        tmnxOspfPacketSrcAddressType,
        tmnxOspfPacketSrcAddress,   -- The source IP address
        tmnxOspfConfigErrorType,    -- Type of error
        tmnxOspfPacketType,
        tmnxOspfNgIfRxPackets
    }
    STATUS      current
    DESCRIPTION
        "A tmnxOspfNgIfConfigError notification is generated when a packet has
         been received on a non-virtual interface from a router whose
         configuration parameters conflict with this router's configuration
         parameters.  Note that the event 'optionMismatch' should cause a
         notification only if it prevents an adjacency from forming."
    ::= { tmnxOspfNotifications 43 }

tmnxOspfNgIfAuthFailure NOTIFICATION-TYPE
    OBJECTS {
        tmnxOspfRouterId,           -- The originator of the notification
        tmnxOspfPacketSrcAddressType,
        tmnxOspfPacketSrcAddress,   -- The source IP address
        tmnxOspfConfigErrorType,    -- authTypeMismatch or authFailure
        tmnxOspfPacketType,
        tmnxOspfNgIfAuthFailures
    }
    STATUS      current
    DESCRIPTION
        "A tmnxOspfNgIfAuthFailure notification is generated when a packet
         has been received on a non-virtual interface from a router
         whose authentication key or authentication type conflicts with this
         router's authentication key or authentication type."
    ::= { tmnxOspfNotifications 44 }

tmnxOspfNgIfRxBadPacket NOTIFICATION-TYPE
    OBJECTS {
        tmnxOspfRouterId,               -- The originator of the notification
        tmnxOspfPacketSrcAddressType,
        tmnxOspfPacketSrcAddress,       -- The source IP address
        tmnxOspfPacketType,
        tmnxOspfNgIfBadPacketTypes,
        tmnxOspfBadPacketErrType        -- Type of error
    }
    STATUS      current
    DESCRIPTION
        "A tmnxOspfNgIfRxBadPacket notification is generated when an OSPF packet
         that cannot be parsed has been received on a non-virtual interface."
    ::= { tmnxOspfNotifications 45 }

tmnxOspfNgIfTxRetransmit NOTIFICATION-TYPE
    OBJECTS {
        tmnxOspfRouterId,           -- The originator of the notification
        tmnxOspfPacketType,
        tmnxOspfNgNbrLsRetransQLen
    }
    STATUS       current
    DESCRIPTION
        "A tmnxOspfNgIfTxRetransmit notification is generated when an
         OSPF packet has been retransmitted on a non-virtual interface."
    ::= { tmnxOspfNotifications 46 }

tmnxOspfNgIfStateChange NOTIFICATION-TYPE
    OBJECTS {
        tmnxOspfRouterId,       -- The originator of the notification
        tmnxOspfNgIfState,      -- The new state
        tmnxOspfIfIpName,       -- The OSPF interface IP address
        tmnxOspfIfEvent         -- The root cause for state change
    }
    STATUS       current
    DESCRIPTION
        "A tmnxOspfNgIfStateChange notification is generated when there
         has been a change in the state of a non-virtual OSPF interface.
         This notification should be generated when the interface state
         regresses (e.g., goes from Dr to Down) or progresses to a terminal
         state  (i.e., Point-to-Point, DR Other, Dr, or Backup)."
    ::= { tmnxOspfNotifications 47 }

tmnxOspfNgNbrRestartHlprStsChg NOTIFICATION-TYPE
    OBJECTS {
        tmnxOspfRouterId,           -- The originator of the notification
        tmnxOspfNgNbrRestartHelperStatus,
        tmnxOspfNgNbrRestartHelperAge,
        tmnxOspfNgNbrRestartHelperExitRc
    }
    STATUS       current
    DESCRIPTION
        "A tmnxOspfNgNbrRestartHlprStsChg notification is generated
         when there has been a change in the graceful restart helper state
         for the neighbor.  This notification should be generated when the
         neighbor restart helper status transitions for a neighbor."
    ::= { tmnxOspfNotifications 48 }

tmnxOspfNgLinkOriginateLsa NOTIFICATION-TYPE
    OBJECTS {
        tmnxOspfRouterId,
        tmnxOspfNgLinkLsdbAge
    }
    STATUS       current
    DESCRIPTION
        "A tmnxOspfNgLinkOriginateLsa notification is generated when a new
         LSA has been originated by this router.  This notification should
         not be invoked for simple refreshes of LSAs (which happens every
         30 minutes), but instead will only be invoked when an LSA is
         (re)originated due to a topology change.  Additionally, this
         notification does not include LSAs that are  being flushed because
         they have reached 'MaxAge'."
    ::= { tmnxOspfNotifications 49 }

tmnxOspfNgLinkMaxAgeLsa NOTIFICATION-TYPE
    OBJECTS {
        tmnxOspfRouterId,       -- The originator of the notification
        tmnxOspfNgLinkLsdbAge
    }
    STATUS       current
    DESCRIPTION
        "A tmnxOspfNgLinkMaxAgeLsa notification is generated when one of
         the LSAs in the router's link-state database has aged to 'MaxAge'."
    ::= { tmnxOspfNotifications 50 }

tmnxOspfNgLdpSyncTimerStarted NOTIFICATION-TYPE
    OBJECTS {
        tmnxOspfRouterId,
        tmnxOspfNgIfLdpSyncTimerState
    }
    STATUS  current
    DESCRIPTION
        "A notification sent when the tmnxOspfNgIfLdpSyncTimerState is started.
         The timer is started from the time the LDP session to the neighbor
         is up over the interface. This is to allow for the label FEC bindings
         to be exchanged."
    ::= { tmnxOspfNotifications 51 }

tmnxOspfNgLdpSyncExit NOTIFICATION-TYPE
    OBJECTS {
        tmnxOspfRouterId,
        tmnxOspfNgIfLdpSyncTimerState
    }
    STATUS  current
    DESCRIPTION
        "A notification sent when IGP-LDP synchronization has stopped. The
         cause of this event is indicated by vRtrIsisIfLdpSyncTimerState, one of
         them being expiry of the vRtrIfLdpSyncTimer.  The IGP link metric is
         restored to normal levels."
    ::= { tmnxOspfNotifications 52 }

--
-- Conformance Information
--

tmnxOspfCompliances OBJECT IDENTIFIER    ::= { tmnxOspfConformance 1 }
tmnxOspfGroups      OBJECT IDENTIFIER    ::= { tmnxOspfConformance 2 }

--
-- Compliance Statements
--

tmnxOspfCompliance  MODULE-COMPLIANCE
    STATUS  obsolete
    DESCRIPTION
            "The compliance statement for management of OSPF features
             on Alcatel 7x50 SR series systems."
    MODULE
        MANDATORY-GROUPS {
            tmnxOspfGeneralGroup,
            tmnxOspfAreaGroup,
            tmnxOspfHostGroup,
            tmnxOspfIfGroup,
            tmnxOspfVirtIfGroup,
            tmnxOspfNbrGroup,
            tmnxOspfVirtNbrGroup,
            tmnxOspfAreaAggrGroup,
            tmnxOspfMD5KeyGroup,
            tmnxOspfNotifyObjsGroup,
            tmnxOspfNotificationGroup
        }
    ::= { tmnxOspfCompliances 1 }

tmnxOspfV5v0Compliance  MODULE-COMPLIANCE
    STATUS  obsolete
    DESCRIPTION
            "The compliance statement for management of OSPF features
             on Alcatel-Lucent SROS series systems."
    MODULE
        MANDATORY-GROUPS {
            tmnxOspfGeneralV5v0Group,
            tmnxOspfAreaGroup,
            tmnxOspfHostGroup,
            tmnxOspfIfV5v0Group,
            tmnxOspfVirtIfGroup,
            tmnxOspfNbrGroup,
            tmnxOspfVirtNbrGroup,
            tmnxOspfAreaAggrGroup,
            tmnxOspfMD5KeyGroup,
            tmnxOspfNotifyObjsGroup,
            tmnxOspfNotificationGroup
        }
    ::= { tmnxOspfCompliances 2 }
    
tmnxOspfV6v0Compliance  MODULE-COMPLIANCE
    STATUS  obsolete
    DESCRIPTION
            "The compliance statement for management of OSPF features
             on 6.0 release of Alcatel-Lucent SROS series systems."
    MODULE
        MANDATORY-GROUPS {
            tmnxOspfGeneralV5v0Group,
            tmnxOspfAreaGroup,
            tmnxOspfHostGroup,
            tmnxOspfIfV5v0Group,
            tmnxOspfVirtIfGroup,
            tmnxOspfNbrGroup,
            tmnxOspfVirtNbrGroup,
            tmnxOspfAreaAggrGroup,
            tmnxOspfMD5KeyGroup,
            tmnxOspfNotifyObjsGroup,
            tmnxOspfNotificationGroup,
            tmnxOspfIfV6v0Group,
            tmnxOspfGeneralV6v0Group,
            tmnxOspfNotificationV6v0Group
        }
    ::= { tmnxOspfCompliances 3 }

tmnxOspfV6v1Compliance  MODULE-COMPLIANCE
    STATUS  obsolete
    DESCRIPTION
            "The compliance statement for management of OSPF features
             on 6.1 release of Alcatel-Lucent SROS series systems."
    MODULE
        MANDATORY-GROUPS {
            tmnxOspfGeneralV5v0Group,
            tmnxOspfAreaGroup,
            tmnxOspfHostGroup,
            tmnxOspfIfV5v0Group,
            tmnxOspfVirtIfGroup,
            tmnxOspfNbrGroup,
            tmnxOspfVirtNbrGroup,
            tmnxOspfAreaAggrGroup,
            tmnxOspfMD5KeyGroup,
            tmnxOspfNotifyObjsGroup,
            tmnxOspfNotificationGroup,
            tmnxOspfIfV6v0Group,
            tmnxOspfGeneralV6v0Group,
            tmnxOspfNotificationV6v0Group,
            tmnxOspfGeneralV6v1Group
        }
    ::= { tmnxOspfCompliances 4 }

tmnxOspfV7v0Compliance  MODULE-COMPLIANCE
    STATUS  obsolete
    DESCRIPTION
            "The compliance statement for management of OSPF features
             on 7.0 release of Alcatel-Lucent SROS series systems."
    MODULE
        MANDATORY-GROUPS {
            tmnxOspfGeneralV5v0Group,
            tmnxOspfAreaGroup,
            tmnxOspfHostGroup,
            tmnxOspfIfV5v0Group,
            tmnxOspfVirtIfGroup,
            tmnxOspfNbrGroup,
            tmnxOspfVirtNbrGroup,
            tmnxOspfAreaAggrGroup,
            tmnxOspfMD5KeyGroup,
            tmnxOspfNotifyObjsGroup,
            tmnxOspfNotificationGroup,
            tmnxOspfIfV6v0Group,
            tmnxOspfGeneralV6v0Group,
            tmnxOspfNotificationV6v0Group,
            tmnxOspfGeneralV6v1Group,
            tmnxOspfShamLinksV7v0Group,
            tmnxOspfNotificationV7v0Group,
            tmnxOspfNotifyObjsV7v0Group,
            tmnxOspfGeneralV7v0Group,
            tmnxOspfGenNotificationV7v0Grp
        }
    ::= { tmnxOspfCompliances 5 }

tmnxOspfV8v0Compliance  MODULE-COMPLIANCE
    STATUS  obsolete
    DESCRIPTION
            "The compliance statement for management of OSPF features
             on 8.0 release of Alcatel-Lucent SROS series systems."
    MODULE
        MANDATORY-GROUPS {
            tmnxOspfGeneralV5v0Group,
            tmnxOspfAreaGroup,
            tmnxOspfHostGroup,
            tmnxOspfIfV5v0Group,
            tmnxOspfVirtIfGroup,
            tmnxOspfNbrGroup,
            tmnxOspfVirtNbrGroup,
            tmnxOspfAreaAggrGroup,
            tmnxOspfMD5KeyGroup,
            tmnxOspfNotifyObjsGroup,
            tmnxOspfNotificationGroup,
            tmnxOspfIfV6v0Group,
            tmnxOspfGeneralV6v0Group,
            tmnxOspfNotificationV6v0Group,
            tmnxOspfGeneralV6v1Group,
            tmnxOspfShamLinksV7v0Group,
            tmnxOspfNotificationV7v0Group,
            tmnxOspfNotifyObjsV7v0Group,
            tmnxOspfGeneralV7v0Group,
            tmnxOspfGenNotificationV7v0Grp,
            tmnxOspfAreaV8v0Group,
            tmnxOspfIfV8v0Group,
            tmnxOspfVirtIfV8v0Group,
            tmnxOspfNotifyObjsV8v0Group,
            tmnxOspfGeneralV8v0Group
        }
    ::= { tmnxOspfCompliances 6 }

tmnxOspfV9v0Compliance  MODULE-COMPLIANCE
    STATUS  obsolete
    DESCRIPTION
            "The compliance statement for management of OSPF features
             on 9.0 release of Alcatel-Lucent SROS series systems."
    MODULE
        MANDATORY-GROUPS {
            tmnxOspfGeneralV5v0Group,
            -- tmnxOspfAreaGroup,
            -- tmnxOspfAreaV8v0Group,
            tmnxOspfAreaV9v0Group,
            tmnxOspfNgLinkLsdbV9v0Group,
            tmnxOspfHostGroup,
            -- tmnxOspfIfV5v0Group,
            tmnxOspfNgIfV9v0Group,
            tmnxOspfNgIfOperV9v0Group,
            tmnxOspfNgIfStatsV9v0Group,
            tmnxOspfVirtIfGroup,
            -- tmnxOspfNbrGroup,
            tmnxOspfNgNbrV9v0Group,
            tmnxOspfVirtNbrGroup,
            tmnxOspfAreaAggrGroup,
            -- tmnxOspfMD5KeyGroup,
            tmnxOspfMD5KeyV9v0Group,
            tmnxOspfNotifyObjsGroup,
            -- tmnxOspfNotificationGroup,
            -- tmnxOspfIfV6v0Group,
            tmnxOspfGeneralV6v0Group,
            -- tmnxOspfNotificationV6v0Group,
            tmnxOspfNotificationV9v0Group,
            tmnxOspfGeneralV6v1Group,
            tmnxOspfShamLinksV7v0Group,
            tmnxOspfNotificationV7v0Group,
            -- tmnxOspfNotifyObjsV7v0Group,
            tmnxOspfGeneralV7v0Group,
            tmnxOspfGenNotificationV7v0Grp,
            tmnxOspfIfV8v0Group,
            tmnxOspfVirtIfV8v0Group,
            -- tmnxOspfNotifyObjsV8v0Group,
            tmnxOspfGeneralV8v0Group
        }
    ::= { tmnxOspfCompliances 7 }

tmnxOspfV10v0Compliance  MODULE-COMPLIANCE
    STATUS  obsolete
    DESCRIPTION
            "The compliance statement for management of OSPF features
             on 10.0 release of Alcatel-Lucent SROS series systems."
    MODULE
        MANDATORY-GROUPS {
            tmnxOspfGeneralV5v0Group,
            -- tmnxOspfAreaGroup,
            -- tmnxOspfAreaV8v0Group,
            tmnxOspfAreaV9v0Group,
            tmnxOspfNgLinkLsdbV9v0Group,
            tmnxOspfHostGroup,
            -- tmnxOspfIfV5v0Group,
            tmnxOspfNgIfV9v0Group,
            tmnxOspfNgIfOperV9v0Group,
            tmnxOspfNgIfStatsV9v0Group,
            tmnxOspfVirtIfGroup,
            -- tmnxOspfNbrGroup,
            tmnxOspfNgNbrV9v0Group,
            tmnxOspfVirtNbrGroup,
            tmnxOspfAreaAggrGroup,
            -- tmnxOspfMD5KeyGroup,
            tmnxOspfMD5KeyV9v0Group,
            tmnxOspfNotifyObjsGroup,
            -- tmnxOspfNotificationGroup,
            -- tmnxOspfIfV6v0Group,
            tmnxOspfGeneralV6v0Group,
            -- tmnxOspfNotificationV6v0Group,
            tmnxOspfNotificationV9v0Group,
            tmnxOspfGeneralV6v1Group,
            tmnxOspfShamLinksV7v0Group,
            tmnxOspfNotificationV7v0Group,
            -- tmnxOspfNotifyObjsV7v0Group,
            tmnxOspfGeneralV7v0Group,
            tmnxOspfGenNotificationV7v0Grp,
            tmnxOspfIfV8v0Group,
            tmnxOspfVirtIfV8v0Group,
            -- tmnxOspfNotifyObjsV8v0Group,
            tmnxOspfGeneralV8v0Group,
            tmnxOspfGeneralV10v0Group,
            tmnxOspfFRRV10v0Group
        }
    ::= { tmnxOspfCompliances 8 }

tmnxOspfV11v0Compliance  MODULE-COMPLIANCE
    STATUS  obsolete
    DESCRIPTION
            "The compliance statement for management of OSPF features
             on 11.0 release of Alcatel-Lucent SROS series systems."
    MODULE
        MANDATORY-GROUPS {
            tmnxOspfGeneralV5v0Group,
            -- tmnxOspfAreaGroup,
            -- tmnxOspfAreaV8v0Group,
            tmnxOspfAreaV9v0Group,
            tmnxOspfNgLinkLsdbV9v0Group,
            tmnxOspfHostGroup,
            -- tmnxOspfIfV5v0Group,
            tmnxOspfNgIfV9v0Group,
            tmnxOspfNgIfOperV9v0Group,
            tmnxOspfNgIfStatsV9v0Group,
            tmnxOspfVirtIfGroup,
            -- tmnxOspfNbrGroup,
            tmnxOspfNgNbrV9v0Group,
            tmnxOspfVirtNbrGroup,
            tmnxOspfAreaAggrGroup,
            -- tmnxOspfMD5KeyGroup,
            tmnxOspfMD5KeyV9v0Group,
            tmnxOspfNotifyObjsGroup,
            -- tmnxOspfNotificationGroup,
            -- tmnxOspfIfV6v0Group,
            tmnxOspfGeneralV6v0Group,
            -- tmnxOspfNotificationV6v0Group,
            tmnxOspfNotificationV9v0Group,
            tmnxOspfGeneralV6v1Group,
            tmnxOspfShamLinksV7v0Group,
            tmnxOspfNotificationV7v0Group,
            -- tmnxOspfNotifyObjsV7v0Group,
            tmnxOspfGeneralV7v0Group,
            tmnxOspfGenNotificationV7v0Grp,
            tmnxOspfIfV8v0Group,
            tmnxOspfVirtIfV8v0Group,
            -- tmnxOspfNotifyObjsV8v0Group,
            tmnxOspfGeneralV8v0Group,
            tmnxOspfGeneralV10v0Group,
            tmnxOspfFRRV10v0Group,
            tmnxOspfFRRV11v0Group,
            tmnxOspfGeneralV11v0Group
        }
    ::= { tmnxOspfCompliances 9 }

tmnxOspfV12v0Compliance  MODULE-COMPLIANCE
    STATUS  current
    DESCRIPTION
            "The compliance statement for management of OSPF features
             on 12.0 release of Alcatel-Lucent SROS series systems."
    MODULE
        MANDATORY-GROUPS {
            tmnxOspfGeneralV5v0Group,
            -- tmnxOspfAreaGroup,
            -- tmnxOspfAreaV8v0Group,
            tmnxOspfAreaV9v0Group,
            tmnxOspfNgLinkLsdbV9v0Group,
            tmnxOspfHostGroup,
            -- tmnxOspfIfV5v0Group,
            tmnxOspfNgIfV9v0Group,
            tmnxOspfNgIfOperV9v0Group,
            tmnxOspfNgIfStatsV9v0Group,
            tmnxOspfVirtIfGroup,
            -- tmnxOspfNbrGroup,
            tmnxOspfNgNbrV9v0Group,
            tmnxOspfVirtNbrGroup,
            tmnxOspfAreaAggrGroup,
            -- tmnxOspfMD5KeyGroup,
            tmnxOspfMD5KeyV9v0Group,
            tmnxOspfNotifyObjsGroup,
            -- tmnxOspfNotificationGroup,
            -- tmnxOspfIfV6v0Group,
            tmnxOspfGeneralV6v0Group,
            -- tmnxOspfNotificationV6v0Group,
            tmnxOspfNotificationV9v0Group,
            tmnxOspfGeneralV6v1Group,
            tmnxOspfShamLinksV7v0Group,
            tmnxOspfNotificationV7v0Group,
            -- tmnxOspfNotifyObjsV7v0Group,
            tmnxOspfGeneralV7v0Group,
            tmnxOspfGenNotificationV7v0Grp,
            tmnxOspfIfV8v0Group,
            tmnxOspfVirtIfV8v0Group,
            -- tmnxOspfNotifyObjsV8v0Group,
            tmnxOspfGeneralV8v0Group,
            tmnxOspfGeneralV10v0Group,
            tmnxOspfFRRV10v0Group,
            tmnxOspfFRRV11v0Group,
            tmnxOspfGeneralV11v0Group,
            tmnxOspfGeneralV12v0Group
        }
    ::= { tmnxOspfCompliances 10 }

--
-- Units of conformance
--

tmnxOspfGeneralGroup OBJECT-GROUP
    OBJECTS {
        tmnxOspfGeneralEntries,   
        tmnxOspfGeneralLastChanged,
        tmnxOspfRouterId,
        tmnxOspfAdminState, 
        tmnxOspfASBdrRtrStatus, 
        tmnxOspfRFC1583Compatibility,
        tmnxOspfExtLsdbLimit,
        tmnxOspfMulticastExtensions, 
        tmnxOspfExitOverflowInterval, 
        tmnxOspfDemandExtensions, 
        tmnxOspfReferenceBandwidth,  
        tmnxOspfStrictLsaChecking, 
        tmnxOspfRestartSupport, 
        tmnxOspfRestartInterval, 
        tmnxOspfPreference,
        tmnxOspfExternalPreference,
        tmnxOspfExportPolicy1,
        tmnxOspfExportPolicy2,
        tmnxOspfExportPolicy3,
        tmnxOspfExportPolicy4,
        tmnxOspfExportPolicy5,
        tmnxOspfManualSpfTrigger,
        tmnxOspfOverloadAdmState,
        tmnxOspfOverloadInterval,
        tmnxOspfBootOverloadAdmState,
        tmnxOspfBootOverloadInterval,
        tmnxOspfOverloadStubs,
        tmnxOspfSpfMaxWait,
        tmnxOspfSpfInitialWait,
        tmnxOspfSpfSecondWait,
        tmnxOspfLsaGenMaxWait,
        tmnxOspfLsaGenInitialWait,
        tmnxOspfLsaGenSecondWait,
        tmnxOspfLsaArrivalWait,
        tmnxOspfTESupport,
        tmnxOspfUnicastImport,
        tmnxOspfMulticastImport,
        tmnxOspfGREnable,
        tmnxOspfGRHelperMode,
        tmnxOspfAreaBdrRtrStatus, 
        tmnxOspfBackBoneRouter,
        tmnxOspfStubRouterSupport,
        tmnxOspfAsScopeLsaCount,
        tmnxOspfAsScopeLsaCksumSum,
        tmnxOspfAsScopeUnkLsaCount,
        tmnxOspfAsScopeUnkLsaCksumSum,
        tmnxOspfExternLsaCount, 
        tmnxOspfExternLsaCksumSum,
        tmnxOspfOpaqueLsaSupport,
        tmnxOspfRestartStatus,  
        tmnxOspfRestartAge, 
        tmnxOspfRestartExitRc,  
        tmnxOspfDiscontinuityTime,
        tmnxOspfLastEnabledTime,
        tmnxOspfLastOvrflwEnteredTime,
        tmnxOspfLastOverflowExitTime,
        tmnxOspfInOverflowState,
        tmnxOspfOverloadOperState,
        tmnxOspfOverloadRemInterval,
        tmnxOspfLastOverloadEntrdTime,
        tmnxOspfLastOverloadExitTime,
        tmnxOspfLastOverloadEnterCode,
        tmnxOspfLastOverloadExitCode,
        tmnxOspfLastExtSpfRunTime,
        tmnxOspfLastFullSpfRunTime,
        tmnxOspfLastFullSpfInterval,
        tmnxOspfMaxSpfRunInterval,
        tmnxOspfMinSpfRunInterval,
        tmnxOspfAvgSpfRunInterval,
        tmnxOspfExtSpfRunInterval,
        tmnxOspfRoutesSubmitted,
        tmnxOspfOriginateNewLsas, 
        tmnxOspfRxNewLsas, 
        tmnxOspfFullSpfRuns,
        tmnxOspfExtSpfRuns,
        tmnxOspfIncremntlInterSpfRuns,
        tmnxOspfIncrementalExtSpfRuns,
        tmnxOspfSpfAttemptsFailed,
        tmnxOspfNumTimesInOverload,
        tmnxOspfNumTimesInOverflow,
        tmnxOspfRoutesAddsFailed,
        tmnxOspfRoutesDelsFailed,
        tmnxOspfRoutesModsFailed,
        tmnxOspfAreaEntries,
        tmnxOspfAreaLsaCountEntries,        
        tmnxOspfAsLsdbEntries,
        tmnxOspfAreaLsdbEntries,
        tmnxOspfLinkLsdbEntries,
        tmnxOspfHostEntries,
        tmnxOspfIfEntries,
        tmnxOspfVirtIfEntries,
        tmnxOspfNbrEntries,
        tmnxOspfCfgNbrEntries,
        tmnxOspfVirtNbrEntries,
        tmnxOspfAreaAggrEntries,
        tmnxOspfIfMD5KeyEntries,
        tmnxOspfVirtIfMD5KeyEntries,
        tmnxOspfCSPFRequests,
        tmnxOspfCSPFDroppedRequests,
        tmnxOspfCSPFPathsFound,
        tmnxOspfCSPFPathsNotFound,
        tmnxOspfAreaTableChanged,
        tmnxOspfHostTableChanged,
        tmnxOspfIfTableChanged,
        tmnxOspfVirtIfTableChanged,
        tmnxOspfNbrTableChanged,
        tmnxOspfCfgNbrTableChanged,
        tmnxOspfVirtNbrTableChanged,
        tmnxOspfAreaAggTableChanged,
        tmnxOspfIfMD5KeyTableChanged,
        tmnxOspfVirtIfMD5KeyTableChanged,
        tmnxOspfIgnoreDNBit,
        tmnxOspfSuppressDNBit
    }
    STATUS    obsolete
    DESCRIPTION
        "The group of objects supporting management of the OSPF
         protocol on Alcatel-Lucent SROS series systems."
    ::= { tmnxOspfGroups 1 }

tmnxOspfAreaGroup OBJECT-GROUP
    OBJECTS {
        tmnxOspfAreaStatus,
        tmnxOspfAreaLastChanged, 
        tmnxOspfImportAsExtern, 
        tmnxOspfAreaSummary, 
        tmnxOspfAreaRangeBlackhole,
        tmnxOspfStubMetric, 
        tmnxOspfAreaStubMetricType, 
        tmnxOspfAreaOriginateDefault,
        tmnxOspfAreaNssaRedistribute,
        tmnxOspfAreaNssaTranslatorRole, 
        tmnxOspfAreaNssaTranslatorStabInt, 
        tmnxOspfAreaBdrRtrCount, 
        tmnxOspfAreaAsBdrRtrCount, 
        tmnxOspfAreaScopeLsaCount, 
        tmnxOspfAreaScopeLsaCksumSum, 
        tmnxOspfAreaScopeUnkLsaCount, 
        tmnxOspfAreaScopeUnkLsaCksumSum, 
        tmnxOspfAreaNssaTranslatorState, 
        tmnxOspfAreaActiveInterfaces,
        tmnxOspfAreaInterfaceCount,
        tmnxOspfAreaVirtualLinkCount,
        tmnxOspfAreaLastSpfRunTime,
        tmnxOspfAreaSpfRuns, 
        tmnxOspfAreaNssaTranslatorEvents, 
        tmnxOspfAreaNeighborCount,
        tmnxOspfAreaLsaCountNumber, 
        tmnxOspfAsLsdbSequence, 
        tmnxOspfAsLsdbAge, 
        tmnxOspfAsLsdbChecksum, 
        tmnxOspfAsLsdbAdvertisement, 
        tmnxOspfAsLsdbTypeKnown, 
        tmnxOspfAreaLsdbSequence, 
        tmnxOspfAreaLsdbAge, 
        tmnxOspfAreaLsdbChecksum, 
        tmnxOspfAreaLsdbAdvertisement, 
        tmnxOspfAreaLsdbTypeKnown, 
        tmnxOspfLinkLsdbSequence, 
        tmnxOspfLinkLsdbAge, 
        tmnxOspfLinkLsdbChecksum, 
        tmnxOspfLinkLsdbAdvertisement, 
        tmnxOspfLinkLsdbTypeKnown 
    }   
    STATUS    obsolete
    DESCRIPTION
        "The group of objects supporting management of the OSPF
         Areas on Alcatel-Lucent SROS series systems."
    ::= { tmnxOspfGroups 2 }

tmnxOspfHostGroup OBJECT-GROUP
    OBJECTS {
        tmnxOspfHostMetric, 
        tmnxOspfHostStatus,
        tmnxOspfHostLastChanged,
        tmnxOspfHostAreaID 
    }   
    STATUS    current
    DESCRIPTION
        "The group of objects supporting management of the OSPF
         Hosts on Alcatel-Lucent SROS series systems."
    ::= { tmnxOspfGroups 3 }

tmnxOspfIfGroup OBJECT-GROUP
    OBJECTS {
        tmnxOspfIfStatus,
        tmnxOspfIfLastChanged, 
        tmnxOspfIfAreaId, 
        tmnxOspfIfCfgType, 
        tmnxOspfIfAdminState, 
        tmnxOspfIfRtrPriority, 
        tmnxOspfIfTransitDelay, 
        tmnxOspfIfRetransInterval, 
        tmnxOspfIfHelloInterval, 
        tmnxOspfIfRtrDeadInterval, 
        tmnxOspfIfPollInterval, 
        tmnxOspfIfMulticastForwarding, 
        tmnxOspfIfCfgMTU,
        tmnxOspfIfCfgMetric,
        tmnxOspfIfPassive,
        tmnxOspfIfAdvtSubnet,
        tmnxOspfIfDemand, 
        tmnxOspfIfDemandNbrProbe, 
        tmnxOspfIfDemandNbrProbeRetxLimit, 
        tmnxOspfIfDemandNbrProbeInterval, 
        tmnxOspfIfAuthType,
        tmnxOspfIfAuthKey,
        tmnxOspfIfState, 
        tmnxOspfIfLastEnabledTime,
        tmnxOspfIfOperMTU,
        tmnxOspfIfMetricValue, 
        tmnxOspfIfDRId, 
        tmnxOspfIfDRIpAddrType,
        tmnxOspfIfDRIpAddr,
        tmnxOspfIfBDRId, 
        tmnxOspfIfBDRIpAddrType,
        tmnxOspfIfBDRIpAddr,
        tmnxOspfIfLinkLsaCount, 
        tmnxOspfIfLinkLsaCksumSum, 
        tmnxOspfIfLinkUnkLsaCount, 
        tmnxOspfIfLinkUnkLsaCksumSum, 
        tmnxOspfIfMD5TransmitKeyId,
        tmnxOspfIfLocalIpAddressType, 
        tmnxOspfIfLocalIpAddress,
        tmnxOspfIfMD5NumKeys,
        tmnxOspfIfType,
        tmnxOspfIfEnableBfd,
        tmnxOspfIfEvents, 
        tmnxOspfIfTxPackets,
        tmnxOspfIfTxHellos,
        tmnxOspfIfTxDBDs,
        tmnxOspfIfTxLSRs,
        tmnxOspfIfTxLSUs,
        tmnxOspfIfTxLSAcks,
        tmnxOspfIfRxPackets,
        tmnxOspfIfRxHellos,
        tmnxOspfIfRxDBDs,
        tmnxOspfIfRxLSRs,
        tmnxOspfIfRxLSUs,
        tmnxOspfIfRxLSAcks,
        tmnxOspfIfDiscardPackets,
        tmnxOspfIfRetransmitOuts,
        tmnxOspfIfBadVersions,
        tmnxOspfIfBadNetworks,
        tmnxOspfIfBadVirtualLinks,
        tmnxOspfIfBadAreas,
        tmnxOspfIfBadDstAddrs,
        tmnxOspfIfBadNeighbors,
        tmnxOspfIfBadPacketTypes,
        tmnxOspfIfNeighborCount,
        tmnxOspfIfLastEventTime,
        tmnxOspfIfBadLengths,
        tmnxOspfIfBadHelloIntervals,
        tmnxOspfIfBadDeadIntervals,
        tmnxOspfIfBadOptions,
        tmnxOspfIfRxBadChecksums,
        tmnxOspfIfBadAuthTypes,
        tmnxOspfIfAuthFailures
    }   
    STATUS    obsolete
    DESCRIPTION
        "The group of objects supporting management of the OSPF
         Interfaces on Alcatel-Lucent SROS series systems."
    ::= { tmnxOspfGroups 4 }

tmnxOspfVirtIfGroup OBJECT-GROUP
    OBJECTS {
        tmnxOspfVirtIfStatus,
        tmnxOspfVirtIfLastChanged, 
        tmnxOspfVirtIfIndex, 
        tmnxOspfVirtIfInstId, 
        tmnxOspfVirtIfAdminStat,
        tmnxOspfVirtIfTransitDelay, 
        tmnxOspfVirtIfRetransInterval, 
        tmnxOspfVirtIfHelloInterval, 
        tmnxOspfVirtIfRtrDeadInterval, 
        tmnxOspfVirtIfAuthType,
        tmnxOspfVirtIfAuthKey,
        tmnxOspfVirtIfState, 
        tmnxOspfVirtIfLastEnabledTime,
        tmnxOspfVirtIfCost,
        tmnxOspfVirtIfLinkLsaCount, 
        tmnxOspfVirtIfLinkLsaCksumSum, 
        tmnxOspfVirtIfLinkUnkLsaCount, 
        tmnxOspfVirtIfLinkUnkLsaCksumSum, 
        tmnxOspfVirtIfMD5TransmitKeyId,
        tmnxOspfVirtIfLocalIpAddrType, 
        tmnxOspfVirtIfLocalIpAddress, 
        tmnxOspfVirtIfMD5NumKeys,
        tmnxOspfVirtIfEvents, 
        tmnxOspfVirtIfTxPackets,
        tmnxOspfVirtIfTxHellos,
        tmnxOspfVirtIfTxDBDs,
        tmnxOspfVirtIfTxLSRs,
        tmnxOspfVirtIfTxLSUs,
        tmnxOspfVirtIfTxLSAcks,
        tmnxOspfVirtIfRxPackets,
        tmnxOspfVirtIfRxHellos,
        tmnxOspfVirtIfRxDBDs,
        tmnxOspfVirtIfRxLSRs,
        tmnxOspfVirtIfRxLSUs,
        tmnxOspfVirtIfRxLSAcks,
        tmnxOspfVirtIfDiscardPackets,
        tmnxOspfVirtIfRetransmitOuts,
        tmnxOspfVirtIfBadVersions,
        tmnxOspfVirtIfBadNetworks,
        tmnxOspfVirtIfBadAreas,
        tmnxOspfVirtIfBadDstAddrs,
        tmnxOspfVirtIfBadNeighbors,
        tmnxOspfVirtIfBadPacketTypes,
        tmnxOspfVirtIfLastEventTime,
        tmnxOspfVirtIfBadLengths,
        tmnxOspfVirtIfBadHelloIntervls,
        tmnxOspfVirtIfBadDeadIntervals,
        tmnxOspfVirtIfBadOptions,
        tmnxOspfVirtIfRxBadChecksums,
        tmnxOspfVirtIfBadAuthTypes,
        tmnxOspfVirtIfAuthFailures
    }   
    STATUS    current
    DESCRIPTION
        "The group of objects supporting management of the OSPF
         Virtual Interfaces on Alcatel-Lucent SROS series systems."
    ::= { tmnxOspfGroups 5 }

tmnxOspfNbrGroup OBJECT-GROUP
    OBJECTS {
        tmnxOspfNbrAddressType, 
        tmnxOspfNbrAddress,             
        tmnxOspfNbrOptions, 
        tmnxOspfNbrPriority, 
        tmnxOspfNbrState, 
        tmnxOspfNbrHelloSuppressed, 
        tmnxOspfNbrIfId, 
        tmnxOspfNbrRestartHelperStatus,  
        tmnxOspfNbrRestartHelperAge,  
        tmnxOspfNbrRestartHelperExitRc, 
        tmnxOspfNbrUpTime,
        tmnxOspfNbrLastEventTime,
        tmnxOspfNbrDeadTimeOutstanding,
        tmnxOspfNbrLastRestartTime,
        tmnxOspfNbrRestartReason,
        tmnxOspfNbrBfdTracking,
        tmnxOspfNbrDrId,
        tmnxOspfNbrBdrId,
        tmnxOspfNbrEvents, 
        tmnxOspfNbrLsRetransQLen, 
        tmnxOspfNbrBadNbrStates,
        tmnxOspfNbrLsaInstallFailed,
        tmnxOspfNbrBadSeqNums,
        tmnxOspfNbrBadMTUs,
        tmnxOspfNbrBadPackets,
        tmnxOspfNbrLsaNotInLsdbs,
        tmnxOspfNbrOptionMismatches,
        tmnxOspfNbrDuplicates,
        tmnxOspfNbrNumRestarts,
        tmnxOspfCfgNbrStatus, 
        tmnxOspfCfgNbrStorageType,
        tmnxOspfCfgNbrLastChanged, 
        tmnxOspfCfgNbrPriority, 
        tmnxOspfCfgNbrRtrId, 
        tmnxOspfCfgNbrState 
    }   
    STATUS    obsolete
    DESCRIPTION
        "The group of objects supporting management of the OSPF
         Neighbors on Alcatel-Lucent SROS series systems."
    ::= { tmnxOspfGroups 6 }

tmnxOspfVirtNbrGroup OBJECT-GROUP
    OBJECTS {
        tmnxOspfVirtNbrIfIndex, 
        tmnxOspfVirtNbrIfInstId, 
        tmnxOspfVirtNbrAddressType, 
        tmnxOspfVirtNbrAddress, 
        tmnxOspfVirtNbrOptions, 
        tmnxOspfVirtNbrState, 
        tmnxOspfVirtNbrHelloSuppressed, 
        tmnxOspfVirtNbrIfId, 
        tmnxOspfVirtNbrRestartHelperStatus,  
        tmnxOspfVirtNbrRestartHelperAge,  
        tmnxOspfVirtNbrRestartHelperExitRc, 
        tmnxOspfVirtNbrUpTime,
        tmnxOspfVirtNbrLastEventTime,
        tmnxOspfVirtNbrDeadTmeOutstng,
        tmnxOspfVirtNbrLastRestartTime,
        tmnxOspfVirtNbrRestartReason,
        tmnxOspfVirtNbrEvents, 
        tmnxOspfVirtNbrLsRetransQLen, 
        tmnxOspfVirtNbrBadNbrStates,
        tmnxOspfVirtNbrLsaInstallFail,
        tmnxOspfVirtNbrBadSeqNums,
        tmnxOspfVirtNbrBadMTUs,
        tmnxOspfVirtNbrBadPackets,
        tmnxOspfVirtNbrLsaNotInLsdbs,
        tmnxOspfVirtNbrOptionMismatch,
        tmnxOspfVirtNbrDuplicates,
        tmnxOspfVirtNbrNumRestarts
    }   
    STATUS    current
    DESCRIPTION
        "The group of objects supporting management of the OSPF
         Virtual Neighbors on Alcatel-Lucent SROS series systems."
    ::= { tmnxOspfGroups 7 }

tmnxOspfAreaAggrGroup OBJECT-GROUP
    OBJECTS {
        tmnxOspfAreaAggrStatus,
        tmnxOspfAreaAggrLastChanged, 
        tmnxOspfAreaAggrEffect, 
        tmnxOspfAreaAggrRouteTag 
    }   
    STATUS    current
    DESCRIPTION
        "The group of objects supporting management of the OSPF
         Area Aggregates on Alcatel-Lucent SROS series systems."
    ::= { tmnxOspfGroups 8 }

tmnxOspfMD5KeyGroup OBJECT-GROUP
    OBJECTS {
        tmnxOspfIfMD5KeyStatus,
        tmnxOspfIfMD5KeyKey,
        tmnxOspfIfMD5KeyStartTime,
        tmnxOspfIfMD5KeyStopTime,
        tmnxOspfVirtIfMD5KeyStatus,
        tmnxOspfVirtIfMD5KeyKey,
        tmnxOspfVirtIfMD5KeyStartTime,
        tmnxOspfVirtIfMD5KeyStopTime
    }   
    STATUS    obsolete
    DESCRIPTION
        "The group of objects supporting management of the OSPF
         MD5 Keys on Alcatel-Lucent SROS series systems."
    ::= { tmnxOspfGroups 9 }

tmnxOspfNotifyObjsGroup OBJECT-GROUP
    OBJECTS {
        tmnxOspfSetTrap,
        tmnxOspfConfigErrorType,
        tmnxOspfPacketType,
        tmnxOspfPacketSrcAddressType,
        tmnxOspfPacketSrcAddress
    }   
    STATUS    current
    DESCRIPTION
        "The group of objects supporting management of the OSPF
         Notification Support Objects on Alcatel-Lucent SROS series systems."
    ::= { tmnxOspfGroups 10 }

tmnxOspfNotificationGroup NOTIFICATION-GROUP
    NOTIFICATIONS {
        tmnxOspfVirtIfStateChange,
        tmnxOspfNbrStateChange,
        tmnxOspfVirtNbrStateChange,
        tmnxOspfIfConfigError,
        tmnxOspfVirtIfConfigError,
        tmnxOspfIfAuthFailure, 
        tmnxOspfVirtIfAuthFailure,
        tmnxOspfIfRxBadPacket,
        tmnxOspfVirtIfRxBadPacket,
        tmnxOspfIfTxRetransmit,
        tmnxOspfVirtIfTxRetransmit,
        tmnxOspfAreaOriginateLsa,
        tmnxOspfAreaMaxAgeLsa,
        tmnxOspfLsdbOverflow,
        tmnxOspfLsdbApproachingOverflow,
        tmnxOspfIfStateChange,
        tmnxOspfNssaTranslatorStatusChg,
        tmnxOspfRestartStatusChange,
        tmnxOspfNbrRestartHlprStsChg,
        tmnxOspfVirtNbrRestartHlprStsChg,
        tmnxOspfSpfRunsStopped,
        tmnxOspfSpfRunsRestarted,
        tmnxOspfOverloadEntered,
        tmnxOspfOverloadExited,
        tmnxOspfAsOriginateLsa,
        tmnxOspfAsMaxAgeLsa,
        tmnxOspfLinkOriginateLsa,
        tmnxOspfLinkMaxAgeLsa
    }
    STATUS    obsolete
    DESCRIPTION
        "The group of notifications supporting management of the 
         OSPF Notifications on Alcatel-Lucent SROS series systems."
    ::= { tmnxOspfGroups 11 }

tmnxOspfGeneralV5v0Group OBJECT-GROUP
    OBJECTS {
        tmnxOspfGeneralEntries,   
        tmnxOspfGeneralLastChanged,
        tmnxOspfRouterId,
        tmnxOspfAdminState, 
        tmnxOspfASBdrRtrStatus, 
        tmnxOspfRFC1583Compatibility,
        tmnxOspfExtLsdbLimit,
        tmnxOspfMulticastExtensions, 
        tmnxOspfExitOverflowInterval, 
        tmnxOspfDemandExtensions, 
        tmnxOspfReferenceBandwidth,  
        tmnxOspfStrictLsaChecking, 
        tmnxOspfRestartSupport, 
        tmnxOspfRestartInterval, 
        tmnxOspfPreference,
        tmnxOspfExternalPreference,
        tmnxOspfExportPolicy1,
        tmnxOspfExportPolicy2,
        tmnxOspfExportPolicy3,
        tmnxOspfExportPolicy4,
        tmnxOspfExportPolicy5,
        tmnxOspfManualSpfTrigger,
        tmnxOspfOverloadAdmState,
        tmnxOspfOverloadInterval,
        tmnxOspfBootOverloadAdmState,
        tmnxOspfBootOverloadInterval,
        tmnxOspfOverloadStubs,
        tmnxOspfSpfMaxWait,
        tmnxOspfSpfInitialWait,
        tmnxOspfSpfSecondWait,
        tmnxOspfLsaGenMaxWait,
        tmnxOspfLsaGenInitialWait,
        tmnxOspfLsaGenSecondWait,
        tmnxOspfLsaArrivalWait,
        tmnxOspfTESupport,
        tmnxOspfUnicastImport,
        tmnxOspfMulticastImport,
        tmnxOspfGREnable,
        tmnxOspfGRHelperMode,
        tmnxOspfAreaBdrRtrStatus, 
        tmnxOspfBackBoneRouter,
        tmnxOspfStubRouterSupport,
        tmnxOspfAsScopeLsaCount,
        tmnxOspfAsScopeLsaCksumSum,
        tmnxOspfAsScopeUnkLsaCount,
        tmnxOspfAsScopeUnkLsaCksumSum,
        tmnxOspfExternLsaCount, 
        tmnxOspfExternLsaCksumSum,
        tmnxOspfOpaqueLsaSupport,
        tmnxOspfRestartStatus,  
        tmnxOspfRestartAge, 
        tmnxOspfRestartExitRc,  
        tmnxOspfDiscontinuityTime,
        tmnxOspfLastEnabledTime,
        tmnxOspfLastOvrflwEnteredTime,
        tmnxOspfLastOverflowExitTime,
        tmnxOspfInOverflowState,
        tmnxOspfOverloadOperState,
        tmnxOspfOverloadRemInterval,
        tmnxOspfLastOverloadEntrdTime,
        tmnxOspfLastOverloadExitTime,
        tmnxOspfLastOverloadEnterCode,
        tmnxOspfLastOverloadExitCode,
        tmnxOspfLastExtSpfRunTime,
        tmnxOspfLastFullSpfRunTime,
        tmnxOspfLastFullSpfInterval,
        tmnxOspfMaxSpfRunInterval,
        tmnxOspfMinSpfRunInterval,
        tmnxOspfAvgSpfRunInterval,
        tmnxOspfExtSpfRunInterval,
        tmnxOspfRoutesSubmitted,
        tmnxOspfOriginateNewLsas, 
        tmnxOspfRxNewLsas, 
        tmnxOspfFullSpfRuns,
        tmnxOspfExtSpfRuns,
        tmnxOspfIncremntlInterSpfRuns,
        tmnxOspfIncrementalExtSpfRuns,
        tmnxOspfSpfAttemptsFailed,
        tmnxOspfNumTimesInOverload,
        tmnxOspfNumTimesInOverflow,
        tmnxOspfRoutesAddsFailed,
        tmnxOspfRoutesDelsFailed,
        tmnxOspfRoutesModsFailed,
        tmnxOspfAreaEntries,
        tmnxOspfAreaLsaCountEntries,        
        tmnxOspfAsLsdbEntries,
        tmnxOspfAreaLsdbEntries,
        tmnxOspfLinkLsdbEntries,
        tmnxOspfHostEntries,
        tmnxOspfIfEntries,
        tmnxOspfVirtIfEntries,
        tmnxOspfNbrEntries,
        tmnxOspfCfgNbrEntries,
        tmnxOspfVirtNbrEntries,
        tmnxOspfAreaAggrEntries,
        tmnxOspfIfMD5KeyEntries,
        tmnxOspfVirtIfMD5KeyEntries,
        tmnxOspfCSPFRequests,
        tmnxOspfCSPFDroppedRequests,
        tmnxOspfCSPFPathsFound,
        tmnxOspfCSPFPathsNotFound,
        tmnxOspfAreaTableChanged,
        tmnxOspfHostTableChanged,
        tmnxOspfIfTableChanged,
        tmnxOspfVirtIfTableChanged,
        tmnxOspfNbrTableChanged,
        tmnxOspfCfgNbrTableChanged,
        tmnxOspfVirtNbrTableChanged,
        tmnxOspfAreaAggTableChanged,
        tmnxOspfIfMD5KeyTableChanged,
        tmnxOspfVirtIfMD5KeyTableChanged,
        tmnxOspfRowStatus,
        tmnxOspfOperRouterId,
        tmnxOspfAsbrDomainId,
        tmnxOspfIgnoreDNBit,
        tmnxOspfSuppressDNBit
    }
    STATUS    current
    DESCRIPTION
        "The group of objects supporting management of the OSPF
         protocol on Alcatel-Lucent SROS series systems."
    ::= { tmnxOspfGroups 12 }

tmnxOspfIfV5v0Group OBJECT-GROUP
    OBJECTS {
        tmnxOspfIfStatus,
        tmnxOspfIfLastChanged, 
        tmnxOspfIfAreaId, 
        tmnxOspfIfCfgType, 
        tmnxOspfIfAdminState, 
        tmnxOspfIfRtrPriority, 
        tmnxOspfIfTransitDelay, 
        tmnxOspfIfRetransInterval, 
        tmnxOspfIfHelloInterval, 
        tmnxOspfIfRtrDeadInterval, 
        tmnxOspfIfPollInterval, 
        tmnxOspfIfMulticastForwarding, 
        tmnxOspfIfCfgMTU,
        tmnxOspfIfCfgMetric,
        tmnxOspfIfPassive,
        tmnxOspfIfAdvtSubnet,
        tmnxOspfIfDemand, 
        tmnxOspfIfDemandNbrProbe, 
        tmnxOspfIfDemandNbrProbeRetxLimit, 
        tmnxOspfIfDemandNbrProbeInterval, 
        tmnxOspfIfAuthType,
        tmnxOspfIfAuthKey,
        tmnxOspfIfState, 
        tmnxOspfIfLastEnabledTime,
        tmnxOspfIfOperMTU,
        tmnxOspfIfMetricValue, 
        tmnxOspfIfDRId, 
        tmnxOspfIfDRIpAddrType,
        tmnxOspfIfDRIpAddr,
        tmnxOspfIfBDRId, 
        tmnxOspfIfBDRIpAddrType,
        tmnxOspfIfBDRIpAddr,
        tmnxOspfIfLinkLsaCount, 
        tmnxOspfIfLinkLsaCksumSum, 
        tmnxOspfIfLinkUnkLsaCount, 
        tmnxOspfIfLinkUnkLsaCksumSum, 
        tmnxOspfIfMD5TransmitKeyId,
        tmnxOspfIfLocalIpAddressType, 
        tmnxOspfIfLocalIpAddress,
        tmnxOspfIfMD5NumKeys,
        tmnxOspfIfType,
        tmnxOspfIfEnableBfd,
        tmnxOspfIfRemainDownOnFail,     
        tmnxOspfIfEvents, 
        tmnxOspfIfTxPackets,
        tmnxOspfIfTxHellos,
        tmnxOspfIfTxDBDs,
        tmnxOspfIfTxLSRs,
        tmnxOspfIfTxLSUs,
        tmnxOspfIfTxLSAcks,
        tmnxOspfIfRxPackets,
        tmnxOspfIfRxHellos,
        tmnxOspfIfRxDBDs,
        tmnxOspfIfRxLSRs,
        tmnxOspfIfRxLSUs,
        tmnxOspfIfRxLSAcks,
        tmnxOspfIfDiscardPackets,
        tmnxOspfIfRetransmitOuts,
        tmnxOspfIfBadVersions,
        tmnxOspfIfBadNetworks,
        tmnxOspfIfBadVirtualLinks,
        tmnxOspfIfBadAreas,
        tmnxOspfIfBadDstAddrs,
        tmnxOspfIfBadNeighbors,
        tmnxOspfIfBadPacketTypes,
        tmnxOspfIfNeighborCount,
        tmnxOspfIfLastEventTime,
        tmnxOspfIfBadLengths,
        tmnxOspfIfBadHelloIntervals,
        tmnxOspfIfBadDeadIntervals,
        tmnxOspfIfBadOptions,
        tmnxOspfIfRxBadChecksums,
        tmnxOspfIfBadAuthTypes,
        tmnxOspfIfAuthFailures
    }   
    STATUS    obsolete
    DESCRIPTION
        "The group of objects supporting management of the OSPF
         Interfaces on Alcatel-Lucent SROS series systems."
    ::= { tmnxOspfGroups 13 }
 
tmnxOspfIfV6v0Group OBJECT-GROUP
     OBJECTS 
     {
        tmnxOspfIfTeMetric,
        tmnxOspfIfTeState,
        tmnxOspfIfAdminGroup,
        tmnxOspfIfLdpSyncState,
        tmnxOspfIfLdpSyncMaxMetric,
        tmnxOspfIfLdpSyncTimerState,
        tmnxOspfIfLdpSyncTimeLeft
     }
     STATUS    obsolete
     DESCRIPTION
         "The group of objects supporting management of the OSPF Interfaces on 
          6.0 release of Alcatel-Lucent SROS series systems."
     ::= { tmnxOspfGroups 14 }

tmnxOspfGeneralV6v0Group OBJECT-GROUP
         OBJECTS 
         {
            tmnxOspfLdpSyncAdminState
         }
         STATUS    current
         DESCRIPTION
             "The group of objects supporting management of the OSPF protocol 
              6.0 release of Alcatel-Lucent SROS series systems."
         ::= { tmnxOspfGroups 15 }

tmnxOspfNotificationV6v0Group NOTIFICATION-GROUP
    NOTIFICATIONS
     {
        tmnxOspfLdpSyncTimerStarted,
        tmnxOspfLdpSyncExit
     }
     STATUS    obsolete
     DESCRIPTION
         "The group of notifications supporting management of the 
          OSPF Notifications on 6.0 release of Alcatel-Lucent SROS series systems."
     ::= { tmnxOspfGroups 16 }

tmnxOspfNotifyObjsV6v0Group OBJECT-GROUP
    OBJECTS
    {   tmnxOspfIfIpName,
        tmnxOspfIfEvent
    }
    STATUS  current
    DESCRIPTION
        "The group of objects added in the 6.0 release to support
         OSPF notifications."
    ::= { tmnxOspfGroups 17 }

tmnxOspfGeneralV6v1Group OBJECT-GROUP
    OBJECTS
    {
        tmnxOspfVpnDomainType,
        tmnxOspfVpnDomainId,
        tmnxOspfVpnTag,
        tmnxOspfSuperBackBone
    }
    STATUS    current
    DESCRIPTION
        "The group of objects supporting management of the OSPF protocol
         6.1 release of Alcatel-Lucent SROS series systems."
    ::= { tmnxOspfGroups 18 }

tmnxOspfShamLinksV7v0Group OBJECT-GROUP
    OBJECTS
    {
        tmnxOspfShamIfStatus,
        tmnxOspfShamIfLastChanged,
        tmnxOspfShamIfAreaId,
        tmnxOspfShamIfAdminState,
        tmnxOspfShamIfTransitDelay,
        tmnxOspfShamIfRetransInterval,
        tmnxOspfShamIfHelloInterval,
        tmnxOspfShamIfRtrDeadInterval,
        tmnxOspfShamIfCfgMetric,
        tmnxOspfShamIfAuthType,
        tmnxOspfShamIfAuthKey,
        tmnxOspfShamIfState,
        tmnxOspfShamIfLastEnabledTime,
        tmnxOspfShamIfLinkLsaCount,
        tmnxOspfShamIfLinkLsaCksumSum,
        tmnxOspfShamIfLinkUnkLsaCount,
        tmnxOspfShamIfLinkUnkLsaCksumSum,
        tmnxOspfShamIfMD5TransmitKeyId,
        tmnxOspfShamIfLocalIpAddressType,
        tmnxOspfShamIfLocalIpAddress,
        tmnxOspfShamIfMD5NumKeys,
        tmnxOspfShamIfEvents,
        tmnxOspfShamIfTxPackets,
        tmnxOspfShamIfTxHellos,
        tmnxOspfShamIfTxDBDs,
        tmnxOspfShamIfTxLSRs,
        tmnxOspfShamIfTxLSUs,
        tmnxOspfShamIfTxLSAcks,
        tmnxOspfShamIfRxPackets,
        tmnxOspfShamIfRxHellos,
        tmnxOspfShamIfRxDBDs,
        tmnxOspfShamIfRxLSRs,
        tmnxOspfShamIfRxLSUs,
        tmnxOspfShamIfRxLSAcks,
        tmnxOspfShamIfDiscardPackets,
        tmnxOspfShamIfRetransmitOuts,
        tmnxOspfShamIfBadVersions,
        tmnxOspfShamIfBadNetworks,
        tmnxOspfShamIfBadAreas,
        tmnxOspfShamIfBadDstAddrs,
        tmnxOspfShamIfBadNeighbors,
        tmnxOspfShamIfBadPacketTypes,
        tmnxOspfShamIfLastEventTime,
        tmnxOspfShamIfBadLengths,
        tmnxOspfShamIfBadHelloIntervals,
        tmnxOspfShamIfBadDeadIntervals,
        tmnxOspfShamIfBadOptions,
        tmnxOspfShamIfRxBadChecksums,
        tmnxOspfShamIfBadAuthTypes,
        tmnxOspfShamIfAuthFailures,
        tmnxOspfShamIfMD5KeyStatus,
        tmnxOspfShamIfMD5KeyKey,
        tmnxOspfShamIfMD5KeyStartTime,
        tmnxOspfShamIfMD5KeyStopTime,
        tmnxOspfShamNbrOptions,
        tmnxOspfShamNbrState,
        tmnxOspfShamNbrHelloSuppressed,
        tmnxOspfShamNbrIfId,
        tmnxOspfShamNbrRestartHelperStatus,
        tmnxOspfShamNbrRestartHelperAge,
        tmnxOspfShamNbrRestartHelperExitRc,
        tmnxOspfShamNbrUpTime,
        tmnxOspfShamNbrLastEventTime,
        tmnxOspfShamNbrDeadTmeOutstng,
        tmnxOspfShamNbrLastRestartTime,
        tmnxOspfShamNbrRestartReason,
        tmnxOspfShamNbrEvents,
        tmnxOspfShamNbrLsRetransQLen,
        tmnxOspfShamNbrBadNbrStates,
        tmnxOspfShamNbrLsaInstallFail,
        tmnxOspfShamNbrBadSeqNums,
        tmnxOspfShamNbrBadMTUs,
        tmnxOspfShamNbrBadPackets,
        tmnxOspfShamNbrLsaNotInLsdbs,
        tmnxOspfShamNbrOptionMismatch,
        tmnxOspfShamNbrDuplicates,
        tmnxOspfShamNbrNumRestarts,
        tmnxOspfShamIfEntries,
        tmnxOspfShamNbrEntries,
        tmnxOspfShamIfMD5KeyEntries,
        tmnxOspfShamIfTableChanged,
        tmnxOspfShamNbrTableChanged,
        tmnxOspfShamIfMD5KeyTableChanged,
        tmnxOspfAreaShamLinkCount
    }
    STATUS    current
    DESCRIPTION
        "The group of objects supporting management of the OSPF Sham Links 
         feature on 7.0 release of Alcatel-Lucent SROS series systems."
    ::= { tmnxOspfGroups 19 }

tmnxOspfNotificationV7v0Group NOTIFICATION-GROUP
    NOTIFICATIONS { 
        tmnxOspfShamIfStateChange,
        tmnxOspfShamNbrStateChange,
        tmnxOspfShamIfConfigError,
        tmnxOspfShamIfAuthFailure,
        tmnxOspfShamIfRxBadPacket,
        tmnxOspfShamIfTxRetransmit,
        tmnxOspfShamNbrRestartHlprStsChg,
        tmnxOspfFailureDisabled
    }
    STATUS    current
    DESCRIPTION
        "The group of notifications supporting management of the OSPF sham
         links Notifications on 7.0 release of Alcatel-Lucent SROS series systems."
    ::= { tmnxOspfGroups 20 }

tmnxOspfNotifyObjsV7v0Group OBJECT-GROUP
    OBJECTS
    {   tmnxOspfFailureReasonCode
    }
    STATUS  current
    DESCRIPTION
        "The group of objects added in the 7.0 release to support
         OSPF notifications."
    ::= { tmnxOspfGroups 21 }

tmnxOspfGeneralV7v0Group OBJECT-GROUP
    OBJECTS
    {
        tmnxOspfLdpOverRsvp,
        tmnxOspfExportLimit,
        tmnxOspfExportLimitLogPercent,
        tmnxOspfTotalExportedRoutes
    }
    STATUS    current
    DESCRIPTION
        "The group of objects supporting management of the OSPF protocol added
         in the 7.0 release of Alcatel-Lucent SROS series systems."
    ::= { tmnxOspfGroups 22 }

tmnxOspfGenNotificationV7v0Grp  NOTIFICATION-GROUP
    NOTIFICATIONS { 
        tmnxOspfExportLimitReached,
        tmnxOspfExportLimitWarning,
        tmnxOspfRoutesExpLmtDropped
    }
    STATUS    current
    DESCRIPTION
         "The group of notifications supporting management of the 
          OSPF on 7.0 release of Alcatel-Lucent SROS series systems."
    ::= { tmnxOspfGroups 23 }

tmnxOspfAreaV8v0Group OBJECT-GROUP
    OBJECTS {
        tmnxOspfAreaKeyRolloverInterval 
    }   
    STATUS    obsolete
    DESCRIPTION
        "The group of objects supporting management of the OSPF
         Areas on 8.0 release of Alcatel-Lucent SROS series systems."
    ::= { tmnxOspfGroups 24 }

tmnxOspfVirtIfV8v0Group OBJECT-GROUP
    OBJECTS {
        tmnxOspfVirtIfInboundSAName,
        tmnxOspfVirtIfOutboundSAName,
        tmnxOspfVirtIfOperInbSAName,
        tmnxOspfVirtIfOperInbSANameTemp,
        tmnxOspfVirtIfOperOutbSAName
    }   
    STATUS    current
    DESCRIPTION
        "The group of objects supporting management of the OSPF
         Virtual Interfaces on release 8.0 Alcatel-Lucent SROS series systems."
    ::= { tmnxOspfGroups 25 }

tmnxOspfIfV8v0Group OBJECT-GROUP
     OBJECTS 
     {
        tmnxOspfIfInboundSAName,
        tmnxOspfIfOutboundSAName,
        tmnxOspfIfOperInbSAName,
        tmnxOspfIfOperInbSANameTemp,
        tmnxOspfIfOperOutbSAName
     }
     STATUS    current
     DESCRIPTION
         "The group of objects supporting management of the OSPF Interfaces on 
          release 8.0 of Alcatel-Lucent SROS series systems."
     ::= { tmnxOspfGroups 26 }

tmnxOspfNotifyObjsV8v0Group OBJECT-GROUP
    OBJECTS
    {   tmnxOspfBadPacketErrType
    }
    STATUS  current
    DESCRIPTION
        "The group of objects added in the 8.0 release to support
         OSPF notifications."
    ::= { tmnxOspfGroups 27 }

tmnxOspfGeneralV8v0Group OBJECT-GROUP
    OBJECTS
    {
        tmnxOspfRsvpShortcut,
        tmnxOspfAdvertiseTunnelLink
    }
    STATUS    current
    DESCRIPTION
        "The group of objects supporting management of the OSPF protocol added
         in the 8.0 release of Alcatel-Lucent SROS series systems."
    ::= { tmnxOspfGroups 28 }

tmnxOspfAreaV9v0Group OBJECT-GROUP
    OBJECTS {
        tmnxOspfAreaStatus,
        tmnxOspfAreaLastChanged,
        tmnxOspfImportAsExtern,
        tmnxOspfAreaSummary,
        tmnxOspfAreaRangeBlackhole,
        tmnxOspfStubMetric,
        tmnxOspfAreaStubMetricType,
        tmnxOspfAreaOriginateDefault,
        tmnxOspfAreaNssaRedistribute,
        tmnxOspfAreaNssaTranslatorRole,
        tmnxOspfAreaNssaTranslatorStabInt,
        tmnxOspfAreaBdrRtrCount,
        tmnxOspfAreaAsBdrRtrCount,
        tmnxOspfAreaScopeLsaCount,
        tmnxOspfAreaScopeLsaCksumSum,
        tmnxOspfAreaScopeUnkLsaCount,
        tmnxOspfAreaScopeUnkLsaCksumSum,
        tmnxOspfAreaNssaTranslatorState,
        tmnxOspfAreaActiveInterfaces,
        tmnxOspfAreaInterfaceCount,
        tmnxOspfAreaVirtualLinkCount,
        tmnxOspfAreaLastSpfRunTime,
        tmnxOspfAreaSpfRuns,
        tmnxOspfAreaNssaTranslatorEvents,
        tmnxOspfAreaNeighborCount,
        tmnxOspfAreaLsaCountNumber,
        tmnxOspfAsLsdbSequence,
        tmnxOspfAsLsdbAge,
        tmnxOspfAsLsdbChecksum,
        tmnxOspfAsLsdbAdvertisement,
        tmnxOspfAsLsdbTypeKnown,
        tmnxOspfAreaLsdbSequence,
        tmnxOspfAreaLsdbAge,
        tmnxOspfAreaLsdbChecksum,
        tmnxOspfAreaLsdbAdvertisement,
        tmnxOspfAreaLsdbTypeKnown,
        tmnxOspfAreaKeyRolloverInterval
    }
    STATUS    current
    DESCRIPTION
        "The group of objects supporting management of the OSPF
         Areas on Alcatel-Lucent SROS series systems."
    ::= { tmnxOspfGroups 29 }

tmnxOspfNgLinkLsdbV9v0Group OBJECT-GROUP
    OBJECTS {
        tmnxOspfNgLinkLsdbSequence,
        tmnxOspfNgLinkLsdbAge,
        tmnxOspfNgLinkLsdbChecksum,
        tmnxOspfNgLinkLsdbAdvertisement,
        tmnxOspfNgLinkLsdbTypeKnown
    }
    STATUS    current
    DESCRIPTION
        "The group of objects supporting Link-Scope Link State Advertisement
         database on Alcatel-Lucent SROS series systems from release 9.0."
    ::= { tmnxOspfGroups 30 }

tmnxOspfNgNbrV9v0Group OBJECT-GROUP
    OBJECTS {
        tmnxOspfNgNbrAddressType, 
        tmnxOspfNgNbrAddress,             
        tmnxOspfNgNbrOptions, 
        tmnxOspfNgNbrPriority, 
        tmnxOspfNgNbrState, 
        tmnxOspfNgNbrHelloSuppressed, 
        tmnxOspfNgNbrIfId, 
        tmnxOspfNgNbrRestartHelperStatus,  
        tmnxOspfNgNbrRestartHelperAge,  
        tmnxOspfNgNbrRestartHelperExitRc, 
        tmnxOspfNgNbrUpTime,
        tmnxOspfNgNbrLastEventTime,
        tmnxOspfNgNbrDeadTimeOutstanding,
        tmnxOspfNgNbrLastRestartTime,
        tmnxOspfNgNbrRestartReason,
        tmnxOspfNgNbrBfdTracking,
        tmnxOspfNgNbrDrId,
        tmnxOspfNgNbrBdrId,
        tmnxOspfNgNbrEvents,
        tmnxOspfNgNbrLsRetransQLen,
        tmnxOspfNgNbrBadNbrStates,
        tmnxOspfNgNbrLsaInstallFailed,
        tmnxOspfNgNbrBadSeqNums,
        tmnxOspfNgNbrBadMTUs,
        tmnxOspfNgNbrBadPackets,
        tmnxOspfNgNbrLsaNotInLsdbs,
        tmnxOspfNgNbrOptionMismatches,
        tmnxOspfNgNbrDuplicates,
        tmnxOspfNgNbrNumRestarts,
        tmnxOspfCfgNbrLastChanged,
        tmnxOspfCfgNbrPriority,
        tmnxOspfCfgNbrRtrId,
        tmnxOspfCfgNbrState,
        tmnxOspfCfgNbrStatus,
        tmnxOspfCfgNbrStorageType
    }   
    STATUS    current
    DESCRIPTION
        "The group of objects supporting management of the OSPF
         Neighbors on Alcatel-Lucent SROS series systems from release 9.0."
    ::= { tmnxOspfGroups 31 }

tmnxOspfNgIfV9v0Group OBJECT-GROUP
    OBJECTS {
        tmnxOspfNgIfStatus,
        tmnxOspfNgIfLastChanged,
        tmnxOspfNgIfCfgType,
        tmnxOspfNgIfAdminState,
        tmnxOspfNgIfRtrPriority,
        tmnxOspfNgIfTransitDelay,
        tmnxOspfNgIfRetransInterval,
        tmnxOspfNgIfHelloInterval,
        tmnxOspfNgIfRtrDeadInterval,
        tmnxOspfNgIfPollInterval,
        tmnxOspfNgIfCfgMTU,
        tmnxOspfNgIfCfgMetric,
        tmnxOspfNgIfPassive,
        tmnxOspfNgIfAdvtSubnet,
        tmnxOspfNgIfAuthType,
        tmnxOspfNgIfAuthKey,
        tmnxOspfNgIfEnableBfd,
        tmnxOspfNgIfRemainDownOnFail,
        tmnxOspfNgIfInboundSAName,
        tmnxOspfNgIfOutboundSAName
    }   
    STATUS    current
    DESCRIPTION
        "The group of objects supporting management of the OSPF
         Interfaces on Alcatel-Lucent SROS series systems from release 9.0."
    ::= { tmnxOspfGroups 32 }

tmnxOspfNgIfOperV9v0Group OBJECT-GROUP
    OBJECTS {
        tmnxOspfNgIfState,
        tmnxOspfNgIfLastEnabledTime,
        tmnxOspfNgIfOperMTU,
        tmnxOspfNgIfMetricValue,
        tmnxOspfNgIfDRId,
        tmnxOspfNgIfDRIpAddrType,
        tmnxOspfNgIfDRIpAddr,
        tmnxOspfNgIfBDRId,
        tmnxOspfNgIfBDRIpAddrType,
        tmnxOspfNgIfBDRIpAddr,
        tmnxOspfNgIfLinkLsaCount,
        tmnxOspfNgIfLinkLsaCksumSum,
        tmnxOspfNgIfMD5TransmitKeyId,
        tmnxOspfNgIfLocalIpAddressType,
        tmnxOspfNgIfLocalIpAddress,
        tmnxOspfNgIfMD5NumKeys,
        tmnxOspfNgIfType,
        tmnxOspfNgIfTeMetric,
        tmnxOspfNgIfTeState,
        tmnxOspfNgIfAdminGroup,
        tmnxOspfNgIfLdpSyncState,
        tmnxOspfNgIfLdpSyncMaxMetric,
        tmnxOspfNgIfLdpSyncTimerState,
        tmnxOspfNgIfLdpSyncTimeLeft,
        tmnxOspfNgIfOperInbSAName,
        tmnxOspfNgIfOperInbSANameTemp,
        tmnxOspfNgIfOperOutbSAName
    }   
    STATUS    current
    DESCRIPTION
        "The group of objects supporting management of the OSPF
         Interfaces on Alcatel-Lucent SROS series systems from release 9.0."
    ::= { tmnxOspfGroups 33 }

tmnxOspfNgIfStatsV9v0Group OBJECT-GROUP
    OBJECTS {
        tmnxOspfNgIfEvents,
        tmnxOspfNgIfTxPackets,
        tmnxOspfNgIfTxHellos,
        tmnxOspfNgIfTxDBDs,
        tmnxOspfNgIfTxLSRs,
        tmnxOspfNgIfTxLSUs,
        tmnxOspfNgIfTxLSAcks,
        tmnxOspfNgIfRxPackets,
        tmnxOspfNgIfRxHellos,
        tmnxOspfNgIfRxDBDs,
        tmnxOspfNgIfRxLSRs,
        tmnxOspfNgIfRxLSUs,
        tmnxOspfNgIfRxLSAcks,
        tmnxOspfNgIfDiscardPackets,
        tmnxOspfNgIfRetransmitOuts,
        tmnxOspfNgIfBadVersions,
        tmnxOspfNgIfBadNetworks,
        tmnxOspfNgIfBadVirtualLinks,
        tmnxOspfNgIfBadAreas,
        tmnxOspfNgIfBadDstAddrs,
        tmnxOspfNgIfBadNeighbors,
        tmnxOspfNgIfBadPacketTypes,
        tmnxOspfNgIfNeighborCount,
        tmnxOspfNgIfLastEventTime,
        tmnxOspfNgIfBadLengths,
        tmnxOspfNgIfBadHelloIntervals,
        tmnxOspfNgIfBadDeadIntervals,
        tmnxOspfNgIfBadOptions,
        tmnxOspfNgIfRxBadChecksums,
        tmnxOspfNgIfBadAuthTypes,
        tmnxOspfNgIfAuthFailures
    }   
    STATUS    current
    DESCRIPTION
        "The group of objects supporting management of the OSPF
         Interfaces on Alcatel-Lucent SROS series systems from release 9.0."
    ::= { tmnxOspfGroups 34 }

tmnxOspfMD5KeyV9v0Group OBJECT-GROUP
    OBJECTS {
        tmnxOspfNgIfMD5KeyStatus,
        tmnxOspfNgIfMD5KeyKey,
        tmnxOspfNgIfMD5KeyStartTime,
        tmnxOspfNgIfMD5KeyStopTime,
        tmnxOspfVirtIfMD5KeyStatus,
        tmnxOspfVirtIfMD5KeyKey,
        tmnxOspfVirtIfMD5KeyStartTime,
        tmnxOspfVirtIfMD5KeyStopTime
    }   
    STATUS    current
    DESCRIPTION
        "The group of objects supporting management of the OSPF
         MD5 Keys on Alcatel-Lucent SROS series systems."
    ::= { tmnxOspfGroups 35 }

tmnxOspfNotificationV9v0Group NOTIFICATION-GROUP
    NOTIFICATIONS {
        tmnxOspfVirtIfStateChange,
        tmnxOspfNgNbrStateChange,
        tmnxOspfVirtNbrStateChange,
        tmnxOspfNgIfConfigError,
        tmnxOspfVirtIfConfigError,
        tmnxOspfNgIfAuthFailure, 
        tmnxOspfVirtIfAuthFailure,
        tmnxOspfNgIfRxBadPacket,
        tmnxOspfVirtIfRxBadPacket,
        tmnxOspfNgIfTxRetransmit,
        tmnxOspfVirtIfTxRetransmit,
        tmnxOspfAreaOriginateLsa,
        tmnxOspfAreaMaxAgeLsa,
        tmnxOspfLsdbOverflow,
        tmnxOspfLsdbApproachingOverflow,
        tmnxOspfNgIfStateChange,
        tmnxOspfNssaTranslatorStatusChg,
        tmnxOspfRestartStatusChange,
        tmnxOspfNgNbrRestartHlprStsChg,
        tmnxOspfVirtNbrRestartHlprStsChg,
        tmnxOspfSpfRunsStopped,
        tmnxOspfSpfRunsRestarted,
        tmnxOspfOverloadEntered,
        tmnxOspfOverloadExited,
        tmnxOspfAsOriginateLsa,
        tmnxOspfAsMaxAgeLsa,
        tmnxOspfNgLinkOriginateLsa,
        tmnxOspfNgLinkMaxAgeLsa,
        tmnxOspfNgLdpSyncTimerStarted,
        tmnxOspfNgLdpSyncExit
    }
    STATUS    current
    DESCRIPTION
        "The group of notifications supporting management of the 
         OSPF Notifications on Alcatel-Lucent SROS series systems."
    ::= { tmnxOspfGroups 36 }

tmnxOspfObsoletedObjV9v0Group OBJECT-GROUP
    OBJECTS {
        tmnxOspfIfAdminGroup,
        tmnxOspfIfAdminState,
        tmnxOspfIfAdvtSubnet,
        tmnxOspfIfAreaId,
        tmnxOspfIfAuthFailures,
        tmnxOspfIfAuthKey,
        tmnxOspfIfAuthType,
        tmnxOspfIfBDRId,
        tmnxOspfIfBDRIpAddr,
        tmnxOspfIfBDRIpAddrType,
        tmnxOspfIfBadAreas,
        tmnxOspfIfBadAuthTypes,
        tmnxOspfIfBadDeadIntervals,
        tmnxOspfIfBadDstAddrs,
        tmnxOspfIfBadHelloIntervals,
        tmnxOspfIfBadLengths,
        tmnxOspfIfBadNeighbors,
        tmnxOspfIfBadNetworks,
        tmnxOspfIfBadOptions,
        tmnxOspfIfBadPacketTypes,
        tmnxOspfIfBadVersions,
        tmnxOspfIfBadVirtualLinks,
        tmnxOspfIfCfgMTU,
        tmnxOspfIfCfgMetric,
        tmnxOspfIfCfgType,
        tmnxOspfIfDRId,
        tmnxOspfIfDRIpAddr,
        tmnxOspfIfDRIpAddrType,
        tmnxOspfIfDemand,
        tmnxOspfIfDemandNbrProbe,
        tmnxOspfIfDemandNbrProbeInterval,
        tmnxOspfIfDemandNbrProbeRetxLimit,
        tmnxOspfIfDiscardPackets,
        tmnxOspfIfEnableBfd,
        tmnxOspfIfEvents,
        tmnxOspfIfHelloInterval,
        tmnxOspfIfInboundSAName,
        tmnxOspfIfLastChanged,
        tmnxOspfIfLastEnabledTime,
        tmnxOspfIfLastEventTime,
        tmnxOspfIfLdpSyncMaxMetric,
        tmnxOspfIfLdpSyncState,
        tmnxOspfIfLdpSyncTimeLeft,
        tmnxOspfIfLdpSyncTimerState,
        tmnxOspfIfLinkLsaCksumSum,
        tmnxOspfIfLinkLsaCount,
        tmnxOspfIfLinkUnkLsaCksumSum,
        tmnxOspfIfLinkUnkLsaCount,
        tmnxOspfIfLocalIpAddress,
        tmnxOspfIfLocalIpAddressType,
        tmnxOspfIfMD5KeyKey,
        tmnxOspfIfMD5KeyStartTime,
        tmnxOspfIfMD5KeyStatus,
        tmnxOspfIfMD5KeyStopTime,
        tmnxOspfIfMD5NumKeys,
        tmnxOspfIfMD5TransmitKeyId,
        tmnxOspfIfMetricValue,
        tmnxOspfIfMulticastForwarding,
        tmnxOspfIfNeighborCount,
        tmnxOspfIfOperInbSAName,
        tmnxOspfIfOperInbSANameTemp,
        tmnxOspfIfOperMTU,
        tmnxOspfIfOperOutbSAName,
        tmnxOspfIfOutboundSAName,
        tmnxOspfIfPassive,
        tmnxOspfIfPollInterval,
        tmnxOspfIfRemainDownOnFail,
        tmnxOspfIfRetransInterval,
        tmnxOspfIfRetransmitOuts,
        tmnxOspfIfRtrDeadInterval,
        tmnxOspfIfRtrPriority,
        tmnxOspfIfRxBadChecksums,
        tmnxOspfIfRxDBDs,
        tmnxOspfIfRxHellos,
        tmnxOspfIfRxLSAcks,
        tmnxOspfIfRxLSRs,
        tmnxOspfIfRxLSUs,
        tmnxOspfIfRxPackets,
        tmnxOspfIfState,
        tmnxOspfIfStatus,
        tmnxOspfIfTeMetric,
        tmnxOspfIfTeState,
        tmnxOspfIfTransitDelay,
        tmnxOspfIfTxDBDs,
        tmnxOspfIfTxHellos,
        tmnxOspfIfTxLSAcks,
        tmnxOspfIfTxLSRs,
        tmnxOspfIfTxLSUs,
        tmnxOspfIfTxPackets,
        tmnxOspfIfType,
        tmnxOspfLinkLsdbAdvertisement,
        tmnxOspfLinkLsdbAge,
        tmnxOspfLinkLsdbChecksum,
        tmnxOspfLinkLsdbSequence,
        tmnxOspfLinkLsdbTypeKnown,
        tmnxOspfNbrAddress,
        tmnxOspfNbrAddressType,
        tmnxOspfNbrBadMTUs,
        tmnxOspfNbrBadNbrStates,
        tmnxOspfNbrBadPackets,
        tmnxOspfNbrBadSeqNums,
        tmnxOspfNbrBdrId,
        tmnxOspfNbrBfdTracking,
        tmnxOspfNbrDeadTimeOutstanding,
        tmnxOspfNbrDrId,
        tmnxOspfNbrDuplicates,
        tmnxOspfNbrEvents,
        tmnxOspfNbrHelloSuppressed,
        tmnxOspfNbrIfId,
        tmnxOspfNbrLastEventTime,
        tmnxOspfNbrLastRestartTime,
        tmnxOspfNbrLsRetransQLen,
        tmnxOspfNbrLsaInstallFailed,
        tmnxOspfNbrLsaNotInLsdbs,
        tmnxOspfNbrNumRestarts,
        tmnxOspfNbrOptionMismatches,
        tmnxOspfNbrOptions,
        tmnxOspfNbrPriority,
        tmnxOspfNbrRestartHelperAge,
        tmnxOspfNbrRestartHelperExitRc,
        tmnxOspfNbrRestartHelperStatus,
        tmnxOspfNbrRestartReason,
        tmnxOspfNbrState,
        tmnxOspfNbrUpTime
    }
    STATUS    current
    DESCRIPTION
        "The group of objects no longer supported in version 9.0 
         of Alcatel-Lucent SROS series systems."
    ::= { tmnxOspfGroups 37 }

tmnxOspfGeneralV10v0Group OBJECT-GROUP
    OBJECTS
    {
        tmnxOspfImportPolicy1,
        tmnxOspfImportPolicy2,
        tmnxOspfImportPolicy3,
        tmnxOspfImportPolicy4,
        tmnxOspfImportPolicy5
    }
    STATUS    current
    DESCRIPTION
        "The group of objects supporting management of the OSPF protocol added
         in the 10.0 release of Alcatel-Lucent SROS series systems."
    ::= { tmnxOspfGroups 38 }

tmnxOspfFRRV10v0Group OBJECT-GROUP
    OBJECTS {
        tmnxOspfLoopfreeAlternate,
        tmnxOspfAreaLoopfreeAltExclude,
        tmnxOspfNgIfLoopfreeAltExclude,
        tmnxOspfLfaSpfRuns,
        tmnxOspfLastLfaSpfRunTime,
        tmnxOspfLfaNodesCovered,
        tmnxOspfLfaTotalNodes,
        tmnxOspfLfaCoverage,
        tmnxOspfLfaPfxCovered, 
        tmnxOspfLfaTotalPfx,   
        tmnxOspfLfaPfxCoverage,
        tmnxOspfPathMetric,
        tmnxOspfPathLfaIfIndex,
        tmnxOspfPathLfaType,
        tmnxOspfPathLfaNhopRouterId,
        tmnxOspfPathLfaMetric   
    }   
    STATUS    current
    DESCRIPTION
        "The group of objects supporting management of the Fast Re-route 
         feature for OSPF on 10.0 release of Alcatel-Lucent SROS series 
         systems."
    ::= { tmnxOspfGroups 39 }

tmnxOspfFRRV11v0Group OBJECT-GROUP
    OBJECTS {
        tmnxOspfNgIfLsaFilterOut,
        tmnxOspfLsaAccumulate,
        tmnxOspfRedistDelay,
        tmnxOspfIncrSpfWait,
        tmnxOspfAreaNssaAdjCheck
    }   
    STATUS    current
    DESCRIPTION
        "The group of objects supporting management of the Fast Re-route 
         feature for OSPF on 11.0 release of Alcatel-Lucent SROS series 
         systems."
    ::= { tmnxOspfGroups 40 }

tmnxOspfGeneralV11v0Group OBJECT-GROUP
    OBJECTS {
        tmnxOspfPathNhOwner,
        tmnxOspfPathLfaNhOwner
    }
    STATUS    current
    DESCRIPTION
        "The group of objects supporting management of the OSPF protocol added
         in the 11.0 release of Alcatel-Lucent SROS series systems."
    ::= { tmnxOspfGroups 41 }

tmnxOspfGeneralV12v0Group OBJECT-GROUP
    OBJECTS {
        tmnxOspfGeneralExLastChanged,
        tmnxOspfAdvRtrCapability,
        tmnxOspfAreaAdvRtrCapability,
        tmnxOspfNgIfAdvRtrCapability,
        tmnxOspfNgIfAuthKeyChain,
        tmnxOspfVirtIfAuthKeyChain,
        tmnxOspfShamIfAuthKeyChain,
        tmnxOspfOverloadInclExt2,
        tmnxOspfLFAExcludePolicy1,
        tmnxOspfLFAExcludePolicy2,
        tmnxOspfLFAExcludePolicy3,
        tmnxOspfLFAExcludePolicy4,
        tmnxOspfLFAExcludePolicy5,
        tmnxOspfNgIfRouteNHTemplate
    }
    STATUS    current
    DESCRIPTION
        "The group of objects supporting management of the OSPF protocol added
         in the 12.0 release of Alcatel-Lucent SROS series systems."
    ::= { tmnxOspfGroups 42 }

END
