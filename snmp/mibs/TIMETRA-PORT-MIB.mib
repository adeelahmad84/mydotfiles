TIMETRA-PORT-MIB DEFINITIONS ::= BEGIN

IMPORTS
        MODULE-IDENTITY, OBJECT-TYPE,
        NOTIFICATION-TYPE, Unsigned32,
        Counter32, IpAddress, Counter64,
        Integer32, Gauge32
                                               FROM SNMPv2-SMI

        MODULE-COMPLIANCE, OBJECT-GROUP,
        NOTIFICATION-GROUP                     FROM SNMPv2-CONF

        TEXTUAL-CONVENTION, DateAndTime,
        RowStatus, TimeStamp, TimeInterval,
        TruthValue, MacAddress, RowPointer,
        DisplayString                          FROM SNMPv2-TC

        SnmpAdminString                        FROM SNMP-FRAMEWORK-MIB

        dot1xPaePortNumber                     FROM IEEE8021-PAE-MIB

        TmnxActionType, TmnxPortID,
        TItemDescription, TNamedItemOrEmpty,
        TNamedItem, TFCName, TQueueId,
        TmnxOperState, TPortSchedulerPIR,
        TPortSchedulerCIR, TItemLongDescription,
        THsmdaPIRMRateOverride, TWeight, TWeightOverride,
        TSecondaryShaper10GPIRRate,
        THsmdaWeightOverride, TMlpppQoSProfileId,
        TIngressQueueId, TEgressQueueId,
        TBurstSizeOverride, TBurstPercentOrDefaultOverride,
        TPIRRateOverride, TCIRRateOverride, TMcFrQoSProfileId,
        TmnxEnabledDisabled, TRateType,
        TAdaptationRuleOverride, TBurstSizeBytesOverride,
        TmnxSubMgtIntDestId, TmnxSubMgtOrgStrOrZero,
        TPIRPercentOverride, TCIRPercentOverride,
        TmnxSubIdentStringOrEmpty, TExpSecondaryShaperPIRRate,
        TExpSecondaryShaperClassRate,
        TClassBurstLimit, TEgrPolicerId,
        TmnxEgrPolicerStatMode,
        TPortSchedulerPIRRate, TEgressHsmdaQueueId, TEgressHsmdaCounterId,
        TEgrHsmdaPerPacketOffsetOvr,THsmdaPIRKRateOverride,
        THsmdaWrrWeightOverride, THSMDABurstSizeBytesOverride,
        TQosIngressPolicyID,
        TEgrRateModType, TPortSchedulerAggRateLimitPIR
                                               FROM TIMETRA-TC-MIB

        timetraSRMIBModules                    FROM TIMETRA-GLOBAL-MIB

        tmnxHwObjs, tmnxHwNotification,
        tmnxHwConformance, tmnxChassisIndex,
        tmnxChassisNotifyChassisId, tmnxMdaNotifyType,
        TmnxAlarmState, TmnxPortAdminStatus,
        TmnxMDAChanType                        FROM TIMETRA-CHASSIS-MIB

        AtmVpIdentifier, 
        AtmTrafficDescrParamIndex              FROM ATM-TC-MIB
        ;


tmnxPortMIBModule MODULE-IDENTITY
        LAST-UPDATED "201401010000Z"
        ORGANIZATION "Alcatel-Lucent"
        CONTACT-INFO
            "Alcatel-Lucent SROS Support
             Web: http://support.alcatel-lucent.com"
        DESCRIPTION
        "This document is the SNMP MIB module to manage and provision the
        hardware components of the Alcatel-Lucent SROS device.

        Copyright 2003-2014 Alcatel-Lucent.  All rights reserved.
        Reproduction of this document is authorized on the condition that
        the foregoing copyright notice is included.

        This SNMP MIB module (Specification) embodies Alcatel-Lucent's
        proprietary intellectual property.  Alcatel-Lucent retains
        all title and ownership in the Specification, including any
        revisions.

        Alcatel-Lucent grants all interested parties a non-exclusive
        license to use and distribute an unmodified copy of this
        Specification in connection with management of Alcatel-Lucent
        products, and without fee, provided this copyright notice and
        license appear on all copies.

        This Specification is supplied 'as is', and Alcatel-Lucent
        makes no warranty, either express or implied, as to the use,
        operation, condition, or performance of the Specification."

--
--  Revision History
--
        REVISION        "201401010000Z"
        DESCRIPTION     "Rev 12.0                1 Jan 2014 00:00
                         12.0 release of the TIMETRA-PORT-MIB."

        REVISION        "201102010000Z"
        DESCRIPTION     "Rev 9.0                 1 Feb 2011 00:00
                         9.0 release of the TIMETRA-PORT-MIB."

        REVISION        "200902280000Z"
        DESCRIPTION     "Rev 7.0                28 Feb 2009 00:00
                         7.0 release of the TIMETRA-PORT-MIB."

        REVISION        "200807010000Z"
        DESCRIPTION     "Rev 6.1                01 Jul 2008 00:00
                         6.1 release of the TIMETRA-PORT-MIB."

        REVISION        "200801010000Z"
        DESCRIPTION     "Rev 6.0                01 Jan 2008 00:00
                         6.0 release of the TIMETRA-PORT-MIB."

        REVISION        "200701010000Z"
        DESCRIPTION     "Rev 5.0                01 Jan 2007 00:00
                         5.0 release of the TIMETRA-PORT-MIB."

        REVISION        "200603160000Z"
        DESCRIPTION     "Rev 4.0                16 Mar 2006 00:00
                         4.0 release of the TIMETRA-PORT-MIB."

        REVISION        "200508310000Z"
        DESCRIPTION     "Rev 3.0                31 Aug 2005 00:00
                         3.0 release of the TIMETRA-PORT-MIB."

        REVISION        "200501240000Z"
        DESCRIPTION     "Rev 2.1                24 Jan 2005 00:00
                         2.1 release of the TIMETRA-PORT-MIB."

        REVISION        "200403010000Z"
        DESCRIPTION     "Rev 2.0                01 Mar 2004 00:00
                         2.0 release of the TIMETRA-PORT-MIB."

        ::= { timetraSRMIBModules 25 }


tmnxPortObjs                    OBJECT IDENTIFIER ::= { tmnxHwObjs 4 }
tmnxPortNotificationObjects     OBJECT IDENTIFIER ::= { tmnxHwObjs 7 }
tmnxFRObjs                      OBJECT IDENTIFIER ::= { tmnxHwObjs 9 }
tmnxQosAppObjs                  OBJECT IDENTIFIER ::= { tmnxHwObjs 10 }
tmnxATMObjs                     OBJECT IDENTIFIER ::= { tmnxHwObjs 11 }
tmnxPortStatsObjs               OBJECT IDENTIFIER ::= { tmnxHwObjs 12 }

tmnxPortNotifyPrefix OBJECT IDENTIFIER ::= { tmnxHwNotification 2 }
  tmnxPortNotification OBJECT IDENTIFIER ::= { tmnxPortNotifyPrefix 0 }

tmnxPortConformance     OBJECT IDENTIFIER ::= { tmnxHwConformance 2 }

--
-- Subtrees
--
tmnxPortPlcyObjs                OBJECT IDENTIFIER ::= { tmnxPortObjs 67 }

--%%%%%%%%%%%%%%%%%%%%%%%%%%%%%%%%%%%%%%%%%%%%%%%%%%%%%%%%%%%%%%%%%%%%%
--
--      TIMETRA-PORT-MIB textual conventions
--

--
--      TmnxPortOperStatus
--
TmnxPortOperStatus ::= TEXTUAL-CONVENTION
    STATUS  current
    DESCRIPTION
        "The current operational status of this port."
    SYNTAX  INTEGER {
                unknown (1),
                inService (2),
                outOfService (3),
                diagnosing (4),
                failed (5)
            }

--
--      TmnxPortEtherReportValue
--
TmnxPortEtherReportValue ::= TEXTUAL-CONVENTION
    STATUS  current
    DESCRIPTION
        "The TmnxPortEtherReportValue is an enumerated integer that describes
         the values used to identify the reason an alarm has been raised on an
         Ethernet Port.
        
         The possible values are:
            notUsed      (0) - not applicable
            signalFailure(1) - Ethernet signal lost alarm
                When the optic module declares a loss of signal, the MAC will
                declare localFault(3) and the PCS will declare noBlockLock(6).
            remoteFault  (2) - Remote Fault
                See localFault(3).
            locaFault   (3) - Local Fault
                Defined in IEEE 802.3ba Clause 81.3.4.
                When the PCS detects a fault it generates a localFault(3)
                towards the MAC layer. The MAC layer responds by sending a
                remoteFault(2) to the far end.  A local fault can get caused
                by any of the PCS layer defects below.
            noFrameLock  (4) - Not locked on the Ethernet framing sequence
                Defined in IEEE 802.3ba Clause 82.2.13.
                The frame lock is obtained when all lanes have 64B/66B block
                sync, been deskewed, and alignment marker lock.
            highBer      (5) - High Bit Error Rate
                Defined in IEEE 802.3ba Clause 82.2.18.2.2.
                Bit error ratio > 10^-4.
            noBlockLock  (6) - 40G/100G PCS Lanes Not Block Locked
                Defined in IEEE 802.3ba Clause 82.2.11.
                Cleared once all lanes have 64B/66B block lock.
            noAmLock     (7) - 40G/100G PCS Alignment Marker Loss of Lock
                Defined in IEEE 802.3ba Clause 82.2.12.
                Cleared once all lanes alignment marker lock.
            duplicateLane(8) - 40G/100G PCS Duplicate Lane Marker
                Not defined in the standard.
                Raised when two or more lanes are seen with the same alignment
                marker."
    SYNTAX  INTEGER {
                notUsed      (0),
                signalFailure(1),
                remoteFault  (2),
                localFault   (3),
                noFrameLock  (4),
                highBer      (5),
                noBlockLock  (6),
                noAmLock     (7),
                duplicateLane(8) 
            }

--
--      TmnxPortEtherReportStatus
--
TmnxPortEtherReportStatus ::= TEXTUAL-CONVENTION
    STATUS  current
    DESCRIPTION
        "The TmnxPortEtherReportStatus is a bitmask that describes alarms that
         can be raised/cleared on an Ethernet Port.

         The possible values are:
            notUsed      (0) - not applicable
            signalFailure(1) - Ethernet signal lost alarm
                When the optic module declares a loss of signal, the MAC will
                declare localFault(3) and the PCS will declare noBlockLock(6).
            remoteFault  (2) - Remote Fault
                See localFault(3).
            locaFault   (3) - Local Fault
                Defined in IEEE 802.3ba Clause 81.3.4.
                When the PCS detects a fault it generates a localFault(3)
                towards the MAC layer. The MAC layer responds by sending a
                remoteFault(2) to the far end.  A local fault can get caused
                by any of the PCS layer defects below.
            noFrameLock  (4) - Not locked on the Ethernet framing sequence
                Defined in IEEE 802.3ba Clause 82.2.13.
                The frame lock is obtained when all lanes have 64B/66B block
                sync, been deskewed, and alignment marker lock.
            highBer      (5) - High Bit Error Rate
                Defined in IEEE 802.3ba Clause 82.2.18.2.2.
                Bit error ratio > 10^-4.
            noBlockLock  (6) - 40G/100G PCS Lanes Not Block Locked
                Defined in IEEE 802.3ba Clause 82.2.11.
                Cleared once all lanes have 64B/66B block lock.
            noAmLock     (7) - 40G/100G PCS Alignment Marker Loss of Lock
                Defined in IEEE 802.3ba Clause 82.2.12.
                Cleared once all lanes alignment marker lock.
            duplicateLane(8) - 40G/100G PCS Duplicate Lane Marker
                Not defined in the standard.
                Raised when two or more lanes are seen with the same alignment
                marker."
    SYNTAX  BITS {
                notUsed      (0),
                signalFailure(1),
                remoteFault  (2),
                localFault   (3),
                noFrameLock  (4),
                highBer      (5),
                noBlockLock  (6),
                noAmLock     (7),
                duplicateLane(8) 
            }

--
--      TmnxPortEtherMonReportValue
--
TmnxPortEtherMonReportValue      ::= TEXTUAL-CONVENTION
    STATUS  current
    DESCRIPTION
        "The TmnxPortEtherMonReportValue is an enumerated integer that
         describes the values used to identify the reason an alarm has been
         raised for a fault in Monitoring on an Ethernet Port.

         TmnxPortEtherMonReportStatus defines the valid alarm values."
    SYNTAX  INTEGER {
                noFault             (0),
                sdThresholdExceeded (1),
                sfThresholdExceeded (2)
            }

--
--      TmnxPortEtherMonReportStatus
--
TmnxPortEtherMonReportStatus     ::= TEXTUAL-CONVENTION
    STATUS  current
    DESCRIPTION
        "The TmnxPortEtherMonReportStatus is a bitmask that describes alarms
        that can be raised/cleared on an Ethernet Port used in Monitoring.

        The possible values are:
           sdThresholdExceeded (0)-- Signal Degradation exceeded the threshold.
           sfThresholdExceeded (1)-- Signal Failure exceeded the threshold."
    SYNTAX  BITS {
                sdThresholdExceeded (0),
                sfThresholdExceeded (1)
            }

--
--      TmnxPortEtherOperPhyTxClock
--
TmnxPortEtherOperPhyTxClock ::= TEXTUAL-CONVENTION
    STATUS  current
    DESCRIPTION
        "The TmnxPortEtherOperPhyTxClock data type is an enumerated integer that
         indicates the result of the master/slave resolution on copper based
         Ethernet ports running at 1 Gbps.

         - The value of 'notApplicable' indicates that this object is not
           applicable to this port.
         - The value of 'master' indicates that the port is the timing master
           for the link partner.
         - The value of 'slave' indicates that the port is timing slave 
           to the link partner."
    SYNTAX  INTEGER {
                notApplicable (0),
                master (1),
                slave (2)
            }

--
--      TmnxPortClass
--
TmnxPortClass ::= TEXTUAL-CONVENTION
    STATUS  current
    DESCRIPTION
        "The TmnxPortClass data type is an enumerated integer that
         describes the values used to identify the class of interface
         provided by this port."
    SYNTAX  INTEGER {
                none  (1),      -- no port installed
                faste (2),      -- Fast Ethernet (10/100MBS)
                gige  (3),      -- Gigabit Ethernet
                xgige (4),      -- Ten-Gigabit Ethernet
                sonet (5),      -- SONET
                vport (6),      -- Virtual port
                unused(7),      -- Unused
                xcme  (8),      -- 10/100/1000 Ethernet
                tdm   (9),      -- TDM
                xlgige(10),     -- Forty-Gigabit Ethernet
                cgige (11),     -- 100Gig Ethernet
                vsme  (12)      -- VSM Ethernet
            }

--
--      TmnxPortConnectorType
--
TmnxPortConnectorType ::= TEXTUAL-CONVENTION
    STATUS  current
    DESCRIPTION
        "The TmnxPortConnectorType data type is an enumerated integer that
         describes the values used to identify the connector type used on
         a port.  A TmnxPortConnectorType value specifies the index value
         for the entry in the tmnxPortConnectTypeTable used to identify a
         specific type of port connector.  Some example port connector types
         are: 'unknown', 'rj45', 'bncCoax', 'mtrj', 'scDuplex', 'sffp',
         'lcDuplex'."
    SYNTAX  Unsigned32

--
--      TmnxPortState
--
TmnxPortState ::= TEXTUAL-CONVENTION
    STATUS  current
    DESCRIPTION
        "The state level of this port.  A value of 'none' indicates the
         port is either in its initial creation state or is just about to
         be deleted.  A value of 'ghost' represents a port that is not
         physically present.  This state may represent a pre-provisioned
         port.  A value of 'linkDown' represents a port that is physically
         present but does not have a link.  The 'linkUp' state represents a
         port that is physically present and has physical link present.
         A port in 'up' state is ready to pass some kinds of traffic.
         The tmnxPortUpProtocols variable indicates the actual type(s) of
         traffic that can be passed on this 'up' link. The 'diagnose' state
         represents the port undergoing diagnostic test."
    SYNTAX  INTEGER {
                none (1),
                ghost (2),
                linkDown (3),
                linkUp (4),
                up (5),
                diagnose (6)
            }

--
--      TmnxPortType
--
TmnxPortType ::= TEXTUAL-CONVENTION
    STATUS      current
    DESCRIPTION
        "The TmnxPortType data type is an enumerated integer that describes
         the values used to identify the specific type of hardware port.
         A TmnxPortType value specifies the index value for the entry in the
         tmnxPortTypeTable used to identify a specific type of port.
         Some example port types are:
            -- unknown            - no port installed or unidentified
            -- portType100Tx      - 10/100 base copper
            -- portType100F       - 10/100 base fiber
            -- portType1000Tx     - 1000 base copper
            -- portType1000F      - 1000 base fiber
            -- portType1000dF     - 1000 base dual fiber
            -- portTypeOC3sonet   - OC-3
            -- portTypeOC12sonet  - OC-12
            -- portTypeOC48sonet  - OC-48
            -- portTypeOC192sonet - OC-192
            -- portType10000F     - 10 Gig Ethernet LAN
            -- portTypeXgigWan    - 10 Gig Ethernet WAN
            -- portTypeVport      - Virtual port
            -- portTypeDS3E3      - DS3/E3 port
            -- portTypeDS1E1      - DS1/E1 port
            -- portTypeXcmeTx     - 10/100/1000 base copper
         "
    SYNTAX  Unsigned32

--
--      TmnxPortEncapType
--
TmnxPortEncapType ::= TEXTUAL-CONVENTION
    STATUS      current
    DESCRIPTION
        "The type of encapsulation protocol configured on a
         port's network interface.

         When the encap type has a value of 'nullEncap', 
         frames received will not carry any tags
         or labels and as a result only one service can be
         configured on this port.  Sometimes this is referred to
         as raw Ethernet packets.

         When the encap type has a value of 'qEncap', ingress frames
         carry 802.1q tags where each different tag can signify a
         different service. This is not a valid value if
         tmnxPortClass has a value of 'sonetPath'.

         When the encap type has a value of 'bcpNullEncap',
         BCP is used on the SONET path as the NCP control protocol.
         The BCP IEEE 802 Tagged Frame Configuration Option (type 8)
         is negotiated to 'enabled'.  VLAN tagged frames are
         allowed into the SONET path.  Only a single SAP can
         be associated with the SONET path.  'bcpNullEncap' is
         valid only if tmnxPortClass has a value of 'sonetPath'.

         When the encap type has a value of 'bcpDot1qEncap',
         BCP is used as the NCP control protocol.  The BCP IEEE 802
         Tagged Frame Configuration Option (type 8) is negotiated to
         'enabled'.  VLAN tagged frames are allowed on the SONET path.
         This encapsulation type is required when multiple SAPs are
         defined on the SONET path where each one is service
         delimited by a provisioned Dot1q tag.  When 'bcpDot1qEncap'
         is specified, BCP does not enter the 'open' state unless
         the far end peer also supports 'bcpDot1qEncap'.  This allows
         a LCP negotiation to transmit configuration request and
         confirmation messages to enable this feature.  'bcpDot1qEncap'
         is a valid value only if tmnxPortClass has a value of 'SONET'.

         When the encap type has a value of 'ipcpEncap',
         BCP will not be used on this SONET path.  IPCP NCP is used
         instead.  'ipcpEncap' is a valid only if tmnxPortClass has
         a value of 'sonetPath'.

         When the encap type has a value of 'frEncap', Frame Relay is
         the expected encapsulation.

         When the encap type has a value of 'pppAutoEncap', IPCP is
         automatically enabled. This encap type is only valid on
         ports/paths in network mode.

         When the encap type has a value of 'atmEncap', the encapsulation
         on the port is ATM. The 'atmEncap' is also used when mirroring
         ATM ports.

         When the encap type has a value of 'wanMirrorEncap', the
         port is used for mirroring of frame-relay and POS ports. On such
         ports no link management protocol would run.

         When the encap type has a value of 'ciscoHDLCEncap', the Cisco HDLC
         encapsulation is applied. This encap type is only valid if
         TmnxPortClass has a value of 'tdm' or 'sonet'.

         When the encap type has a value of 'cemEncap', encapsulation of
         frames will be circuit emulation.  This is used to support transparent
         transmission of frames.  This encap type is only valid
         if TmnxPortClass has a value of 'tdm' or 'sonet' in access mode.
         "
    SYNTAX      INTEGER {
                    unknown (0),
                    nullEncap (1),  
                    qEncap (2),
                    mplsEncap (3),
                    bcpNullEncap (4),
                    bcpDot1qEncap (5),
                    ipcpEncap (6),
                    frEncap (7),
                    pppAutoEncap (8),
                    atmEncap (9),
                    qinqEncap (10),
                    wanMirrorEncap (11),
                    ciscoHDLCEncap (12),
                    cemEncap (13)
                }

--
--      TmnxDs0ChannelList
--
TmnxDs0ChannelList ::= TEXTUAL-CONVENTION
    STATUS       current
    DESCRIPTION
            "A list of ds0 timeslots on a DS1 line.

            The list is specified as an OCTET STRING in which each ds0
            timeslot is represented by a single bit, where  timeslots 1
            through 8 are represented by the bits in the first octet,
            timeslots 9 through 16 by the bits in the second octet,
            etc.  In each octet, the lowest numbered timeslot is
            represented by the most significant bit, and the highest
            numbered timeslot by the least significant bit.  A timeslot
            is present in the list when its bit is 1, and absent
            when its bit is 0.

            If the OCTET STRING value has more bits than required to
            represent the timeslots on a DS1, then the extra bits
            are ignored."
    SYNTAX       OCTET STRING (SIZE(0..4))

--
--      TmnxBundleID
--
TmnxBundleID ::= TEXTUAL-CONVENTION
    STATUS  current
    DESCRIPTION
        "A TmnxBundleID is an unique 32 bit number encoded as shown below.

            |32 30| 29 26 | 25 22 | 21 16 | 15     13 | 12   1|
            +-----+-------+-------+-------+-----------+-------+
            |001  |  slot |  mda  |   0   | bndl type | bndlid|
            +-----+-------+-------+-------+-----------+-------+

         The bundle id is unique for a MDA.  The bndlid must fall in one of
         the following ranges depending on MDA type:

           mda-type             range
           m4-choc3-as-sfp      1-256
           m1-choc12-as-sfp     1-256
           m12-chds3-as         1-256
           m4-chds3-as          1-112
           m4-chds3             1-56
           m12-chds3            1-56
           m1-choc12-sfp        1-56
           m4-choc3-sfp         1-56
           c8-chds1             1-56
           c8-atmds1            1-8

         A slot value of 15 (Invalid slot) and mda value of 0 (invalid mda)
         represents a bundle protection group.
         Otherwise, the bundle is considered associated with a valid slot
         and mda.

         The following bundle types are supported:

         bndl type     value
           MLPPP        000
           IMA          001
           MLFR         010"
    SYNTAX  Unsigned32

--
--      TmnxDSXBertPattern
--
TmnxDSXBertPattern ::= TEXTUAL-CONVENTION
    STATUS  current
    DESCRIPTION
        "The TmnxDSXBertPattern data type is an enumerated integer that
         indicates the pattern used for the Bit Error Rate Test (BERT)."
    SYNTAX  INTEGER {
                none        (0),
                ones        (1),
                zeros       (2),
                alternating (3),
                twoexp3     (4),
                twoexp9     (5),
                twoexp15    (6),
                twoexp20    (7),
                twoexp11    (8),
                twoexp20q   (9),
                twoexp23   (10)
            }

--
--      TmnxDSXBertOperStatus
--
TmnxDSXBertOperStatus ::= TEXTUAL-CONVENTION
    STATUS  current
    DESCRIPTION
        "The TmnxDSXBertOperStatus data type is an enumerated integer that
         indicates the status of Bit Error Rate Test (BERT).
         When BERT is activated, the status will be 'active'. Otherwise
         the status will be 'idle' or 'noMdaResources' if the last BERT test
         could not be executed because of an MDA concurrent BERT test limit."
    SYNTAX  INTEGER {
                none (0),
                active (1),
                idle (2),
                noMdaResources (3)
            }

--
--      TmnxDSXIdleCycleFlags
--
TmnxDSXIdleCycleFlags ::= TEXTUAL-CONVENTION
    STATUS  current
    DESCRIPTION
        "The TmnxDSXIdleCycleFlags data type is an enumerated integer that
         indicates the value that the DS3/DS1 port/channel or a DS0 channel
         group transmits during idle cycle.

         The value of 'none' is applicable to ATM and CEM ports/channels only,
         which transmit idle cells and not octets defined by the below values.

         If the value is set to 'flags', a value of 0x7E is used.
         If the value is set to 'ones', a value of 0xFF is used."
    SYNTAX  INTEGER {
                none  (0),
                flags (1),
                ones (2)
            }

--
--      TmnxDSXIdleFillType
--
TmnxDSXIdleFillType ::= TEXTUAL-CONVENTION
    STATUS  current
    DESCRIPTION
        "The TmnxDSXIdleFillType data type is an enumerated integer that
         indicates the type of data fill that a CEM DS3/DS1 channel or a DS0
         channel group plays out when the channel experiences underun.

         - The value of 'notApplicable' indicates that this object is not
           applicable to the channel.
         - The value of 'allOnes' indicates that all 1's will be played out.
         - The value of 'userDefinedPattern' indicates that a user defined
           pattern will be played out."
    SYNTAX  INTEGER {
                notApplicable (0),
                allOnes (1),
                userDefinedPattern (2)
            }

--
--      TmnxDSXLoopback
--
TmnxDSXLoopback ::= TEXTUAL-CONVENTION
    STATUS  obsolete
    DESCRIPTION
        "The TmnxDSXLoopback data type is an enumerated integer that
         indicates the type of loopback the DS3/DS1 port/channel
         currently is in."
    SYNTAX  INTEGER {
                none (0),
                line (1),
                internal (2),
                remote (3)
            }

--
--      TmnxDSXReportAlarm
--
TmnxDSXReportAlarm ::= TEXTUAL-CONVENTION
    STATUS      current
    DESCRIPTION
        "The TmnxDSXReportAlarm data type indicates the type of TDM alarm:
         ais - alarm indication signal errors.
         los - loss of signal errors.
         oof - out-of-frame errors.
         rai - resource availability indicator events.
         looped - far end wants the read end to loopback
         berSd - DSX bit error signal degradation
         berSf - DSX bit error signal failure"
    SYNTAX      BITS {
                    notUsed (0),
                    ais (1),
                    los (2),
                    oof (3),
                    rai (4),
                    looped (5),
                    berSd (6),
                    berSf (7)
                }

--
--      TmnxDSXClockSource
--
TmnxDSXClockSource ::= TEXTUAL-CONVENTION
    STATUS      current
    DESCRIPTION
        "The TmnxDSXClockSource data type is an enumerated type
         that indicates the clock for transmitted data on a DS3 or DS1 channel.
         loopTimed(1)     - The clock is recovered from the line's receive
                            data stream
         nodeTimed(2)     - The clock is internal
         adaptive(3)      - The clock is adaptively recovered from the rate at
                            which data is received and not from the physical
                            layer.
         differential(4)  - The clock is recovered from differential RTP
                            timestamp header."
    SYNTAX      INTEGER {
                    loopTimed    (1),
                    nodeTimed    (2),
                    adaptive     (3),
                    differential (4)
                }

--
--      TmnxDSXClockSyncState
--
TmnxDSXClockSyncState ::= TEXTUAL-CONVENTION
    STATUS      current
    DESCRIPTION
        "The TmnxDSXClockSyncState data type is an enumeration type that
         indicates the clock synchronization state on a DS3 or DS1 channel.
         unknown(0)       - Unsupported or unknown state
         normal(1)        - Normal (locked) state
         holdOver(2)      - Synchronization with reference has been lost
         freeRun(3)       - Synchronized with internal reference"
    SYNTAX      INTEGER {
                    unknown  (0),
                    normal   (1),
                    holdOver (2),
                    freeRun  (3)
                }

--
--      TmnxDS1Loopback
--
TmnxDS1Loopback ::= TEXTUAL-CONVENTION
    STATUS  current
    DESCRIPTION
        "The TmnxDS1Loopback data type is an enumerated integer that
         indicates the type of loopback the DS1 port/channel
         currently is in.
         A 'line' loopback loops frames received on this port back to the
         remote system.
         A 'internal' loopback loops frames from the local system back at
         the framer.
         A 'fdlAnsi' requests a line loopback of type FDL ANSI T1.403.
         A 'fdlBellcore' requests a line loopback of type FDL Bellcore
         TR-TSY-000312.
         A 'payloadAnsi' requests a payload loopback of type FDL ANSI T1.403.
         A 'inbandAnsi' requests a line loopback of type inband ANSI T1.403.
         A 'inbandBellcore' requests a line loopback of type inband Bellcore
         TR-TSY-000312."
    SYNTAX  INTEGER {
                none (0),
                line (1),
                internal (2),
                fdlAnsi (3),
                fdlBellcore (4),
                payloadAnsi (5),
                inbandAnsi  (6),
                inbandBellcore (7)
            }

--
--      TmnxDS3Loopback
--
TmnxDS3Loopback ::= TEXTUAL-CONVENTION
    STATUS  current
    DESCRIPTION
        "The TmnxDS3Loopback data type is an enumerated integer that
         indicates the type of loopback the DS3 port/channel
         currently is in.
         A 'line' loopback loops frames received on this port back to the
         remote system.
         A 'internal' loopback loops the frames from the local system back at
         the framer.
         When the value is set to 'remote', a signal is sent to the remote
         system to provide a line loopback."
    SYNTAX  INTEGER {
                none (0),
                line (1),
                internal (2),
                remote (3)
            }

--
--      TmnxImaGrpState
--
TmnxImaGrpState ::= TEXTUAL-CONVENTION
    STATUS      current
    DESCRIPTION
        "The TmnxImaGrpState indicates the current state
         of the IMA Group State Machine."
    SYNTAX      INTEGER {
                    invalid                          (0),
                    notConfigured                    (1),
                    startUp                          (2),
                    startUpAck                       (3),
                    configAbortUnsupportedM          (4),
                    configAbortIncompatibleSymmetry  (5),
                    configAbortOther                 (6),
                    insufficientLinks                (7),
                    blocked                          (8),
                    operational                      (9),
                    configAbortUnsupportedImaVersion (10)
                }

TmnxImaGrpFailState ::= TEXTUAL-CONVENTION
    STATUS      current
    DESCRIPTION
        "The TmnxImaGrpFailState indcates the failure
         reason of an IMA group."
    SYNTAX      INTEGER {
                    noFailure(1), -- unit is up
                    startUpNe(2),
                    startUpFe(3),
                    invalidMValueNe(4),
                    invalidMValueFe(5),
                    failedAssymetricNe(6),
                    failedAssymetricFe(7),
                    insufficientLinksNe(8),
                    insufficientLinksFe(9),
                    blockedNe(10),
                    blockedFe(11),
                    otherFailure(12),
                    invalidImaVersionNe(13),
                    invalidImaVersionFe(14)
                }

TmnxImaLnkState ::= TEXTUAL-CONVENTION
    STATUS      current
    DESCRIPTION
        "The TmnxImaLnkState indicates the current
         state of an IMA link."
    SYNTAX      INTEGER {
                    notInGroup(1),
                    unusableNoGivenReason(2),
                    unusableFault(3),
                    unusableMisconnected(4),
                    unusableInhibited(5),
                    unusableFailed(6),
                    usable(7),
                    active(8)
                }

TmnxImaLnkFailState ::= TEXTUAL-CONVENTION
    STATUS      current
    DESCRIPTION
        "The TmnxImaLnkFailState indicates the local failure
         status of a link belonging to an IMA group."
    SYNTAX      INTEGER {
                    noFailure(1),
                    imaLinkFailure(2),
                    lifFailure(3),
                    lodsFailure(4),
                    misConnected(5),
                    blocked(6),
                    fault(7),
                    farEndTxLinkUnusable(8),
                    farEndRxLinkUnusable(9)
                }

TmnxImaTestState ::= TEXTUAL-CONVENTION
    STATUS      current
    DESCRIPTION
        "The TmnxImaTestState indicates the current state
         of the test pattern procedure."
    SYNTAX      INTEGER {
                    disabled(1),
                    operating(2),
                    failed(3)
                }

TmnxImaGrpClockModes ::= TEXTUAL-CONVENTION
    STATUS      current
    DESCRIPTION
        "The TmnxImaGrpClockModes lists the types of
         clock modes available to IMA Groups."
    SYNTAX      INTEGER {
                    ctc(1),
                    itc(2)
                }

TmnxImaGrpVersion ::= TEXTUAL-CONVENTION
    STATUS      current
    DESCRIPTION
        "The TmnxImaGrpVersion lists the types of
         Ima versions available per IMA Groups."
    SYNTAX      INTEGER {
                    oneDotZero(1),
                    oneDotOne(2)
                }

TmnxMcMlpppClassIndex ::= TEXTUAL-CONVENTION
    STATUS      current
    DESCRIPTION
        "The TmnxMcMlpppClassIndex indicates the class
         of a Multiclass MLPPP bundle.

         For Multiclass MLPPP bundles with a non-zero
         tmnxBundleMlpppClassCount of classes, class index takes
         valid values from 0 to (tmnxBundleMlpppClassCount - 1)
         inclusive. For example a 4-class MLPPP bundle has 4 classes
         with indices 0, 1, 2, and 3."
    SYNTAX      INTEGER (0..15)

TmnxMlpppEndpointIdClass ::= TEXTUAL-CONVENTION
    STATUS  current
    DESCRIPTION
        "TmnxMlpppEndpointIdClass indicates the MLPPP Endpoint
         Discriminator Class Field Type."
    SYNTAX      INTEGER {
                    nullClass (0),
                    localAddress (1),
                    ipAddress (2),
                    ieee802dot1GlobalMacAddress (3),
                    pppMagicNumberBlock (4),
                    publicSwitchedNetworkDirNumber (5)
                }

TmnxMlfrLinkDownReason ::= TEXTUAL-CONVENTION
    STATUS  current
    DESCRIPTION
        "TmnxMlfrLinkDownReason indicates the reason code for marking
         a MLFR member link of a bundle to down.
             A 'none' down reason indicates that the link is active.
             An 'outOfService' down reason indicates that the link
             operational status is down.
             A 'redDiffDelayExceeded' down reason indicates that the
             differential delay of the link exceeded the configured
             value of red differential delay and the delay action was
             configured as 'down'.
             A 'loopback' down reason indicates that the link has been
             detected to be in a loopback condition.
             A 'negotiating' down reason indicates that the link has
             not successfully negotiated the link into a bundle.
             A 'noRxHelloAck' down reason indicates that the link has
             not received a hello ack response.
             A 'rxCause' down reason indicates that a peer failure has
             been detected on this link.
             A 'txCause' down reason indicates that a local failure has
             been detected on this link.
             A linkReset' down reason indicates that the link is being reset."
    SYNTAX      INTEGER {
                    none (0),
                    outOfService (1),
                    redDiffDelayExceeded (2),
                    loopback (3),
                    negotiating (4),
                    noRxHelloAck (5),
                    rxCause (7),
                    txCause (8),
                    linkReset (9)
                }

--
--      TmnxWaveTrackerAlarm
--
TmnxWaveTrackerAlarm ::= TEXTUAL-CONVENTION
    STATUS      current
    DESCRIPTION
        "The TmnxWaveTrackerAlarm specifies the alarms which are enabled or
         outstanding against a Wave Tracker enabled interface.
         The valid alarms are as follows:

                - encFail       - Encoder Failure.
                - encDegr       - Encoder Degrade.
                - pwrFail       - Power Control Failure.
                - pwrDegr       - Power Control Degrade.
                - pwrHigh       - Power Control High limit reached.
                - pwrLow        - Power Control Low limit reached.
                - missing       - Missing pluggable VOA."
   SYNTAX       BITS {
                    encFail      (0),
                    encDegr      (1),
                    pwrFail      (2),
                    pwrDegr      (3),
                    pwrHigh      (4),
                    pwrLow       (5),
                    missing      (6)
                }

--
--      TmnxOpticalAmpAlarm
--
TmnxOpticalAmpAlarm ::= TEXTUAL-CONVENTION
    STATUS      current
    DESCRIPTION
        "The TmnxOpticalAmpAlarm specifies the alarms which are enabled
         or outstanding against an interface that is equipped with an
         optical amplifier.
         The valid alarms are as follows:

                - ampIld        - Amplifier Pump over-current.
                - ampTmp        - Amplifier Pump temperature.
                - ampMth        - Amplifier Module Case temperature high.
                - ampMtl        - Amplifier Module Case temperature low.
                - ampLos        - Amplifier Loss of input optical power.
                - ampLop        - Amplifier Loss of output power.
                - ampCom        - Amplifier Module communication failure."
   SYNTAX       BITS {
                    ampIld       (0),
                    ampTmp       (1),
                    ampMth       (2),
                    ampMtl       (3),
                    ampLos       (4),
                    ampLop       (5),
                    ampCom       (6)
                }

--
--      TmnxOpticalTdcmAlarm
--
TmnxOpticalTdcmAlarm ::= TEXTUAL-CONVENTION
    STATUS      current
    DESCRIPTION
        "The TmnxOpticalTdcmAlarm specifies the alarms which are enabled
         or outstanding against an interface that is equipped with a
         tunable dispersion compensation module.
         The valid alarms are as follows:

                - tdcmNotRdy     - Tdcm not ready.
                - tdcmMth        - Tdcm module temperature high.
                - tdcmMtl        - Tdcm module temperature low.
                - tdcmUnLck      - Tdcm thermal control unlocked.
                - tdcmTmpLim     - Tdcm thermal control temperature limit.
                - tdcmEprInv     - Tdcm EEPROM invalid.
                - tdcmCom        - Tdcm module communication failure."
   SYNTAX       BITS {
                    tdcmNotRdy     (0),
                    tdcmMth        (1),
                    tdcmMtl        (2),
                    tdcmUnLck      (3),
                    tdcmTmpLim     (4),
                    tdcmEprInv     (5),
                    tdcmCom        (6)
                }

--
--      TmnxOpticalDispCtrlMode
--
TmnxOpticalDispCtrlMode ::= TEXTUAL-CONVENTION
    STATUS      current
    DESCRIPTION
        "The TmnxOpticalDispCtrlMode specifies the operational control mode
         of the dispersion compensation module. The valid modes are as follows:
                - automatic     - The software control loop automatically
                                  determines the dispersion using a FEC
                                  feedback algorithm to find the best
                                  operational dispersion compensation point
                - manual        - The software control loop is disabled and
                                  the user manually configures the dispersion
                                  compensation."                                  
    SYNTAX          INTEGER {
                        automatic (0),
                        manual    (1)
                    }

TmnxOpticalAmpCtrlState ::= TEXTUAL-CONVENTION
    STATUS      current
    DESCRIPTION
        "The TmnxOpticalAmpCtrlState specifies the state of the control loop
         that optimizes the receive optical power of to the MSA optics."
    SYNTAX          INTEGER {
                        unknown        (0),
                        lossOfsignal   (1),
                        adjusting      (2),
                        paused         (3),
                        converged      (4)
                    }
        
TmnxOpticalTdcmCtrlState ::= TEXTUAL-CONVENTION
    STATUS      current
    DESCRIPTION
        "The TmnxOpticalTdcmCtrlState specifies the state of the control loop
         that optimizes the dispersion by tuning the dispersion compensation
         module to the set point at which the FEC corrected error rate is the
         lowest."
    SYNTAX          INTEGER {
                        unknown     (0),
                        disabled    (1),
                        waiting     (2),
                        sweeping    (3),
                        zoneIn      (4),
                        fineTuning  (5),
                        converged   (6)
                    }

TmnxOpticalDwdmChannel ::= TEXTUAL-CONVENTION
    STATUS      current
    DESCRIPTION
        "TmnxOpticalDwdmChannel is the DWDM ITU channel associated with an
         optical interface. It is expressed in a form that is derived from the
         laser's operational frequency. For example 193.40 THz corresponds to
         DWDM ITU channel 34 in the 100 GHz grid and 193.45 THz corresponds to
         DWDM ITU channel 345 in the 50 GHz grid.

             Range    ITU Grid
             -------- ----------------------
             17-61    100 GHz Grid
             170-610  50 GHz Grid

         For configurable attributes, the value 0 represents no channel. For
         read-only attributes, the value 0 represents no channel transmitted or
         the interface is not equipped with a laser."
    SYNTAX      Unsigned32 (0|17..61|170..610)

TmnxDigitalDiagnosticFailureBits ::= TEXTUAL-CONVENTION
    STATUS      current
    DESCRIPTION
        "The TmnxDigitalDiagnosticFailureBits specifies the state of the Digital
         Diagnostic Monitoring (DDM) SFF thresholds. For each monitored
         attribute a low-warning, low-alarm, high-warning, and high-alarm are
         recorded.

         A set bit indicates the object is in a failed state, a cleared bit
         indicates the object has not exceeded the threshold."
    SYNTAX      BITS {
                    unknown                      (0),
                    temperature-low-warning      (1),
                    temperature-low-alarm        (2),
                    temperature-high-warning     (3),
                    temperature-high-alarm       (4),
                    supplyVoltage-low-warning    (5),
                    supplyVoltage-low-alarm      (6),
                    supplyVoltage-high-warning   (7),
                    supplyVoltage-high-alarm     (8),
                    txBiasCurrent-low-warning    (9),
                    txBiasCurrent-low-alarm     (10),
                    txBiasCurrent-high-warning  (11),
                    txBiasCurrent-high-alarm    (12),
                    txOutputPower-low-warning   (13),
                    txOutputPower-low-alarm     (14),
                    txOutputPower-high-warning  (15),
                    txOutputPower-high-alarm    (16),
                    rxOpticalPower-low-warning  (17),
                    rxOpticalPower-low-alarm    (18),
                    rxOpticalPower-high-warning (19),
                    rxOpticalPower-high-alarm   (20),
                    aux1-low-warning            (21),
                    aux1-low-alarm              (22),
                    aux1-high-warning           (23),
                    aux1-high-alarm             (24),
                    aux2-low-warning            (25),
                    aux2-low-alarm              (26),
                    aux2-high-warning           (27),
                    aux2-high-alarm             (28)
                }

TmnxCoherentOpticalDefectPoint ::= TEXTUAL-CONVENTION
    STATUS      current
    DESCRIPTION
        "The TmnxCoherentOpticalDefectPoint specifies the type of coherent
         optical defects currently active on the port.
                    
             overTemp           - Module over safe operating temperature.
             hwPost             - Hardware fault detected during power-on 
                                  self-test.
             pldFlashInit       - PLD (Programmable Logic Device), CPLD
                                  (Complex Programmable Logic Device), or FPGA
                                  (Field Programmable Gate Array)
                                  initialization fault.
             powerSupply        - Power supply is out of range.
             chkSum             - CFP (C Form factor Pluggable) table checksum
                                  fault.
             refClkIn           - Loss of reference clock.
             txJitPllLol        - TX jitter PLL (Phase-Locked Loop) loss of
                                  lock.
             txCmuLol           - TX CMU (Clock Multiplier Unit) loss of lock.
             txLossFunc         - TX loss of signal functionality.
             hostTxLol          - TX IC (Integrated Circuit) lock indicator.
             netRxLol           - RX IC lock indicator.
             hostTxSkewHigh     - Host lane skew out of alignment.
             netTxTec           - Lane TX thermo-electric cooler fault.
             netTxWaveUnlk      - Lane wavelength unlocked.
             netTxLosf          - Lane TX loss of signal functionality
             netRxLos           - Lane RX loss of signal.
             netRxFifoErr       - Lane RX FIFO error.
             netRxTec           - Lane RX thermo-electric cooler fault.
             netTxOutOfAlign    - Out of alignment.
             netTxCmuLock       - CMU lock fault.
             netTxRefClk        - Reference clock fault.
             netRxModemSyncDet  - Modem sync detect fault.
             netRxModemLock     - Modem lock fault.
             hostTxLaneFifoErr  - Lane TX FIFO error.
             hostTxDeskew       - Deskew lock fault."
    SYNTAX      BITS {
                    overTemp          (0),
                    hwPost            (1),
                    pldFlashInit      (2),
                    powerSupply       (3),
                    chkSum            (4),
                    refClkIn          (5),
                    txJitPllLol       (6),
                    txCmuLol          (7),
                    txLossFunc        (8),
                    hostTxLol         (9),
                    netRxLol          (10), 
                    hostTxSkewHigh    (11),
                    netTxTec          (12),
                    netTxWaveUnlk     (13),
                    netTxLosf         (14),
                    netRxLos          (15),
                    netRxFifoErr      (16),
                    netRxTec          (17),
                    netTxOutOfAlign   (18),
                    netTxCmuLock      (19),
                    netTxRefClk       (20),
                    netRxModemSyncDet (21),
                    netRxModemLock    (22),
                    hostTxLaneFifoErr (23),
                    hostTxDeskew      (24)
                }

TmnxCoherentOpticalAlarm ::= TEXTUAL-CONVENTION
    STATUS      current
    DESCRIPTION
        "The TmnxCoherentOpticalAlarm specifies the type of coherent optical
         alarm currently active on the port. The values are logical ORs of
         TmnxCoherentOpticalDefectPoint.
                   
         moduleFault  - logical OR of defect points 'overTemp(1)',
                        'hwPost(2)', 'pldFlashInit(3)', 'powerSupply(4)',
                        'chkSum(5)'

         module       - logical OR of defect points 'refClkIn(6)',
                        'txJitPllLol(7)', 'txCmuLol(8)', 'txLossFunc(9)'

         netRx        - logical OR of defect points 'netRxLol(11)',
                        'netRxLos(16)', 'netRxFifoErr(17)', 'netRxTec(18)',
                        'netRxModemSyncDet(22)', 'netRxModemLock(23)'

         netTx        - logical OR of defect points 'netTxTec(13)',
                        'netTxWaveUnlk(14)', 'netTxLosf(15)',
                        'netTxOutOfAlign(19)', 'netTxCmuLock(20)',
                        'netTxRefClk(21)'

         hostTx       - logical OR of defect points 'hostTxLol(10)',
                        'hostTxSkewHigh(12)', 'hostTxLaneFifoErr(24)',
                        'hostTxDeskew(25)'"
    SYNTAX      BITS {
                    moduleFault (0),
                    module      (1),
                    netRx       (2),
                    netTx       (3),
                    hostTx      (4)
                }

TmnxPortLosReaction              ::= TEXTUAL-CONVENTION
    STATUS      current
    DESCRIPTION
        "The TmnxPortLosReaction specifies the type of action that is taken in
         the event of a Loss Of Signal (LOS). The valid modes are as follows:

                - none     - Specifies that the interface not be taken down on
                             crossing the optical LOS threshold.
                - squelch  - Specifies that the interface be taken down on
                             crossing the optical LOS threshold."
    SYNTAX      INTEGER {
                    none    (0),
                    squelch (1)
                }

TmnxSFFStatus                   ::= TEXTUAL-CONVENTION
    STATUS      current
    DESCRIPTION
        "The TmnxSFFStatus specifies the operational status of the small form
         factor (SFF) that is inserted into the port. If the SFF is removed
         from the port, the value of TmnxSFFStatus will be 'not-equipped (0)',
         otherwise 'operational (1)' if no failure is detected.
         
         A failure to read the SFF data will result in a 'read-error (2)',
         while corrupted information on the SFF will result in either
         'data-corrupt (3)', or 'ddm-corrupt (4)' if an SFF read results in
         invalid data or DDM information respectively.  An insertion of an
         unsupported SFF will result in 'unsupported (5)'.

         A trap will be raised if the value of TmnxSFFStatus indicates a
         failure; that is the TmnxSFFStatus is neither 'not-equipped (0)',
         nor 'operational (1)'."
    SYNTAX      INTEGER {
                     not-equipped (0),
                     operational  (1),
                     read-error   (2),
                     data-corrupt (3),
                     ddm-corrupt  (4),
                     unsupported  (5)
                }

TmnxHoldTime                    ::= TEXTUAL-CONVENTION
    STATUS      current
    DESCRIPTION
        "The TmnxHoldTime specifies the hold-timer for link up/down event
         dampening. This guards against reporting excessive interface
         transitions. This is implemented by not advertising subsequent
         transitions of the interface to upper layer protocols until the
         configured timer has expired."
     SYNTAX     Unsigned32

--%%%%%%%%%%%%%%%%%%%%%%%%%%%%%%%%%%%%%%%%%%%%%%%%%%%%%%%%%%%%%%%%%%%%%
--
--      IOM Port tables
--
tmnxPortTableLastChange   OBJECT-TYPE
    SYNTAX      TimeStamp
    MAX-ACCESS  read-only
    STATUS      current
    DESCRIPTION
        "The value of sysUpTime when the tmnxPortTable was last changed."
    ::= { tmnxPortObjs 1 }

tmnxPortTable OBJECT-TYPE
    SYNTAX      SEQUENCE OF TmnxPortEntry
    MAX-ACCESS  not-accessible
    STATUS      current
    DESCRIPTION
        "The port table has an entry for each port on each IOM card in each
         chassis in the TMNX system."
    ::= { tmnxPortObjs 2 }

tmnxPortEntry       OBJECT-TYPE
    SYNTAX      TmnxPortEntry
    MAX-ACCESS  not-accessible
    STATUS      current
    DESCRIPTION
        "Each row entry represents a port on a IOM card in a chassis in the
         system.  Entries cannot be created and deleted via SNMP SET
         operations.  Before an IOM tmnxMDAEntry can be deleted from the
         tmnxMDATable, its supported tmnxPortEntry rows must be in the proper
         state for removal."
    INDEX   { tmnxChassisIndex, tmnxPortPortID }
    ::= { tmnxPortTable 1 }

TmnxPortEntry ::=
    SEQUENCE {
        tmnxPortPortID                    TmnxPortID,
        tmnxPortLastChangeTime            TimeStamp,
        tmnxPortType                      TmnxPortType,
        tmnxPortClass                     TmnxPortClass,
        tmnxPortDescription               TItemLongDescription,
        tmnxPortName                      TNamedItemOrEmpty,
        tmnxPortAlias                     TNamedItemOrEmpty,
        tmnxPortUserAssignedMac           TruthValue,
        tmnxPortMacAddress                MacAddress,
        tmnxPortHwMacAddress              MacAddress,
        tmnxPortMode                      INTEGER,
        tmnxPortEncapType                 TmnxPortEncapType,
        tmnxPortLagId                     Unsigned32,
        tmnxPortHoldTimeUp                TmnxHoldTime,
        tmnxPortHoldTimeDown              TmnxHoldTime,
        tmnxPortUpProtocols               BITS,
        tmnxPortConnectorType             TmnxPortConnectorType,
        tmnxPortTransceiverType           INTEGER,
        tmnxPortTransceiverCode           BITS,
        tmnxPortTransceiverLaserWaveLen   Unsigned32,
        tmnxPortTransceiverDiagCapable    INTEGER,
        tmnxPortTransceiverModelNumber    TNamedItemOrEmpty,
        tmnxPortSFPConnectorCode          INTEGER,
        tmnxPortSFPVendorOUI              Unsigned32,
        tmnxPortSFPVendorManufactureDate  DateAndTime,
        tmnxPortSFPMedia                  INTEGER,
        tmnxPortSFPEquipped               TruthValue,
        tmnxPortEquipped                  TruthValue,
        tmnxPortLinkStatus                TruthValue,
        tmnxPortAdminStatus               TmnxPortAdminStatus,
        tmnxPortOperStatus                TmnxPortOperStatus,
        tmnxPortState                     TmnxPortState,
        tmnxPortPrevState                 TmnxPortState,
        tmnxPortNumAlarms                 Unsigned32,
        tmnxPortAlarmState                TmnxAlarmState,
        tmnxPortLastAlarmEvent            RowPointer,
        tmnxPortClearAlarms               TmnxActionType,
        tmnxPortSFPVendorSerialNum        TNamedItemOrEmpty,
        tmnxPortSFPVendorPartNum          TNamedItemOrEmpty,
        tmnxPortLastStateChanged          TimeStamp,
        tmnxPortNumChannels               Unsigned32,
        tmnxPortNetworkEgrQueues          TNamedItemOrEmpty,
        tmnxPortBundleNumber              INTEGER,
        tmnxPortIsLeaf                    TruthValue,
        tmnxPortChanType                  TmnxMDAChanType,
        tmnxPortParentPortID              TmnxPortID,
        tmnxPortOpticalCompliance         OCTET STRING,
        tmnxPortLoadBalanceAlgorithm      INTEGER,
        tmnxPortEgrPortSchedPlcy          TNamedItemOrEmpty,
        tmnxPortLastClearedTime           TimeStamp,
        tmnxPortEgrHsmdaSchedPlcy         TNamedItemOrEmpty,
        tmnxPortIngNamedPoolPlcy          TNamedItemOrEmpty,
        tmnxPortEgrNamedPoolPlcy          TNamedItemOrEmpty,
        tmnxPortIngPoolPercentRate        Unsigned32,
        tmnxPortEgrPoolPercentRate        Unsigned32,
        tmnxPortDDMEventSuppression       TruthValue,
        tmnxPortSFPStatus                 TmnxSFFStatus,
        tmnxPortReasonDownFlags           BITS,
        tmnxPortSSMRxQualityLevel         INTEGER,
        tmnxPortDwdmLaserChannel          TmnxOpticalDwdmChannel,
        tmnxPortOtuCapable                TruthValue,
        tmnxPortWaveTrackerCapable        TruthValue,
        tmnxPortHybridIngAccessWeight     Unsigned32,
        tmnxPortHybridIngNetworkWeight    Unsigned32,
        tmnxPortHybridEgrAccessWeight     Unsigned32,
        tmnxPortHybridEgrNetworkWeight    Unsigned32,
        tmnxPortDwdmRxDtvAdjustEnable     TruthValue,
        tmnxPortDwdmRxDtvDacPercent       Unsigned32,
        tmnxPortInterfaceGroupHandlerIdx  Unsigned32,
        tmnxPortHoldTimeUnits             INTEGER,
        tmnxPortLinkLengthInfo            OCTET STRING,
        tmnxPortSFPNumLanes               Unsigned32,
        tmnxPortPhysStateChangeCount      Counter32
    }

tmnxPortPortID          OBJECT-TYPE
    SYNTAX      TmnxPortID
    MAX-ACCESS  not-accessible
    STATUS      current
    DESCRIPTION
        "tmnxPortPortID is an index into this table. It maps this port to its
         entry in the mib-2 interfaces table."
    ::= { tmnxPortEntry 1 }

tmnxPortLastChangeTime    OBJECT-TYPE
    SYNTAX      TimeStamp
    MAX-ACCESS  read-only
    STATUS      current
    DESCRIPTION
        "The tmnxPortLastChangeTime variable contains the sysUpTime
         value of the most recently modified writable variable in the
         tmnxPortEntry row for this port."
    ::= { tmnxPortEntry 2 }

tmnxPortType        OBJECT-TYPE
    SYNTAX      TmnxPortType
    MAX-ACCESS  read-only
    STATUS      current
    DESCRIPTION
        "The type of port or optical pack installed."
    ::= { tmnxPortEntry 3 }

tmnxPortClass        OBJECT-TYPE
    SYNTAX      TmnxPortClass
    MAX-ACCESS  read-only
    STATUS      current
    DESCRIPTION
        "The class of port or optical pack installed.  This can be
         derived from tmnxPortType."
    ::= { tmnxPortEntry 4 }

tmnxPortDescription     OBJECT-TYPE
    SYNTAX      TItemLongDescription
    MAX-ACCESS  read-write
    STATUS      current
    DESCRIPTION
        "A textual string containing user supplied information about the
         interface."
    DEFVAL { ''H }
    ::= { tmnxPortEntry 5 }

tmnxPortName        OBJECT-TYPE
    SYNTAX      TNamedItemOrEmpty
    MAX-ACCESS  read-only
    STATUS      current
    DESCRIPTION
        "The textual name of the interface.  The value of this
         object should be the name of the interface as assigned by
         the local device and should be suitable for use in commands
         entered at the device's `console'.  This might be a text
         name, such as `le0' or 'sys171-2/1."
    ::= { tmnxPortEntry 6 }

tmnxPortAlias        OBJECT-TYPE
    SYNTAX      TNamedItemOrEmpty
    MAX-ACCESS  read-write
    STATUS      current
    DESCRIPTION
        "This object is an 'alias' name for the interface as
         specified by a network manager, and provides a non-volatile
         'handle' for the interface.

         On the first instantiation of an interface, the value of
         tmnxPortAlias associated with that interface is the zero-length
         string.  As and when a value is written into an instance of
         tmnxPortAlias through a network management set operation, then the
         agent must retain the supplied value in the tmnxPortAlias instance
         associated with the same interface for as long as that
         interface remains instantiated, including across all re-
         initializations/reboots of the network management system."
    DEFVAL { ''H }
    ::= { tmnxPortEntry 7 }

tmnxPortUserAssignedMac OBJECT-TYPE
    SYNTAX      TruthValue
    MAX-ACCESS  read-only
    STATUS      current
    DESCRIPTION
        "When tmnxPortUserAssignedMac has a value of 'true', the value of
         tmnxPortMacAddress has been explicitly assigned by a SNMP SET
         request.  When tmnxPortUserAssignedMac is set to 'false',
         tmnxPortMacAddress returns the system assigned MAC address."
    DEFVAL { false }
    ::= { tmnxPortEntry 8 }

tmnxPortMacAddress  OBJECT-TYPE
    SYNTAX      MacAddress
    MAX-ACCESS  read-write
    STATUS      current
    DESCRIPTION
        "When tmnxPortUserAssignedMac has a value of 'true',
         tmnxPortMacAddress has the value that has been explicitly
         assigned by a SNMP SET request.  When tmnxPortUserAssignedMac
         has a value of 'false', tmnxPortMacAddress returns the same
         value as tmnxPortHwMacAddress, the hardware or system assigned
         MAC address.  When tmnxPortMacAddress is modified by a SET
         request, the agent sets tmnxPortUserAssignedMac to 'true'.

         Setting tmnxPortMacAddress to all zeros causes the agent to
         revert to using the default tmnxPortHwMacAddress and also to
         return tmnxPortUserAssignedMac as 'false'."
    DEFVAL { '000000000000'h }
    ::= { tmnxPortEntry 9 }

tmnxPortHwMacAddress  OBJECT-TYPE
    SYNTAX      MacAddress
    MAX-ACCESS  read-only
    STATUS      current
    DESCRIPTION
        "The interface's hardware or system assigned MAC address at its
         protocol sub-layer.  When tmnxPortUserAssignedMac has a value of
         'true', the value of tmnxPortMacAddress is used instead of
         tmnxPortHwMacAddress.

         In the case of a pre-provisioned port that is not yet physically
         in the system, the MAC address may not be known.  In this case
         a MAC address of all zeros is returned."
    ::= { tmnxPortEntry 10 }

tmnxPortMode        OBJECT-TYPE
    SYNTAX      INTEGER {
                    undefined (0),
                    access (1),
                    network (2),
                    hybrid (3)
                }
    MAX-ACCESS  read-write
    STATUS      current
    DESCRIPTION
        "The tmnxPortMode variable indicates if the interface on this port
         is configured as a service access port, a network port or a 
         hybrid port.  Once the port's mode has been configured for 'access', 
         'network' or 'hybrid' mode, multiple services may be configured 
         on the port.

         tmnxPortEncapType is defaulted based on MDA type and
         Port Mode according to the following table:

         MDA Type           Port Mode             tmnxPortEncapType
         ---------------------------------------------------------
         ATM                access                atmEncap

         CEM                access                cemEncap

         Ethernet           access                nullEncap
                            network               nullEncap
                            hybrid                qEncap

         ISA
           isa-aa           network               nullEncap
           isa-bb           access                qinqEncap
                            network               qEncap
           isa-ipsec        access                qEncap
           isa-video        access                qEncap

         Sonet/SDH          access                bcpNullEncap
                            network               pppAutoEncap

         TDM                access                bcpNullEncap
                            network               pppAutoEncap

         VSM
            vsm-cca         access                qEncap
            vsm-cca         network               qEncap
         "         
    ::= { tmnxPortEntry 11 }

tmnxPortEncapType   OBJECT-TYPE
    SYNTAX      TmnxPortEncapType
    MAX-ACCESS  read-write
    STATUS      current
    DESCRIPTION
        "The value of tmnxPortEncapType specifies the type of encapsulation 
         protocol configured on this port's network interface.  

         tmnxPortEncapType is set to 'unknown' for physical SONET/SDH and
         TDM ports.

         If the port mode equals 'hybrid', tmnxPortEncapType can only
         be set to 'qEncap' or 'qinqEncap'.
         "
    ::= { tmnxPortEntry 12 }

tmnxPortLagId OBJECT-TYPE
    SYNTAX      Unsigned32 (0..200)
    MAX-ACCESS  read-write
    STATUS      current
    DESCRIPTION
        "The value of tmnxPortLagId indicates which LAG or multi-link trunk
         (MLT) this port is assigned to. If this port is not associated
         with any LAG, this value will be set to zero(0).

         The maximum value of this object is '64', when the value of
         TIMETRA-CHASSIS-MIB::tmnxChassisType is '5' (ESS-1/SR-1)."
    DEFVAL { 0 }
    ::= { tmnxPortEntry 13 }

tmnxPortHoldTimeUp  OBJECT-TYPE
    SYNTAX      TmnxHoldTime (0..3600000)
    MAX-ACCESS  read-write
    STATUS      current
    DESCRIPTION
        "The value of tmnxPortHoldTimeUp is used to configure the
         hold-timer for link up event dampening.

         A value of zero (0) indicates that an up transition is reported
         immediately.  The value of tmnxPortHoldTimeUp is not applicable
         when tmnxPortClass has a value of 'sonet (5)' or tmnxPortType has a
         value of 'portTypeDS3E3'. In these cases, tmnxSonetHoldTimeUp and
         tmnxDS3HoldTimeUp are used, respectively.

         tmnxPortHoldTimeUp is measured in units as specified by
         tmnxPortHoldTimeUnits. If the value of tmnxPortHoldTimeUnits is
         'centisenconds(1)', the value must be specified in multiples of 5.
         The maximum hold-time for this object is 10 hours, regardless of the
         units specified. Attempts to change the maximum value to a hold-time
         longer than 10 hours will result in an 'inconsistentValue' error."
    DEFVAL { 0 }
    ::= { tmnxPortEntry 14 }

tmnxPortHoldTimeDown    OBJECT-TYPE
    SYNTAX      TmnxHoldTime (0..3600000)
    MAX-ACCESS  read-write
    STATUS      current
    DESCRIPTION
        "The value of tmnxPortHoldTimeDown is used to configure the
         hold-timer for link down event dampening.

         A value of zero (0) indicates that a down transition is reported
         immediately. The value of tmnxPortHoldTimeDown is not applicable
         when tmnxPortClass has a value of 'sonet (5)' or tmnxPortType has a
         value of 'portTypeDS3E3'. In these cases, tmnxSonetHoldTimeDown and
         tmnxDS3HoldTimeDown are used, respectively.

         tmnxPortHoldTimeDown is measured in units as specified by
         tmnxPortHoldTimeUnits. If the value of tmnxPortHoldTimeUnits is
         'centisenconds(1)', the value must be specified in multiples of 5.
         The maximum hold-time for this object is 10 hours, regardless of the
         units specified. Attempts to change the maximum value to a hold-time
         longer than 10 hours will result in an 'inconsistentValue' error."
    DEFVAL { 0 }
    ::= { tmnxPortEntry 15 }

tmnxPortUpProtocols     OBJECT-TYPE
    SYNTAX      BITS {
                    portUpIpv4  (0),
                    portUpMpls  (1),
                    portUpBcp   (2),
                    portUpIso   (3),
                    portUpFr    (4),
                    portUpAtm   (5),
                    portUpChdlc (6),
                    portUpIma   (7),
                    portUpIpv6  (8)
                }
    MAX-ACCESS  read-only
    STATUS      current
    DESCRIPTION
        "The tmnxPortUpProtocols variable is a bitmap that indicates what
         protocols can be used on this port type."
    ::= { tmnxPortEntry 16 }

tmnxPortConnectorType       OBJECT-TYPE
    SYNTAX      TmnxPortConnectorType
    MAX-ACCESS  read-only
    STATUS      current
    DESCRIPTION
        "The type of connector installed on this port."
    ::= { tmnxPortEntry 17 }

tmnxPortTransceiverType       OBJECT-TYPE
    SYNTAX      INTEGER {
                    unknown(0),
                    gbic(1),
                    moduleConnectorSolderedToMotherboard(2),
                    sfpTransceiver(3),
                    xbiTransceiver(4),
                    xenpakTransceiver(5),
                    xfpTransceiver(6),
                    xffTransceiver(7),
                    xfpeTransceiver(8),
                    xpakTransceiver(9),
                    x2Transceiver(10),
                    dwdmSfpTransceiver(11),
                    qsfpTransceiver(12),
                    qsfpPlusTransceiver(13),
                    cfpTransceiver(14),
                    cxpTransceiver(15),
                    oifMsa100gLh(16),
                    cfp2Transceiver(17)
                }
    MAX-ACCESS  read-only
    STATUS      current
    DESCRIPTION
        "Type of the transceiver."
    ::= { tmnxPortEntry 25 }

tmnxPortTransceiverCode       OBJECT-TYPE
    SYNTAX      BITS{
                    unknown(0),
                    oc48-longreach(1),
                    oc48-intermediatereach(2),
                    oc48-shortreach(3),
                    oc12-singlemodelongreach(4),
                    oc12-singlemodeinterreach(5),
                    oc12-multimodeshortreach(6),
                    oc3-singlemodelongreach(7),
                    oc3-singlemodeinterreach(8),
                    oc3-multi-modeshortreach(9),
                    gige-1000base-t(10),
                    gige-1000base-cx(11),
                    gige-1000base-lx(12),
                    gige-1000base-sx(13),
                    faste-100base-mm-fx(14),
                    faste-100base-sm-fx(15),
                    xgige-10gbase-sr(16),
                    xgige-10gbase-lr(17),
                    xgige-10gbase-er(18),
                    xgige-10gbase-sw(19),
                    xgige-10gbase-lw(20),
                    xgige-10gbase-ew(21)
                }
    MAX-ACCESS  read-only
    STATUS      obsolete
    DESCRIPTION
        "The code for the transmission media.

         tmnxPortOpticalCompliance is used instead of
         tmnxPortTransceiverCode.tmnxPortOpticalCompliance  contains the
         same information and is defined by an industry standard."
    ::= { tmnxPortEntry 26 }

tmnxPortTransceiverLaserWaveLen       OBJECT-TYPE
    SYNTAX      Unsigned32
    MAX-ACCESS  read-only
    STATUS      current
    DESCRIPTION
        "The light wavelength transmitted by the transceiver's laser.
         A value of zero indicates that the port is not equipped with
         the transceiver.

         A value in the range of 1 to 2000 indicates that the units are in
         nano-meters (nm). A value in the range of 850000 to 2000000
         indicates that the units are in pico-meters (pm)."
    ::= { tmnxPortEntry 27 }

tmnxPortTransceiverDiagCapable    OBJECT-TYPE
    SYNTAX      INTEGER {
                    notApplicable(0),
                    true(1),
                    false(2)
                }
    MAX-ACCESS  read-only
    STATUS      current
    DESCRIPTION
        "Indicates if the transceiver is capable of doing diagnostics."
    ::= { tmnxPortEntry 28 }

tmnxPortTransceiverModelNumber OBJECT-TYPE
    SYNTAX       TNamedItemOrEmpty
    MAX-ACCESS   read-only
    STATUS       current
    DESCRIPTION
        "The value of tmnxPortTransceiverModelNumber indicates the model
         information for the transceiver, as read from the transceiver
         EEPROM.  For example, the string may contain the Alcatel-Lucent
         part number and CLEI for the transceiver.

         The string is expected to contain printable ASCII characters, but
         unprintable ASCII characters read from the EEPROM are not
         filtered out."
    ::= { tmnxPortEntry 29 }

tmnxPortSFPConnectorCode       OBJECT-TYPE
    SYNTAX      INTEGER {
                    unknown(0),
                    sc(1),
                    fiberChannel-Style1-CopperConnector(2),
                    fiberChannel-Style2-CopperConnector(3),
                    bncortnc(4),
                    fiberChannelCoaxialHeaders(5),
                    fiberJack(6),
                    lc(7),
                    mt-rj(8),
                    mu(9),
                    sg(10),
                    opticalPigtail(11),
                    hssdcII(32),
                    copperPigtail(33),
                    opticalTransceiver(51),
                    copperGigE(128)
                }
    MAX-ACCESS  read-only
    STATUS      current
    DESCRIPTION
        "The external connector provided on the interface."
    ::= { tmnxPortEntry 30 }

tmnxPortSFPVendorOUI       OBJECT-TYPE
    SYNTAX      Unsigned32
    MAX-ACCESS  read-only
    STATUS      current
    DESCRIPTION
        "The vendor organizationally unique identifier field (OUI)
         contains the IEEE company identifier for the vendor.
         A value of all zero indicates that the vendor OUI
         is unspecified."
    ::= { tmnxPortEntry 31 }

tmnxPortSFPVendorManufactureDate       OBJECT-TYPE
    SYNTAX      DateAndTime
    MAX-ACCESS  read-only
    STATUS      current
    DESCRIPTION
        "The vendor's date code."
    ::= { tmnxPortEntry 32 }

tmnxPortSFPMedia       OBJECT-TYPE
    SYNTAX      INTEGER {
                    notApplicable(0),
                    ethernet(1),
                    sonetsdh(2)
                }
    MAX-ACCESS  read-only
    STATUS      current
    DESCRIPTION
        "The value of tmnxPortSFPMedia indicates the media supported for the
         SFF (Small Form-Factor)."
    ::= { tmnxPortEntry 33 }

tmnxPortSFPEquipped    OBJECT-TYPE
    SYNTAX      TruthValue
    MAX-ACCESS  read-only
    STATUS      current
    DESCRIPTION
        "The value of tmnxPortSFPEquipped indicates if the SFF is equipped."
    ::= { tmnxPortEntry 34 }

tmnxPortEquipped    OBJECT-TYPE
    SYNTAX      TruthValue
    MAX-ACCESS  read-only
    STATUS      current
    DESCRIPTION
        "Indicates if there is an optics pack installed in this
         port or not."
    ::= { tmnxPortEntry 35 }

tmnxPortLinkStatus  OBJECT-TYPE
    SYNTAX      TruthValue
    MAX-ACCESS  read-only
    STATUS      current
    DESCRIPTION
        "Indicates whether or not the port has a physical link."
    ::= { tmnxPortEntry 36 }

tmnxPortAdminStatus  OBJECT-TYPE
    SYNTAX      TmnxPortAdminStatus
    MAX-ACCESS  read-write
    STATUS      current
    DESCRIPTION
        "The desired administrative status of this port.
        
         When tmnxPortType references a row in the tmnxPortTypeTable
         where tmnxPortTypeName is the octet string 'Application 
         Assurance', an attempt to set tmnxPortAdminStatus to a 
         value other than 'inService' results in an 
         'inconsistentValue' error."
    DEFVAL { inService }
    ::= { tmnxPortEntry 37 }

tmnxPortOperStatus   OBJECT-TYPE
    SYNTAX      TmnxPortOperStatus
    MAX-ACCESS  read-only
    STATUS      current
    DESCRIPTION
        "The current operational status of this port."
    ::= { tmnxPortEntry 38 }

tmnxPortState   OBJECT-TYPE
    SYNTAX  TmnxPortState
    MAX-ACCESS  read-only
    STATUS  current
    DESCRIPTION
        "The state level of this port.  A value of 'none' indicates
         the port is either in its initial creation state or is
         just about to be deleted.  A value of 'ghost' represents
         a port that is not physically present.  This state may
         represent a pre-provisioned port.  A value of 'linkDown'
         represents a port that is physically present but does
         not have a link.  The 'linkUp' state represents a port
         that is physically present and has physical link present.
         A port in 'up' state is ready to pass some kinds of traffic.
         The tmnxPortUpProtocols variable indicates the actual type(s)
         of traffic can be passed on this 'up' link."
    ::= { tmnxPortEntry 39 }

tmnxPortPrevState   OBJECT-TYPE
    SYNTAX      TmnxPortState
    MAX-ACCESS  read-only
    STATUS      current
    DESCRIPTION
        "The tmnxPortPrevState indicates the state level that the port
         transitioned from into the current tmnxPortState level."
    ::= { tmnxPortEntry 40 }

tmnxPortNumAlarms   OBJECT-TYPE
    SYNTAX      Unsigned32
    MAX-ACCESS  read-only
    STATUS      current
    DESCRIPTION
        "The number of alarms currently outstanding on this port."
    ::= { tmnxPortEntry 41 }

tmnxPortAlarmState    OBJECT-TYPE
    SYNTAX  TmnxAlarmState
    MAX-ACCESS  read-only
    STATUS  current
    DESCRIPTION
        "The value of tmnxPortAlarmState indicates the current alarm
         state for this port."
    ::= { tmnxPortEntry 42 }

tmnxPortLastAlarmEvent    OBJECT-TYPE
    SYNTAX  RowPointer
    MAX-ACCESS  read-only
    STATUS  current
    DESCRIPTION
        "The value of tmnxPortLastAlarmEvent indicates the object name
         and instance value that points to the row entry in the ALARM-MIB
         containing the most recent alarm associated with this port.  If
         tmnxPortAlarmState has a value of 'alarmCleared(2)', the
         most recent alarm event will be in the cleared alarm table.  If it has
         a value of 'alarmActive(1)', the most recent alarm event will be in
         the active alarm table.  If the value of tmnxPortLastAlarmEvent is
         '0.0', either no port alarm events have occurred since the system was
         last booted, or the last port alarm event has aged out and its entry
         is no longer available in the ALARM-MIB tables."
    ::= { tmnxPortEntry 43 }

tmnxPortClearAlarms OBJECT-TYPE
    SYNTAX      TmnxActionType
    MAX-ACCESS  read-write
    STATUS      current
    DESCRIPTION
        "Setting this action variable causes all the alarms
         associated with this port to be moved from the current
         alarm log to the history alarm log. Primarily meant
         for use in development.  This object will most likely
         be removed from the MIB before product release."
    DEFVAL { notApplicable }
    ::= { tmnxPortEntry 44 }

tmnxPortSFPVendorSerialNum       OBJECT-TYPE
    SYNTAX      TNamedItemOrEmpty
    MAX-ACCESS  read-only
    STATUS      current
    DESCRIPTION
        "The value of tmnxPortSFPVendorSerialNum indicates the
         transceiver's vendor serial number in ASCII characters,
         as read from the transceiver EEPROM.

         An empty string indicates the vendor serial number is
         unspecified.

         The string is expected to contain printable ASCII characters,
         but unprintable ASCII characters read from the EEPROM are not
         filtered out."
    ::= { tmnxPortEntry 45 }

tmnxPortSFPVendorPartNum       OBJECT-TYPE
    SYNTAX      TNamedItemOrEmpty
    MAX-ACCESS  read-only
    STATUS      current
    DESCRIPTION
        "The value of tmnxPortSFPVendorPartNum indicates the
         transceiver's vendor part number (or product name) in ASCII
         characters, as read from the transceiver EEPROM.

         An empty string indicates the vendor part number is
         unspecified.

         The string is expected to contain printable ASCII characters, but
         unprintable ASCII characters read from the EEPROM are not
         filtered out."
    ::= { tmnxPortEntry 46 }

tmnxPortLastStateChanged       OBJECT-TYPE
    SYNTAX      TimeStamp
    MAX-ACCESS  read-only
    STATUS      current
    DESCRIPTION
        "The tmnxPortLastStateChanged variable contains the
         value of the sysUpTime the last time the operational status
         of the port changed state."
    ::= { tmnxPortEntry 48 }

tmnxPortNumChannels       OBJECT-TYPE
    SYNTAX      Unsigned32
    MAX-ACCESS  read-only
    STATUS      current
    DESCRIPTION
        "For SONET/SDH paths or TDM channels, tmnxPortNumChannels
         contains the number of possible immediate children. For
         leaf paths or channels, the value of this object will be zero.
         For SONET/SDH or TDM physical ports, tmnxPortNumChannels
         contains the total number of channels on the physical port.
         For all other entries in the tmnxPortTable, the value of
         this object will be zero."
    ::= { tmnxPortEntry 49 }

tmnxPortNetworkEgrQueues       OBJECT-TYPE
    SYNTAX      TNamedItemOrEmpty
    MAX-ACCESS  read-write
    STATUS      current
    DESCRIPTION
        "tmnxPortNetworkEgrQueues contains the network egress queue policy
        if the tmnxPortMode is network. Otherwise this object has no
        significance."
    ::= { tmnxPortEntry 50 }

tmnxPortBundleNumber OBJECT-TYPE
    SYNTAX      INTEGER (0..2000)
    MAX-ACCESS  read-only
    STATUS      current
    DESCRIPTION
        "tmnxPortBundleNumber identifies the bundle for which this port is
         a member. If this port is not a member of any bundle, the value of
         tmnxPortBundleNumber will be zero."
    ::= { tmnxPortEntry 51 }

tmnxPortIsLeaf OBJECT-TYPE
    SYNTAX      TruthValue
    MAX-ACCESS  read-only
    STATUS      current
    DESCRIPTION
        "tmnxPortIsLeaf is applicable only when the 'isSonet' and/or 'isTDM'
         bits in TIMETRA-CHASSIS-MIB:tmnxMDACapabilities are set.
         When the value of this object is 'true', it indicates that the channel
         is capable of passing traffic.

         The value of this object is 'false' for:
         1. Physical ports on SONET/TDM MDA's
         2. Intermediate channels on a channelized MDA
         3. Leaf channels which belong to a bundle

         For ports on Ethernet MDA's or for LAG ports, the value of this object
         will be 'false'."
    ::= { tmnxPortEntry 52 }

tmnxPortChanType      OBJECT-TYPE
    SYNTAX      TmnxMDAChanType
    MAX-ACCESS  read-only
    STATUS      current
    DESCRIPTION
        "tmnxPortChanType is applicable only when the 'isSonet' and/or 'isTDM'
         bits in TIMETRA-CHASSIS-MIB:tmnxMDACapabilities are set. It indicates
         the type of the channel.
         For ports on Ethernet MDA's, the value of this object will
         be 'unknown'."
    ::= { tmnxPortEntry 53 }

tmnxPortParentPortID      OBJECT-TYPE
    SYNTAX      TmnxPortID
    MAX-ACCESS  read-only
    STATUS      current
    DESCRIPTION
        "tmnxPortParentPortID  is applicable only when the 'isSonet'
         and/or 'isTDM' bits in TIMETRA-CHASSIS-MIB:tmnxMDACapabilities are set.
         For SONET or TDM channel, it indicates the port ID of its parent
         channel or port."
    ::= { tmnxPortEntry 54 }

tmnxPortOpticalCompliance   OBJECT-TYPE
    SYNTAX      OCTET STRING (SIZE (8))
    MAX-ACCESS  read-only
    STATUS      current
    DESCRIPTION
        "tmnxPortOpticalCompliance is applicable only when the
         tmnxPortSFPEquipped is set to 'true'. The value of
         tmnxPortOpticalCompliance indicates the 8 bytes of optical compliance
         bits stored in SFF EEPROMs."
    ::= { tmnxPortEntry 55 }

tmnxPortLoadBalanceAlgorithm  OBJECT-TYPE
    SYNTAX      INTEGER {
                    notApplicable (0),
                    default (1),
                    includeL4 (2),
                    excludeL4 (3)
                }
    MAX-ACCESS  read-write
    STATUS      current
    DESCRIPTION
        "The value of tmnxPortLoadBalanceAlgorithm specifies the load
         balancing algorithm to be used on this port. When the
         value is 'includeL4', the src and dst port are used in the
         hashing algorithm. When it's 'excludeL4', they are not included.
         When the value is 'default', the port inherits the global settings
         in tmnxL4LoadBalancing. The value is 'notApplicable' for ports that
         do not pass any traffic. An attempt to modify this object when it is
         set to 'notApplicable' will return an inconsistentValue error."
    DEFVAL { default }
    ::= { tmnxPortEntry 56 }

tmnxPortEgrPortSchedPlcy  OBJECT-TYPE
    SYNTAX      TNamedItemOrEmpty
    MAX-ACCESS  read-write
    STATUS      current
    DESCRIPTION
        "The value of tmnxPortEgrPortSchedPlcy specifies the egress QoS
         port-scheduler policy for this port. This object must correspond
         to the index of a row in TIMETRA-QOS-MIB::tPortSchedulerPlcyTable.

         A non-empty value for tmnxPortEgrPortSchedPlcy is only valid when the
         tmnxMDAAssignedType is a non-HSMDA MDA Type. Attempting to set
         tmnxPortEgrPortSchedPlcy to a non-empty string when the
         tmnxMDAAssignedType is a HSMDA MDA Type will return
         an 'inconsistentValue' error."
    DEFVAL { "" }
    ::= { tmnxPortEntry 57 }

tmnxPortLastClearedTime  OBJECT-TYPE
    SYNTAX      TimeStamp
    MAX-ACCESS  read-only
    STATUS      current
    DESCRIPTION
        "The value of tmnxPortLastClearedTime indicates the sysUpTime
         when the counters in the IF-MIB:ifTable were last cleared."
    ::= { tmnxPortEntry 58 }

 tmnxPortEgrHsmdaSchedPlcy  OBJECT-TYPE
   SYNTAX      TNamedItemOrEmpty
   MAX-ACCESS  read-write
   STATUS      current
   DESCRIPTION
       "The value of tmnxPortEgrHsmdaSchedPlcy specifies the egress QoS
        Hsmda-scheduler policy for this port. This object must correspond
        to the index of a row in TIMETRA-QOS-MIB::tHsmdaSchedulerPlcyTable,
        otherwise an 'inconsistentValue' error will be returned.

        When the tmnxMDAAssignedType is a non-HSMDA MDA Type, the value
        for tmnxPortEgrHsmdaSchedPlcy will be ignored. If the
        tmnxMDAAssignedType is a HSMDA MDA Type, the default for this
        object will be the string 'default'."
   DEFVAL { "" }
   ::= { tmnxPortEntry 59 }

tmnxPortIngNamedPoolPlcy OBJECT-TYPE
    SYNTAX      TNamedItemOrEmpty
    MAX-ACCESS  read-write
    STATUS      current
    DESCRIPTION
        "The value of tmnxPortIngNamedPoolPlcy specifies a named pool
         policy associated with an port ingress context. The policy
         governs the way named pools are created at the port level."
    DEFVAL { ''H }
    ::= { tmnxPortEntry 60 }

tmnxPortEgrNamedPoolPlcy OBJECT-TYPE
    SYNTAX      TNamedItemOrEmpty
    MAX-ACCESS  read-write
    STATUS      current
    DESCRIPTION
        "The value of tmnxPortEgrNamedPoolPlcy specifies a named pool
         policy associated with an port egress context. The policy
         governs the way named pools are created at the port level."
    DEFVAL { ''H }
    ::= { tmnxPortEntry 61 }

tmnxPortIngPoolPercentRate OBJECT-TYPE
    SYNTAX      Unsigned32 (1..1000)
    MAX-ACCESS  read-write
    STATUS      current
    DESCRIPTION
        "The value of tmnxPortIngPoolPercentRate specifies increment or
         decrement of the active bandwidth associated with the ingress port.
         This active bandwidth affects the amount of ingress buffer space
         managed by the port."
    DEFVAL { 100 }
    ::= { tmnxPortEntry 62 }

tmnxPortEgrPoolPercentRate OBJECT-TYPE
    SYNTAX      Unsigned32 (1..1000)
    MAX-ACCESS  read-write
    STATUS      current
    DESCRIPTION
        "The value of tmnxPortEgrPoolPercentRate specifies increment or
         decrement of the active bandwidth associated with the egress port.
         This active bandwidth affects the amount of egress buffer space
         managed by the port.
         
         The table below summarizes cases when the default value of 
         tmnxPortEgrPoolPercentRate differs from 100.
         
             port behavior          default value
             ------------------------------------
             ISA-AA /to-sub                  1000
             ISA-AA /fm-sub                   500
         "
    DEFVAL { 100 }
    ::= { tmnxPortEntry 63 }

tmnxPortDDMEventSuppression OBJECT-TYPE
    SYNTAX      TruthValue
    MAX-ACCESS  read-write
    STATUS      current
    DESCRIPTION
        "The value of tmnxPortDDMEventSuppression specifies whether or not an
         inserted SFF that supports Digital Diagnostic Monitoring
         raises traps and events (false) or suppresses all notifications
         (true)."
    DEFVAL { false }
    ::= { tmnxPortEntry 64 }

tmnxPortSFPStatus           OBJECT-TYPE
    SYNTAX      TmnxSFFStatus
    MAX-ACCESS  read-only
    STATUS      current
    DESCRIPTION
        "The value of tmnxPortSFPStatus indicates the operational status of
         the inserted SFF. If tmnxPortSFPEquipped is false, the
         tmnxPortSFPStatus will be 'not-equipped (0)', otherwise
         'operational (1)' if no failure is detected."
    DEFVAL { not-equipped }
    ::= { tmnxPortEntry 65 }

tmnxPortReasonDownFlags          OBJECT-TYPE
    SYNTAX      BITS {
                   unknown              (0),
                   linklossFwd          (1),
                   lagMemberPortStandby (2),
                   ethCfmFault          (3),
                   opticalTuning        (4),
                   channelOutOfRange    (5),
                   channelNotConfigured (6),
                   crcError             (7),
                   internalMacTxError   (8),
                   efmOamDown           (9),
                   symMonError         (10)
                }
    MAX-ACCESS  read-only
    STATUS      current
    DESCRIPTION
        "The tmnxPortReasonDownFlags indicates why a port may
        be in the operationally 'down' state. The following reasons are
        detected through this object:
                unknown(0)              - Unspecified (or unknown)
                linklossFwd(1)          - A sap using this port has an LLF
                                          operational status set to 'fault'
                lagMemberPortStandby(2) - A lag using this port as a member
                                          port has set the member port to
                                          'standby' while configured to keep
                                          standby member ports down.
                ethCfmFault(3)          - A facility MEP bound to this port
                                          has its dot1agCfmMepHighestPrDefect
                                          set to a value other than 'none (0)'.
                opticalTuning(4)        - The DWDM optical receive signal is 
                                          undergoing tuning and analysis by
                                          control algorithms to find the
                                          optimal settings.
                channelOutOfRange(5)    - The configured DWDM optical channel
                                          is out of range for the equipped
                                          tunable optical interface.
                channelNotConfigured(6) - The DWDM optical channel is not
                                          configured for the equipped
                                          tunable optical interface.
                crcError(7)             - CRC errors on the port exceeded the
                                          configured threshold.
                internalMacTxError(8)   - An internal MAC tx error was detected
                                          on the port.
                efmOamDown(9)           - dot3OamOperStatus is not
                                          'operational'.
                symMonError(10)         - Symbol Monitor Errors on the port
                                          exceeded the configured threshold."
    ::= { tmnxPortEntry 66 }

tmnxPortSSMRxQualityLevel   OBJECT-TYPE
    SYNTAX      INTEGER {
                    unknown (0),
                    prs     (1),
                    stu     (2),
                    st2     (3),
                    tnc     (4),
                    st3e    (5),
                    st3     (6),
                    smc     (7),
                    st4     (8),
                    dus     (9),
                    prc     (10),
                    ssua    (11),
                    ssub    (12),
                    sec     (13),
                    dnu     (14),
                    inv     (15),
                    pno     (16),
                    eec1    (17),
                    eec2    (18),
                    failed  (19)
                }
    MAX-ACCESS  read-only
    STATUS      current
    DESCRIPTION
        "tmnxPortSSMRxQualityLevel indicates the SSM quality level
         of received SSM messages. On ports not supporting SSM, or not
         receiving SSM messages, the quality level will be 'unknown (0)'.

         The values 'prs (1)' through 'dus (9)' and 'pno (16)' correspond to
         quality levels defined in GR-253-CORE.  The values 'prc (10)' through
         'inv (15)' correspond to quality levels defined in G.781.
         The values 'eec1 (17)' and 'eec2 (18)' correspond to quality levels
         defines in G.8264.
         The value 'failed (19)' is used when there is a failure in the SSM 
         channel."
    REFERENCE
        "Bellcore (Telcordia Technologies) GR-253-CORE, Issue 3, September 2000,
         5.4.2.
         ITU-T Recommendation G.781, June 1999.
         ITU-T Recommendation G.8264, October 2008."
    DEFVAL { unknown }
    ::= { tmnxPortEntry 67 }

tmnxPortDwdmLaserChannel    OBJECT-TYPE
    SYNTAX      TmnxOpticalDwdmChannel
    MAX-ACCESS  read-write
    STATUS      current
    DESCRIPTION
        "tmnxPortDwdmLaserChannel specifies the DWDM ITU channel at which a
         tunable optical interface will be configured to operate.

         A value of zero(0) can be specified only on an administratively
         disabled port or a port that is equipped with a non-tunable laser. To
         enable a port that is equipped with a tunable laser,
         tmnxPortDwdmLaserChannel must be changed to a valid DWDM ITU channel
         number in either the 50GHz, or 100GHz grid."
    DEFVAL { 0 }
    ::= { tmnxPortEntry 68 }

tmnxPortOtuCapable               OBJECT-TYPE
    SYNTAX      TruthValue
    MAX-ACCESS  read-only
    STATUS      current
    DESCRIPTION
        "The value of tmnxPortOtuCapable indicates whether or not the physical
         port supports the Optical Transport Unit (OTU) encapsulation."
    ::= { tmnxPortEntry 69 }

tmnxPortWaveTrackerCapable       OBJECT-TYPE
    SYNTAX      TruthValue
    MAX-ACCESS  read-only
    STATUS      current
    DESCRIPTION
        "The value of tmnxPortWaveTrackerCapable indicates whether or not the
         physical port supports Wavelength Tracker.

         tmnxPortWaveTrackerCapable is equivalent to
         'tnWtEncodePortCapabilityPresent' of the 1696-Roadm MIBs."
    ::= { tmnxPortEntry 70 }

tmnxPortHybridIngAccessWeight    OBJECT-TYPE
    SYNTAX      Unsigned32 (0..100)
    MAX-ACCESS  read-write
    STATUS      current
    DESCRIPTION
        "The value of tmnxPortHybridIngAccessWeight specifies the increment or
         decrement of the ingress access weight associated with the port.
         This active weight affects the amount of ingress access buffer space
         managed by the port. This object only applies when tmnxPortMode is
         set to 'hybrid (3)'"
    DEFVAL { 50 }
    ::= { tmnxPortEntry 71 }

tmnxPortHybridIngNetworkWeight   OBJECT-TYPE
    SYNTAX      Unsigned32 (0..100)
    MAX-ACCESS  read-write
    STATUS      current
    DESCRIPTION
        "The value of tmnxPortHybridIngNetworkWeight specifies the increment or
         decrement of the ingress network weight associated with the port.
         This active weight affects the amount of ingress network buffer space
         managed by the port. This object only applies when tmnxPortMode is
         set to 'hybrid (3)'"
    DEFVAL { 50 }
    ::= { tmnxPortEntry 72 }

tmnxPortHybridEgrAccessWeight    OBJECT-TYPE
    SYNTAX      Unsigned32 (0..100)
    MAX-ACCESS  read-write
    STATUS      current
    DESCRIPTION
        "The value of tmnxPortHybridEgrAccessWeight specifies the increment or
         decrement of the egress access weight associated with the port.
         This active weight affects the amount of egress access buffer space
         managed by the port. This object only applies when tmnxPortMode is
         set to 'hybrid (3)'"
    DEFVAL { 50 }
    ::= { tmnxPortEntry 73 }

tmnxPortHybridEgrNetworkWeight   OBJECT-TYPE
    SYNTAX      Unsigned32 (0..100)
    MAX-ACCESS  read-write
    STATUS      current
    DESCRIPTION
        "The value of tmnxPortHybridEgrNetworkWeight specifies the increment or
         decrement of the egress network weight associated with the port.
         This active weight affects the amount of egress network buffer space
         managed by the port. This object only applies when tmnxPortMode is
         set to 'hybrid (3)'"
    DEFVAL { 50 }
    ::= { tmnxPortEntry 74 }

tmnxPortDwdmRxDtvAdjustEnable    OBJECT-TYPE
    SYNTAX      TruthValue
    MAX-ACCESS  read-write
    STATUS      current
    DESCRIPTION
        "The value of tmnxPortDwdmRxDtvAdjustEnable specifies whether or not
         the Receive Decision threshold voltage adjustment feedback loop
         should be enabled.

         When this value is set to false, the optical receiver's default
         receive decision threshold voltage will be used."
    DEFVAL { true }
    ::= { tmnxPortEntry 75 }

tmnxPortDwdmRxDtvDacPercent      OBJECT-TYPE
    SYNTAX      Unsigned32 (0..10000)
    UNITS       "Hundredths of a percent"
    MAX-ACCESS  read-only
    STATUS      current
    DESCRIPTION
        "The value of tmnxPortDwdmRxDtvDacPercent specifies the current
         relative adjustment of the receive decision threshold voltage
         in hundredths of a percent.

         50.00% is the optical receiver's default decision threshold
         voltage."
    DEFVAL      { 5000 }
    ::= { tmnxPortEntry 76 }

tmnxPortInterfaceGroupHandlerIdx  OBJECT-TYPE
    SYNTAX      Unsigned32
    MAX-ACCESS  read-only
    STATUS      current
    DESCRIPTION
        "The value of tmnxPortInterfaceGroupHandlerIdx indicates whether or not
         the physical port is a member of an Interface Group Handler."
    ::= { tmnxPortEntry 77 }

tmnxPortHoldTimeUnits             OBJECT-TYPE
    SYNTAX      INTEGER {
                    seconds (0),
                    centiseconds (1)
                }
    MAX-ACCESS  read-write
    STATUS      current
    DESCRIPTION
        "The value of tmnxPortHoldTimeUnits specifies the measurable units of
         tmnxPortHoldTimeDown and tmnxPortHoldTimeUp."
    DEFVAL { seconds }
    ::= { tmnxPortEntry 78 }

tmnxPortLinkLengthInfo           OBJECT-TYPE
    SYNTAX      OCTET STRING (SIZE (6))
    MAX-ACCESS  read-only
    STATUS      current
    DESCRIPTION
        "The value of tmnxPortLinkLengthInfo indicates the link length info
         stored in SFF EEPROMs.

         tmnxPortLinkLengthInfo is applicable only when tmnxPortSFPEquipped is
         'true'; otherwise, all 6 bytes will have a value of '0'.

         See SFF Committee documents for details on the representation of
         the values in each byte. For SFP EEPROMs, the 6 bytes are bytes 14 to
         19 of the A0 bank inclusive, described in SFF Committee document
         SFF-8472. For XFP EEPROMs, the first 5 bytes are bytes 142 to 146 of
         the 01 bank inclusive, described in SFF Committee document INF-8077i.
         For XFP EEPROMs, byte 6 will have a value of '0'."
    REFERENCE
        "SFF Committee, SFF-8472 Specification for Diagnostic Monitoring
         Interface for Optical Transceivers, Rev 11.0, September 14, 2010

         SFF Committee, INF-8077i 10 Gigabit Small Form Factor Pluggable
         Module, Rev 4.5, August 31, 2005"
    ::= { tmnxPortEntry 79 }

tmnxPortSFPNumLanes              OBJECT-TYPE
    SYNTAX      Unsigned32
    MAX-ACCESS  read-only
    STATUS      current
    DESCRIPTION
        "The value of tmnxPortSFPNumLanes indicates the total number of lanes
         supported by the CSFP/QSFP.  If tmnxPortSFPEquipped is false, this
         object will have a value of '0'."
    ::= { tmnxPortEntry 80 }

tmnxPortPhysStateChangeCount     OBJECT-TYPE
    SYNTAX      Counter32
    MAX-ACCESS  read-only
    STATUS      current
    DESCRIPTION
        "The value of tmnxPortPhysStateChangeCount indicates the number of times
         a physical port state has changed from 'linkDown (3)' to either
         'linkUp (4)' or 'up (5)' and from either 'linkUp (4)' or 'up (5)' to
         'linkDown (3)'.  The count does not include transitions between
         'linkUp (4)' and 'up (5)'.

         This counter is applicable to physical Ethernet ports only. All other
         ports maintain a count of 0.

         This object is automatically reset to zero, once the port enters the
         'ghost (2)' state.  To reset this object manually, one may use the
         tmnxClearTable entry whose tmnxClearName value is
         'clearPortPhysStateChangeCount' by specifying the tmnxClearParams value
         with 'port-id=<ifIndex>'."
    ::= { tmnxPortEntry 81 }

--
--  Port Diagnostic Table
--
tmnxPortTestTable OBJECT-TYPE
    SYNTAX  SEQUENCE OF TmnxPortTestEntry
    MAX-ACCESS  not-accessible
    STATUS      current
    DESCRIPTION
         "The tmnxPortTestTable has an entry for each port on each IOM
         card in each chassis in the TMNX system."
    ::= { tmnxPortObjs 3 }

tmnxPortTestEntry       OBJECT-TYPE
    SYNTAX      TmnxPortTestEntry
    MAX-ACCESS  not-accessible
    STATUS      current
    DESCRIPTION
        "Each row entry represents a port on a IOM card in a
         chassis in the system.  Entries cannot be created and
         deleted via SNMP SET operations."
    AUGMENTS { tmnxPortEntry }
    ::= { tmnxPortTestTable 1 }

TmnxPortTestEntry ::=
    SEQUENCE {
        tmnxPortTestState           INTEGER,
        tmnxPortTestMode            INTEGER,
        tmnxPortTestParameter       Unsigned32,
        tmnxPortTestLastResult      INTEGER,
        tmnxPortTestStartTime       DateAndTime,
        tmnxPortTestEndTime         DateAndTime,
        tmnxPortTestDuration        INTEGER,
        tmnxPortTestAction          INTEGER
    }

tmnxPortTestState   OBJECT-TYPE
    SYNTAX      INTEGER {
                    notInTest (1),
                    inTest (2)
                }
    MAX-ACCESS  read-only
    STATUS      current
    DESCRIPTION
        "The current testing status of this port."
    ::= { tmnxPortTestEntry 1 }

tmnxPortTestMode    OBJECT-TYPE
    SYNTAX      INTEGER {
                    notApplicable(0),
                    loopback1 (1),
                    loopback2 (2),
                    loopback3 (3),
                    singalInsertion (4)
                }
    MAX-ACCESS  read-write
    STATUS      current
    DESCRIPTION
        "The type of test to be executed on this port."
    ::= { tmnxPortTestEntry 2 }

tmnxPortTestParameter       OBJECT-TYPE
    SYNTAX      Unsigned32
    MAX-ACCESS  read-write
    STATUS      current
    DESCRIPTION
        "A parameter to be passed to the test program."
    ::= { tmnxPortTestEntry 3 }

tmnxPortTestLastResult      OBJECT-TYPE
    SYNTAX      INTEGER {
                    notApplicable(0),
                    success (1),
                    failure (2),
                    timeout (3)
                }
    MAX-ACCESS  read-only
    STATUS      current
    DESCRIPTION
        "The status of the last test executed on this port."
    ::= { tmnxPortTestEntry 4 }

tmnxPortTestStartTime       OBJECT-TYPE
    SYNTAX      DateAndTime
    MAX-ACCESS  read-only
    STATUS      current
    DESCRIPTION
        "The date and time the test started on this port.
         Returns 0 if tmnxPortTestState is notInTest."
    ::= { tmnxPortTestEntry 5 }

tmnxPortTestEndTime OBJECT-TYPE
    SYNTAX      DateAndTime
    MAX-ACCESS  read-only
    STATUS      current
    DESCRIPTION
        "The date and time the last test completed.  Returns 0
         if a test is in progress or no tests have yet to be run on
         this port."
    ::= { tmnxPortTestEntry 6 }

tmnxPortTestDuration        OBJECT-TYPE
    SYNTAX      INTEGER (0..256)
    MAX-ACCESS  read-write
    STATUS      current
    DESCRIPTION
        "The number of seconds the port test is anticipated to last."
    ::= { tmnxPortTestEntry 7 }

tmnxPortTestAction  OBJECT-TYPE
    SYNTAX      INTEGER {
                    none (1),
                    startTest (2),
                    stopTest (3)
                }
    MAX-ACCESS  read-write
    STATUS      current
    DESCRIPTION
        "The operator sets this variable to perform the appropriate
         type of testing."
    ::= { tmnxPortTestEntry 8 }

--
--  Ethernet Ports Table
--
tmnxPortEtherTable OBJECT-TYPE
    SYNTAX  SEQUENCE OF TmnxPortEtherEntry
    MAX-ACCESS  not-accessible
    STATUS      current
    DESCRIPTION
        "The tmnxPortEtherTable has an entry for each Ethernet
         (faste, gige, xcme or xgige) port on each IOM card in each chassis
         in the TMNX system."
    ::= { tmnxPortObjs 4 }

tmnxPortEtherEntry       OBJECT-TYPE
    SYNTAX  TmnxPortEtherEntry
    MAX-ACCESS      not-accessible
    STATUS  current
    DESCRIPTION
        "Each row entry represents an Ethernet port on a IOM card in a
         chassis in the system.  Entries cannot be created and
         deleted via SNMP SET operations.  Before an IOM card entry
         can be deleted from the tmnxMDATable, its supported
         tmnxPortEntry and tmnxPortEtherEntry rows must be in the proper
         state for removal.  The tmnxPortEtherEntry contains attributes
         that are unique to the Ethernet TmnxPortType."
    INDEX   { tmnxChassisIndex, tmnxPortPortID }
    ::= { tmnxPortEtherTable 1 }

TmnxPortEtherEntry ::=
    SEQUENCE {
        tmnxPortEtherMTU                     Unsigned32,
        tmnxPortEtherDuplex                  INTEGER,
        tmnxPortEtherSpeed                   INTEGER,
        tmnxPortEtherAutoNegotiate           INTEGER,
        tmnxPortEtherOperDuplex              INTEGER,
        tmnxPortEtherOperSpeed               Unsigned32,
        tmnxPortEtherAcctPolicyId            Unsigned32,
        tmnxPortEtherCollectStats            TruthValue,
        tmnxPortEtherMDIMDIX                 INTEGER,
        tmnxPortEtherXGigMode                INTEGER,
        tmnxPortEtherEgressRate              Integer32,
        tmnxPortEtherDot1qEtype              Unsigned32,
        tmnxPortEtherQinqEtype               Unsigned32,
        tmnxPortEtherIngressRate             Integer32,
        tmnxPortEtherReportAlarm             TmnxPortEtherReportStatus,
        tmnxPortEtherReportAlarmStatus       TmnxPortEtherReportStatus,
        tmnxPortEtherPkts1519toMax           Counter32,
        tmnxPortEtherHCOverPkts1519toMax     Counter32,
        tmnxPortEtherHCPkts1519toMax         Counter64,
        tmnxPortEtherLacpTunnel              TruthValue,
        tmnxPortEtherDownWhenLoopedEnabled   TruthValue,
        tmnxPortEtherDownWhenLoopedKeepAlive Unsigned32,
        tmnxPortEtherDownWhenLoopedRetry     Unsigned32,
        tmnxPortEtherDownWhenLoopedState     INTEGER,
        tmnxPortEtherPBBEtype                Unsigned32,
        tmnxPortEtherReasonDownFlags         BITS,
        tmnxPortEtherSingleFiber             TruthValue,
        tmnxPortEtherSSM                     TruthValue,
        tmnxPortEtherDWLUseBroadcastAddr     TruthValue,
        tmnxPortEtherSSMCodeType             INTEGER,
        tmnxPortEtherSSMTxDus                TruthValue,
        tmnxPortEtherSSMRxEsmc               Unsigned32,
        tmnxPortEtherSSMTxQualityLevel       INTEGER,
        tmnxPortEtherCrcMonSdThreshold       Unsigned32,
        tmnxPortEtherCrcMonSdTMultiplier     Unsigned32,
        tmnxPortEtherCrcMonSfThreshold       Unsigned32,
        tmnxPortEtherCrcMonSfTMultiplier     Unsigned32,
        tmnxPortEtherCrcMonWindowSize        Unsigned32,
        tmnxPortEtherCrcAlarmReason          TmnxPortEtherMonReportStatus,
        tmnxPortEtherDownOnInternalError     TruthValue,
        tmnxPortEtherMinFrameLength          Unsigned32,
        tmnxPortEtherPhysAcctPolicyId        Unsigned32,
        tmnxPortEtherPhysCollectStats        TruthValue,
        tmnxPortEtherOperPhyTxClock          TmnxPortEtherOperPhyTxClock
    }

tmnxPortEtherMTU  OBJECT-TYPE
    SYNTAX      Unsigned32 (0|512..9212)
    UNITS       "bytes"
    MAX-ACCESS  read-write
    STATUS      current
    DESCRIPTION
        "The size of the largest packet which can be sent/received
         on the Ethernet physical interface, specified in octets.  For
         interfaces that are used for transmitting network datagrams,
         this is the size of the largest network datagram that can be
         sent on the interface.

         Setting tmnxPortEtherMTU to a value of zero (0), causes the agent
         to recalculate the default MTU size which can vary based on the
         current setting of tmnxPortMode and tmnxPortEncapType variables.
         Some typical default values are:
                1514 with mode access and encap-type null
                1518 with mode access and encap-type dot1q
                1518 with mode access and encap-type mpls
                9198 with mode network
        "
    ::= { tmnxPortEtherEntry 1 }

tmnxPortEtherDuplex OBJECT-TYPE
    SYNTAX      INTEGER {
                    notApplicable (0),
                    fullDuplex (1),
                    halfDuplex (2)
                }
    MAX-ACCESS  read-write
    STATUS      current
    DESCRIPTION
        "The tmnxPortEtherDuplex variable specifies the duplex mode used by
         the Ethernet interface if tmnxPortEtherAutoNegotiate has a value of
         'false' or 'limited'. If tmnxPortEtherAutoNegotiate has a value of
         'true', the link parameters are negotiated with the far end and
         the tmnxPortEtherDuplex variable is ignored. A value of 'fullDuplex'
         sets the link to full duplex mode.  A value of 'halfDuplex' sets
         the link to half duplex mode. tmnxPortEtherDuplex is only valid on
         Ethernet interfaces that support multiple duplex modes."
    DEFVAL { fullDuplex }
    ::= { tmnxPortEtherEntry 2 }

tmnxPortEtherSpeed  OBJECT-TYPE
    SYNTAX      INTEGER {
                    notApplicable (0),
                    speed10 (1),
                    speed100 (2),
                    speed1000 (3),
                    speed10000 (4),
                    speed40000 (5),
                    speed100000 (6),
                    speed25000 (7)
                }
    MAX-ACCESS  read-write
    STATUS      current
    DESCRIPTION
        "The tmnxPortEtherSpeed variable specifies the link speed of the
         Ethernet interface if tmnxPortEtherAutoNegotiate has a value of
         'false' or 'limited'.  If tmnxPortEtherAutoNegotiate has a value of
         'true', the link parameters are negotiated with the far end and
         the tmnxPortEtherSpeed variable is ignored. A value of 'speed10'
         sets the link to 10 mbps.  A value of 'speed100' sets the link to
         100 mbps.  A value of 'speed1000' sets the link to 1000 mbps (1 gbps).
         tmnxPortEtherSpeed is only valid on Ethernet interfaces that support
         multiple link speeds."
    ::= { tmnxPortEtherEntry 3 }

tmnxPortEtherAutoNegotiate   OBJECT-TYPE
    SYNTAX      INTEGER {
                    notApplicable (0),
                    true (1),
                    false (2),
                    limited (3)
                }
    MAX-ACCESS  read-write
    STATUS      current
    DESCRIPTION
        "When the value of tmnxPortEtherAutoNegotiate is 'true', the Ethernet
         interface will automatically negotiate link parameters with the far
         end (including speed and duplex), and will advertise all speeds and
         duplex modes supported by the interface. When the value of
         tmnxPortEtherAutoNegotiate is 'limited', the Ethernet interface will
         automatically negotiate link parameters with the far end, but will
         only advertise the speed and duplex mode specified by
         tmnxPortEtherSpeed and tmnxPortEtherDuplex. If
         tmnxPortEtherAutoNegotiate is 'false', the Ethernet interface will not
         negotiate link parameters with the far end and will instead force the
         speed and duplex mode to the values specified by tmnxPortEtherSpeed and
         tmnxPortEtherDuplex respectively."
    DEFVAL { true }
    ::= { tmnxPortEtherEntry 4 }

tmnxPortEtherOperDuplex OBJECT-TYPE
    SYNTAX      INTEGER {
                    notApplicable (0),
                    fullDuplex (1),
                    halfDuplex (2)
                }
    MAX-ACCESS  read-only
    STATUS      current
    DESCRIPTION
        "The tmnxPortEtherOperDuplex variable indicates the operational duplex
         mode of the Ethernet interface. A value of 'fullDuplex' indicates that
         the link is in full duplex mode.  A value of 'halfDuplex' indicates
         that the link is in half duplex mode. tmnxPortEtherOperDuplex is only
         valid if tmnxPortClass is 'faste' or 'xcme'."
    ::= { tmnxPortEtherEntry 5 }

tmnxPortEtherOperSpeed  OBJECT-TYPE
    SYNTAX      Unsigned32
    UNITS       "mega-bits per second"
    MAX-ACCESS  read-only
    STATUS      current
    DESCRIPTION
        "The tmnxPortEtherOperSpeed variable indicates the operational speed
         of the Ethernet interface in mega-bits per second (mbps).  If the value
         of tmnxPortEtherAutoNegotiate is 'true', the link autonegotiates the
         link parameters with the far end side.  The value of
         tmnxPortEtherOperSpeed is only valid if tmnxPortClass is one of the
         Ethernet classes."
    ::= { tmnxPortEtherEntry 6 }

tmnxPortEtherAcctPolicyId  OBJECT-TYPE
    SYNTAX      Unsigned32 (0..99)
    MAX-ACCESS  read-write
    STATUS      current
    DESCRIPTION
        "The value of the accounting policy must be defined prior to associating
         the policy with the ethernet port. Accounting policies can only be
         associated with network ports.
         A non-zero value indicates the tmnxLogApPolicyId index identifying the
         policy entry in the tmnxLogApTable from the TIMETRA-LOG-MIB which is
         associated with this port.  A zero value indicates that there is no
         accounting policy associated with this port"
    DEFVAL { 0 }
    ::= { tmnxPortEtherEntry 7 }

tmnxPortEtherCollectStats        OBJECT-TYPE
    SYNTAX      TruthValue
    MAX-ACCESS  read-write
    STATUS      current
    DESCRIPTION
        "Enable/disable the collection of accounting and statistical data
         for the network ethernet port. When applying accounting policies the
         data by default will be collected in the appropriate records and
         written to the designated billing file.
         When the value is set to false, the statistics are still accumulated
         by the IOM cards, however, the CPU will not obtain the results and
         write them to the billing file."
    DEFVAL { false }
    ::= { tmnxPortEtherEntry 8 }

tmnxPortEtherMDIMDIX        OBJECT-TYPE
    SYNTAX      INTEGER {
                    unknown (0),
                    mdi (1),
                    mdix (2)
                }
    MAX-ACCESS  read-only
    STATUS      current
    DESCRIPTION
        "The tmnxPortEtherMDIMDIX variable indicates whether the Ethernet
         interface is of type 'mdi' (Media Dependent Interface) or
         'mdix' (Media Dependent Interface with crossover). If the agent
         cannot identify the type of Ethernet interface the value
         'unknown (0)' is indicated. tmnxPortEtherMDIMDIX is only valid if
         tmnxPortClass is 'faste' or 'xcme'."
    ::= { tmnxPortEtherEntry 9 }

tmnxPortEtherXGigMode        OBJECT-TYPE
    SYNTAX      INTEGER {
                    notApplicable (0),
                    lan (1),
                    wan (2)
                }
    MAX-ACCESS  read-write
    STATUS      current
    DESCRIPTION
        "The tmnxPortEtherXGigMode variable specifies whether the Ethernet
         interface is in LAN or WAN mode. tmnxPortEtherXGigMode must be
         'notApplicable' if tmnxPortClass is not 'xgige'."
    DEFVAL { lan }
    ::= { tmnxPortEtherEntry 10 }

tmnxPortEtherEgressRate        OBJECT-TYPE
    SYNTAX      Integer32 (-1 | 1..100000000)
    UNITS       "kilo-bits per second"
    MAX-ACCESS  read-write
    STATUS      current
    DESCRIPTION
        "The tmnxPortEtherEgressRate variable specifies the maximum egress
         bandwidth (in kilo-bits per second) that the Ethernet interface
         can generate. A value of -1 means that the limit is the actual
         physical limit. If the provisioned sub-rate bandwidth is larger than
         the actual physical bandwidth of the interface, the latter applies."
    DEFVAL { -1 }
    ::= { tmnxPortEtherEntry 11 }

tmnxPortEtherDot1qEtype        OBJECT-TYPE
    SYNTAX      Unsigned32 ('600'H..'ffff'H)
    MAX-ACCESS  read-write
    STATUS      current
    DESCRIPTION
        "The tmnxPortEtherDot1qEtype variable indicates the ethertype expected
         when the port's encapsulation type is dot1qEncap."
    DEFVAL { '8100'H }
    ::= { tmnxPortEtherEntry 12 }

tmnxPortEtherQinqEtype         OBJECT-TYPE
    SYNTAX      Unsigned32 ('600'H..'ffff'H)
    MAX-ACCESS  read-write
    STATUS      current
    DESCRIPTION
        "The tmnxPortEtherQinqEtype variable indicates the ethertype expected
         when the port's encapsulation type is qinqEncap."
    DEFVAL { '8100'H }
    ::= { tmnxPortEtherEntry 13 }

tmnxPortEtherIngressRate        OBJECT-TYPE
    SYNTAX      Integer32 (-1 | 1..100000)
    UNITS       "mega-bits per second"
    MAX-ACCESS  read-write
    STATUS      current
    DESCRIPTION
        "The tmnxPortEtherIngressRate variable specifies the maximum ingress
         bandwidth (in mega-bits per second) that the Ethernet interface
         can receive. A value of -1 means that the limit is the actual
         physical limit. If the provisioned sub-rate bandwidth is larger than
         the actual physical bandwidth of the interface, the latter applies.
         
         For interfaces that support more than 10Gbps, the configured value
         must be specified as a multiple of 10Mbps; otherwise, the
         configuration will be rejected with an inconsistentValue error."
    DEFVAL { -1 }
    ::= { tmnxPortEtherEntry 14 }

tmnxPortEtherReportAlarm  OBJECT-TYPE
    SYNTAX          TmnxPortEtherReportStatus
    MAX-ACCESS      read-write
    STATUS          current
    DESCRIPTION
        "The value of tmnxPortEtherReportAlarm determines when and if to
         generate tmnxEqPortEtherAlarm and tmnxEqPortEtherAlarmClear."
    DEFVAL { { remoteFault, localFault } }
    ::= { tmnxPortEtherEntry 15 }

tmnxPortEtherReportAlarmStatus  OBJECT-TYPE
    SYNTAX          TmnxPortEtherReportStatus
    MAX-ACCESS      read-only
    STATUS          current
    DESCRIPTION
        "The value of tmnxPortEtherReportAlarmStatus indicates the alarms on
         this port."
    ::= { tmnxPortEtherEntry 16 }

tmnxPortEtherPkts1519toMax   OBJECT-TYPE
    SYNTAX     Counter32
    UNITS      "Packets"
    MAX-ACCESS read-only
    STATUS     current
    DESCRIPTION
        "The total number of packets received that were longer than 1518 octets
         but less than the maximum frame size for the particular medium, usually
         12287 octets (excluding framing bits, but including FCS octets) and
         were otherwise well formed."
    ::= { tmnxPortEtherEntry 17 }

tmnxPortEtherHCOverPkts1519toMax OBJECT-TYPE
    SYNTAX     Counter32
    UNITS      "Packets"
    MAX-ACCESS read-only
    STATUS     current
    DESCRIPTION
        "The number of times the associated tmnxPortEtherPkts1519toMax
        counter has overflowed."
    ::= { tmnxPortEtherEntry 18 }

tmnxPortEtherHCPkts1519toMax OBJECT-TYPE
    SYNTAX     Counter64
    UNITS      "Packets"
    MAX-ACCESS read-only
    STATUS     current
    DESCRIPTION
        "The total number of packets (including bad packets) received that were
         between 1519 octets in length and the maximum frame size, usually 12287
         octets inclusive (excluding framing bits but including FCS octets).

         The lower 32-bits of this 64-bit counter will equal the value of
         tmnxPortEtherHCPkts1519toMax.  The high 32-bits of this counter will
         equal the value of tmnxPortEtherHCOverPkts1519toMax."
    ::= { tmnxPortEtherEntry 19 }

tmnxPortEtherLacpTunnel          OBJECT-TYPE
    SYNTAX      TruthValue
    MAX-ACCESS  read-write
    STATUS      current
    DESCRIPTION
        "The value of tmnxPortEtherLacpTunnel specifies whether the LACP
         packet tunneling for the ethernet port is enabled or disabled.
         When tunneling is enabled, the port will not process any LACP
         packets but will tunnel them through instead. Also, the port
         cannot be added as a member to a LAG group, and vice versa."
    DEFVAL { false }
    ::= { tmnxPortEtherEntry 20 }

tmnxPortEtherDownWhenLoopedEnabled          OBJECT-TYPE
    SYNTAX      TruthValue
    MAX-ACCESS  read-write
    STATUS      current
    DESCRIPTION
        "The value of tmnxPortEtherDownWhenLoopedEnabled specifies whether
         physical loop detection for the Ethernet port is enabled or
         disabled.  When enabled, the port will periodically send out
         keep-alive PDUs with an EtherType of 0x9000.  If the port
         receives a keep-alive that it transmitted, tmnxPortState will be
         set to 'linkUp' if it was previously 'up'. The port will not move
         back to tmnxPortState 'up' for a period of time defined by
         tmnxPortEtherDownWhenLoopedRetry, but will continue to periodically
         send out keep-alive PDUs.  Every time the port receives a keep alive
         it sent while a loop has been detected, it will reset the time
         period that it will remain down as defined by
         tmnxPortEtherDownWhenLoopedRetry."
    DEFVAL { false }
    ::= { tmnxPortEtherEntry 21 }

tmnxPortEtherDownWhenLoopedKeepAlive         OBJECT-TYPE
    SYNTAX      Unsigned32 (1..120)
    UNITS       "seconds"
    MAX-ACCESS  read-write
    STATUS      current
    DESCRIPTION
        "The tmnxPortEtherDownWhenLoopedKeepAlive variable specifies the
         number of seconds between each keep alive PDU transmission."
    DEFVAL { 10 }
    ::= { tmnxPortEtherEntry 22 }

tmnxPortEtherDownWhenLoopedRetry         OBJECT-TYPE
    SYNTAX      Unsigned32 (0|10..160)
    UNITS       "seconds"
    MAX-ACCESS  read-write
    STATUS      current
    DESCRIPTION
        "The tmnxPortEtherDownWhenLoopedRetry variable specifies the minimum
         number of seconds the port should wait after detecting a loop before
         tmnxPortState can be set to 'up'.  A value of 0 specifies the the
         port should not set tmnxPortState to 'up' until the user
         administratively disables and re-enables the port by setting
         tmnxPortAdminStatus to 'outOfService' and then to 'inService'."
    DEFVAL { 120 }
    ::= { tmnxPortEtherEntry 23 }

tmnxPortEtherDownWhenLoopedState          OBJECT-TYPE
    SYNTAX      INTEGER {
                    noLoopDetected (1),
                    loopDetected (2)
                }
    MAX-ACCESS  read-only
    STATUS      current
    DESCRIPTION
        "The value of tmnxPortEtherDownWhenLoopedState indicates whether
         a physical loop has been detected on the port or not.  If
         tmnxPortEtherDownWhenLoopedEnabled is set to 'false', this value
         will be 'noLoopDetected'."
    ::= { tmnxPortEtherEntry 24 }

tmnxPortEtherPBBEtype        OBJECT-TYPE
    SYNTAX      Unsigned32 ('600'H..'ffff'H)
    MAX-ACCESS  read-write
    STATUS      current
    DESCRIPTION
        "The tmnxPortEtherPBBEtype variable indicates the Ethertype expected
        for Provider Backbone Bridging Frames."
    DEFVAL { '88E7'H }
    ::= { tmnxPortEtherEntry 25 }

tmnxPortEtherReasonDownFlags OBJECT-TYPE
    SYNTAX      BITS {
                   unknown              (0),
                   linklossFwd          (1),
                   lagMemberPortStandby (2)
                }
    MAX-ACCESS  read-only
    STATUS      obsolete
    DESCRIPTION
        "The tmnxPortEtherReasonDownFlags indicates why an ethernet port may
        be in the operationally 'down' state. The following reasons are
        detected through this object:
                unknown(0)              - Unspecified (or unknown)
                linklossFwd(1)          - A sap using this port has the object
                                          'sapEthernetLLFOperStatus' set to
                                          'fault'
                lagMemberPortStandby(2) - A lag using this port as a member
                                          port has set the member port to
                                          'standby' while configured to keep
                                          standby member ports down."
    ::= { tmnxPortEtherEntry 26 }

tmnxPortEtherSingleFiber     OBJECT-TYPE
    SYNTAX      TruthValue
    MAX-ACCESS  read-write
    STATUS      current
    DESCRIPTION
        "tmnxPortEtherSingleFiber is used to enable/disable packet gathering and
         redirection of IP packets from a single fiber on RX port of the
         Ethernet interface and redistribute packets to other interfaces
         through either state routes or policy-based forwarding."
    DEFVAL { false }
    ::= { tmnxPortEtherEntry 27 }

tmnxPortEtherSSM                 OBJECT-TYPE
    SYNTAX      TruthValue
    MAX-ACCESS  read-write
    STATUS      current
    DESCRIPTION
        "tmnxPortEtherSSM specifies whether or not synchronous
         status messages (SSM) are enabled on the ethernet port."
    DEFVAL { false }
    ::= { tmnxPortEtherEntry 28 }

tmnxPortEtherDWLUseBroadcastAddr OBJECT-TYPE
    SYNTAX      TruthValue
    MAX-ACCESS  read-write
    STATUS      current
    DESCRIPTION
        "tmnxPortEtherDWLUseBroadcastAddr specifies whether or not the
         Down When Looped destination MAC address is the broadcast address,
         'true (1)', or the local port mac address, as specified in
         tmnxPortMacAddress, 'false (2)'."
    DEFVAL { false }
    ::= { tmnxPortEtherEntry 29 }

tmnxPortEtherSSMCodeType          OBJECT-TYPE
    SYNTAX      INTEGER {
                    unknown (1),
                    sonet   (2),
                    sdh     (3)
                }
    MAX-ACCESS  read-write
    STATUS      current
    DESCRIPTION
        "The value of tmnxPortEtherSSMCodeType specifies the code-type
         used by the Synchronous Status Message (SSM) channel."
    DEFVAL      { sdh }
    ::= { tmnxPortEtherEntry 30 }

tmnxPortEtherSSMTxDus            OBJECT-TYPE
    SYNTAX      TruthValue
    MAX-ACCESS  read-write
    STATUS      current
    DESCRIPTION
        "The value of tmnxPortEtherSSMTxDus specifies whether or not the
         value 0xF (dus/dnu) is forced in the Synchronous Status Message (SSM)
         channel."
    DEFVAL      { false }
    ::= { tmnxPortEtherEntry 31 }

tmnxPortEtherSSMRxEsmc           OBJECT-TYPE
    SYNTAX      Unsigned32 (0..255)
    MAX-ACCESS  read-only
    STATUS      current
    DESCRIPTION
        "The value of tmnxPortEtherSSMRxEsmc indicates the SSM code received on
         the Ethernet Synchronization Messaging Channel of the Ethernet port.

         The value returned for this object is only meaningful if
         tmnxPortEtherSSM is 'true', and tmnxPortSSMRxQualityLevel is not
         'failed'."
    REFERENCE
        "ITU-T Recommendation G.8264, October 2008."
    ::= { tmnxPortEtherEntry 32 }

tmnxPortEtherSSMTxQualityLevel   OBJECT-TYPE
    SYNTAX      INTEGER {
                    reserved0  (0),
                    prs        (1),
                    stu        (2),
                    st2        (3),
                    tnc        (4),
                    st3e       (5),
                    reserved6  (6),
                    smc        (7),
                    reserved8  (8),
                    dus        (9),
                    prc        (10),
                    ssua       (11),
                    ssub       (12),
                    reserved13 (13),
                    dnu        (14),
                    reserved15 (15),
                    pno        (16),
                    eec1       (17),
                    eec2       (18),
                    reserved19 (19)
                }
    MAX-ACCESS  read-only
    STATUS      current
    DESCRIPTION
        "The value of tmnxPortEtherSSMTxQualityLevel indicates the quality
         level transmitted in the Ethernet Synchronization Messaging Channel."
    REFERENCE
        "ITU-T Recommendation G.8264, October 2008."
    ::= { tmnxPortEtherEntry 33 }

tmnxPortEtherCrcMonSdThreshold   OBJECT-TYPE
    SYNTAX      Unsigned32 (0..9)
    MAX-ACCESS  read-write
    STATUS      current
    DESCRIPTION
        "The value of tmnxPortEtherCrcMonSdThreshold specifies a packet error
         rate threshold used to determine when to send a tmnxEqPortEtherCrcAlarm
         notification for a CRC Signal Degradation (SD) failure and
         tmnxEqPortEtherCrcAlarmClear notification for a CRC SD failure clear.

         tmnxPortEtherCrcMonSdThreshold is the absolute value of the exponent of
         the rate expressed as 10e-n.

         The CRC SD error rate threshold is calculated as:
         tmnxPortEtherCrcMonSdTMultiplier * 10e-tmnxPortEtherCrcMonSdThreshold.

         A value of 0 disables CRC SD monitioring."
    DEFVAL { 0 }
    ::= { tmnxPortEtherEntry 34 }

tmnxPortEtherCrcMonSdTMultiplier OBJECT-TYPE
    SYNTAX      Unsigned32 (1..9)
    MAX-ACCESS  read-write
    STATUS      current
    DESCRIPTION
        "The value of tmnxPortEtherCrcMonSdTMultiplier specifies the
         tmnxPortEtherCrcMonSdThreshold multiplier value.

         The CRC SD error rate threshold is calculated as:
         tmnxPortEtherCrcMonSdTMultiplier * 10e-tmnxPortEtherCrcMonSdThreshold."
    DEFVAL { 1 }
    ::= { tmnxPortEtherEntry 35 }

tmnxPortEtherCrcMonSfThreshold   OBJECT-TYPE
    SYNTAX      Unsigned32 (0..9)
    MAX-ACCESS  read-write
    STATUS      current
    DESCRIPTION
        "The value of tmnxPortEtherCrcMonSfThreshold specifies a packet error
         rate threshold used to determine when to send a tmnxEqPortEtherCrcAlarm
         notification for a CRC Signal Failure (SF) failure.

         Crossing the tmnxPortEtherCrcMonSfThreshold will result in the
         tmnxPortOperStatus being set to 'outOfService'.

         tmnxPortEtherCrcMonSfThreshold is the absolute value of the exponent of
         the rate expressed as 10e-n.

         The CRC SF error rate threshold is calculated as:
         tmnxPortEtherCrcMonSfTMultiplier * 10e-tmnxPortEtherCrcMonSfThreshold.

         A value of 0 disables CRC SF monitoring."
    DEFVAL { 0 }
    ::= { tmnxPortEtherEntry 36 }

tmnxPortEtherCrcMonSfTMultiplier OBJECT-TYPE
    SYNTAX      Unsigned32 (1..9)
    MAX-ACCESS  read-write
    STATUS      current
    DESCRIPTION
        "The value of tmnxPortEtherCrcMonSfTMultiplier specifies the
         tmnxPortEtherCrcMonSfThreshold multiplier value.

         The CRC SF error rate threshold is calculated as:
         tmnxPortEtherCrcMonSfTMultiplier * 10e-tmnxPortEtherCrcMonSfThreshold."
    DEFVAL { 1 }
    ::= { tmnxPortEtherEntry 37 }

tmnxPortEtherCrcMonWindowSize       OBJECT-TYPE
    SYNTAX      Unsigned32 (5..60)
    UNITS       "seconds"
    MAX-ACCESS  read-write
    STATUS      current
    DESCRIPTION
        "The value of tmnxPortEtherCrcMonWindowSize specifies the size of the
         sliding window in seconds over which the tmnxPortEtherCrcMonSdThreshold
         and tmnxPortEtherCrcMonSfThreshold are applied."
    DEFVAL { 10 }
    ::= { tmnxPortEtherEntry 38 }

tmnxPortEtherCrcAlarmReason  OBJECT-TYPE
    SYNTAX      TmnxPortEtherMonReportStatus
    MAX-ACCESS  read-only
    STATUS      current
    DESCRIPTION
        "The value of tmnxPortEtherCrcAlarmReason indicates the current
         status of the Ethernet CRC Monitored alarms on the port."
    ::= { tmnxPortEtherEntry 39 }

tmnxPortEtherDownOnInternalError OBJECT-TYPE
    SYNTAX      TruthValue
    MAX-ACCESS  read-write
    STATUS      current
    DESCRIPTION
        "The value of tmnxPortEtherDownOnInternalError specifies whether
         or not the port is monitored for excessive internal MAC tx errors.

         When enabled, excess Internal MAC tx errors results in the
         tmnxPortOperStatus being set to 'outOfService (3)' and a
         tmnxEqPortEtherInternalAlarm notification trap."
    DEFVAL      { false }
    ::= { tmnxPortEtherEntry 40 }

tmnxPortEtherMinFrameLength      OBJECT-TYPE
    SYNTAX      Unsigned32 (64 | 68)
    UNITS       "Bytes"
    MAX-ACCESS  read-write
    STATUS      current
    DESCRIPTION
        "The value of tmnxPortEtherMinFrameLength specifies the minimum length
        of any frame transmitted out of the port."
    DEFVAL      { 64 }
    ::= { tmnxPortEtherEntry 41 }

tmnxPortEtherPhysAcctPolicyId    OBJECT-TYPE
    SYNTAX      Unsigned32 (0|1..99)
    MAX-ACCESS  read-write
    STATUS      current
    DESCRIPTION
        "The value of tmnxPortEtherPhysAcctPolicyId specifies the
         TIMETRA-LOG-MIB::tmnxLogApPolicyId that identifies the policy entry in
         TIMETRA-LOG-MIB::tmnxLogApTable which is associated with this ethernet
         port for the purpose of collecting physical layer ethernet statistics.
         
         A zero value indicates that there is no accounting policy associated
         with this ethernet port."
    DEFVAL { 0 }
    ::= { tmnxPortEtherEntry 42 }

tmnxPortEtherPhysCollectStats    OBJECT-TYPE
    SYNTAX      TruthValue
    MAX-ACCESS  read-write
    STATUS      current
    DESCRIPTION
        "The value of tmnxPortEtherPhysCollectStats specifies whether or not
         the collection of physical layer ethernet accounting and statistical
         data for the ethernet port is enabled.
         
         When a non-zero value is specified for tmnxPortEtherPhysAcctPolicyId
         and tmnxPortEtherPhysCollectStats is set to true, data will be
         collected in the appropriate records and written to the designated
         billing file.
         
         When a non-zero value is specified for tmnxPortEtherPhysAcctPolicyId
         and tmnxPortEtherPhysCollectStats is set to false, the statistics are
         still accumulated by the IOM cards; however, the CPM will not obtain
         the results and write them to the billing file."
    DEFVAL { false }
    ::= { tmnxPortEtherEntry 43 }

tmnxPortEtherOperPhyTxClock      OBJECT-TYPE
    SYNTAX      TmnxPortEtherOperPhyTxClock
    MAX-ACCESS  read-only
    STATUS      current
    DESCRIPTION
        "The value of tmnxPortEtherOperPhyTxClock indicates the result
         of Master/Slave resolution on copper based Ethernet ports.
         tmnxPortEtherOperPhyTxClock is 'notApplicable' if tmnxPortClass
         is not 'xcme' and tmnxPortType is not 'portTypeXcmeTx' and
         'tmnxPortEtherOperSpeed' is not 1000."
    ::= { tmnxPortEtherEntry 44 }

--
--  Sonet Ports Table
--
tmnxSonetTable OBJECT-TYPE
    SYNTAX  SEQUENCE OF TmnxSonetEntry
    MAX-ACCESS  not-accessible
    STATUS      current
    DESCRIPTION
        "The tmnxSonetTable has an entry for each packet over Sonet
         port on each IOM card in each chassis in the TMNX system."
    ::= { tmnxPortObjs 5 }

tmnxSonetEntry       OBJECT-TYPE
    SYNTAX      TmnxSonetEntry
    MAX-ACCESS  not-accessible
    STATUS      current
    DESCRIPTION
        "Each row entry represents a packet over Sonet port on a
         IOM card in a chassis in the system.  Entries cannot be
         created and deleted via SNMP SET operations.  Before an IOM
         tmnxMDAEntry can be deleted from the tmnxMDATable, its
         supported tmnxPortEntry rows must be in the proper state for
         removal.  The tmnxSonetEntry contains attributes that are
         unique to the 'sonet' TmnxPortType.  It also contains attributes
         that are common to all sonet paths configured on a sonet port.
         The tmnxPortPortID for a sonet port includes a sonet path number
         in the lower bits.   If the sonet path number is zero, '0', it
         represents a single (clear) sonet path on the port that uses
         the full bandwidth of the sonet port.  All entries in this table
         have the sonet path number part of their tmnxPortPortID index
         value set to zero."
    INDEX   { tmnxChassisIndex, tmnxPortPortID }
    ::= { tmnxSonetTable 1 }

TmnxSonetEntry ::=
    SEQUENCE {
        tmnxSonetSpeed                INTEGER,
        tmnxSonetClockSource          INTEGER,
        tmnxSonetFraming              INTEGER,
        tmnxSonetReportAlarm          BITS,
        tmnxSonetBerSdThreshold       Unsigned32,
        tmnxSonetBerSfThreshold       Unsigned32,
        tmnxSonetAps                  TruthValue,
        tmnxSonetApsAdminStatus       TmnxPortAdminStatus,
        tmnxSonetApsOperStatus        TmnxPortOperStatus,
        tmnxSonetApsAuthKey           OCTET STRING,
        tmnxSonetApsNeighborAddr      IpAddress,
        tmnxSonetApsAdvertiseInterval TimeInterval,
        tmnxSonetApsAdvertiseTimeLeft TimeInterval,
        tmnxSonetApsHoldTime          TimeInterval,
        tmnxSonetApsHoldTimeLeft      TimeInterval,
        tmnxSonetLoopback             INTEGER,
        tmnxSonetReportAlarmStatus    BITS,
        tmnxSonetSectionTraceMode     INTEGER,
        tmnxSonetJ0String             OCTET STRING,
        tmnxSonetMonS1Byte            Unsigned32,
        tmnxSonetMonJ0String          OCTET STRING,
        tmnxSonetMonK1Byte            Unsigned32,
        tmnxSonetMonK2Byte            Unsigned32,
        tmnxSonetSingleFiber          TruthValue,
        tmnxSonetHoldTimeUp           TmnxHoldTime,
        tmnxSonetHoldTimeDown         TmnxHoldTime,
        tmnxSonetSuppressLoOrderAlarm TruthValue,
        tmnxSonetTxDus                TruthValue,
        tmnxSonetTxS1Byte             Unsigned32

    }

tmnxSonetSpeed    OBJECT-TYPE
    SYNTAX      INTEGER {
                    oc3 (1),
                    oc12 (2),
                    oc48 (3),
                    oc192 (4),
                    oc768 (5),
                    oc1 (6)
                }
    MAX-ACCESS  read-write
    STATUS      current
    DESCRIPTION
        "The rate of this optical facility."
    ::= { tmnxSonetEntry 1 }

tmnxSonetClockSource  OBJECT-TYPE
    SYNTAX      INTEGER {
                    loopTimed (1),
                    nodeTimed (2)
                }
    MAX-ACCESS  read-write
    STATUS      current
    DESCRIPTION
        "tmnxSonetClockSource configures the clock for transmitted data from
         either the internal clock ('nodeTimed') or from a clock recovered
         from the line's receive data stream ('loopTimed')."
    DEFVAL { loopTimed }
    ::= { tmnxSonetEntry 2 }

tmnxSonetFraming      OBJECT-TYPE
    SYNTAX      INTEGER {
                    unknown (1),
                    sonet (2),
                    sdh (3)
                }
    MAX-ACCESS  read-write
    STATUS      current
    DESCRIPTION
        "The value of tmnxSonetFraming indicates the type of framing used
         on this interface."
    DEFVAL { sonet }
    ::= { tmnxSonetEntry 3 }

tmnxSonetReportAlarm  OBJECT-TYPE
    SYNTAX      BITS {
                    notUsed (0),
                    loc(1),
                    lais(2),
                    lrdi(3),
                    ss1f(4),
                    sb1err(5),
                    lb2erSd(6),
                    lb2erSf(7),
                    slof(8),
                    slos(9),
                    stxptr(10),
                    srxptr(11),
                    lrei(12)
                }
    MAX-ACCESS      read-write
    STATUS          current
    DESCRIPTION
        "The value of tmnxSonetReportAlarm determines when and if to
         generate tmnxEqPortSonetAlarm and tmnxEqPortSonetAlarmClear
         notifications for this port:
            loc(1)      Reports a loss of clock which causes the operational
                        state of the port to be downed.  Set by default.
            lais(2)     Reports line alarm indication signal errors. Not set
                        by default.
            lrdi(3)     Reports line remote defect initiation errors.  LRDIs
                        are caused by remote LOF, LOC, and LOS.  Set by default.
            ss1f(4)     Reports section synchronization failure as reported by
                        the S1 byte.  Not set by default.
            sb1err(5)   Reports section B1 errors.  Not set by default.
            lb2erSd(6)  Reports line signal degradation BER errors.  Not set
                        by default.
            lb2erSf(7)  Reports line signal failure BER errors.  Set by default.
            slof(8)     Reports section loss of frame errors.  Set by default
            slos(9)     Reports section loss of signal errors. Set by default.
            stxptr(10)  Reports a section synchronization error on the transmit
                        side.  Indicates if there is a positive or negative
                        justification count per channel.  Not set by default.
            srxptr(11)  Reports a section synchronization error on the receive
                        side.  Indicates if there is a positive or negative
                        justification count per path.  Not set by default.
            lrei(12)    Reports a line error condition raised by the remote
                        as a result of B1 errors received from this node.
                        Not set by default.
        "
    DEFVAL { {loc, lrdi, lb2erSf, slof, slos} }
    ::= { tmnxSonetEntry 4 }

tmnxSonetBerSdThreshold       OBJECT-TYPE
    SYNTAX      Unsigned32 (3..9)
    MAX-ACCESS  read-write
    STATUS      current
    DESCRIPTION
        "The value of tmnxSonetBerSdThreshold specifies a bit error rate (BER)
         threshold used to determine when to send a tmnxEqPortSonetAlarm
         notification for a BER SD failure and tmnxEqPortSonetAlarmClear
         notification for a BER SD failure clear.  tmnxSonetBerSdThreshold is
         the absolute value of the exponent of the rate expressed as 10e-n."
    DEFVAL { 6 }
    ::= { tmnxSonetEntry 5 }

tmnxSonetBerSfThreshold       OBJECT-TYPE
    SYNTAX      Unsigned32 (3..6)
    MAX-ACCESS  read-write
    STATUS      current
    DESCRIPTION
        "The value of tmnxSonetBerSfThreshold specifies a bit error rate (BER)
         threshold used to determine when to send a tmnxEqPortSonetAlarm
         notification for a BER SF failure and tmnxEqPortSonetAlarmClear
         notification for a BER SF failure clear.  tmnxSonetBerSdThreshold is
         the absolute value of the exponent of the rate expressed as 10e-n."
    DEFVAL { 3 }
    ::= { tmnxSonetEntry 6 }

tmnxSonetAps      OBJECT-TYPE
    SYNTAX      TruthValue
    MAX-ACCESS  read-write
    STATUS      obsolete
    DESCRIPTION
        "Automatic Protection Switching (APS) is supported on 7x50 systems
         by the APS-MIB and TIMETRA-APS-MIB."
    DEFVAL { false }
    ::= { tmnxSonetEntry 7 }

tmnxSonetApsAdminStatus   OBJECT-TYPE
    SYNTAX      TmnxPortAdminStatus
    MAX-ACCESS  read-write
    STATUS      obsolete
    DESCRIPTION
        "Automatic Protection Switching (APS) is supported on 7x50 systems
         by the APS-MIB and TIMETRA-APS-MIB."
    DEFVAL { inService }
    ::= { tmnxSonetEntry 8 }

tmnxSonetApsOperStatus    OBJECT-TYPE
    SYNTAX      TmnxPortOperStatus
    MAX-ACCESS  read-only
    STATUS      obsolete
    DESCRIPTION
        "Automatic Protection Switching (APS) is supported on 7x50 systems
         by the APS-MIB and TIMETRA-APS-MIB."
    ::= { tmnxSonetEntry 9 }

tmnxSonetApsAuthKey OBJECT-TYPE
    SYNTAX       OCTET STRING (SIZE (0..256))
    MAX-ACCESS   read-write
    STATUS       obsolete
    DESCRIPTION
        "Automatic Protection Switching (APS) is supported on 7x50 systems
         by the APS-MIB and TIMETRA-APS-MIB."
    DEFVAL { '0000000000000000'H }
    ::= { tmnxSonetEntry 10 }

tmnxSonetApsNeighborAddr      OBJECT-TYPE
    SYNTAX      IpAddress
    MAX-ACCESS  read-write
    STATUS      obsolete
    DESCRIPTION
        "Automatic Protection Switching (APS) is supported on 7x50 systems
         by the APS-MIB and TIMETRA-APS-MIB."
    DEFVAL { '00000000'H }
    ::= { tmnxSonetEntry 11 }

tmnxSonetApsAdvertiseInterval     OBJECT-TYPE
    SYNTAX      TimeInterval
    UNITS       "milliseconds"
    MAX-ACCESS  read-write
    STATUS      obsolete
     DESCRIPTION
        "Automatic Protection Switching (APS) is supported on 7x50 systems
         by the APS-MIB and TIMETRA-APS-MIB."
    DEFVAL { 1000 }
    ::= { tmnxSonetEntry 12 }

tmnxSonetApsAdvertiseTimeLeft  OBJECT-TYPE
    SYNTAX      TimeInterval
    UNITS       "milliseconds"
    MAX-ACCESS  read-only
    STATUS      obsolete
    DESCRIPTION
        "Automatic Protection Switching (APS) is supported on 7x50 systems
         by the APS-MIB and TIMETRA-APS-MIB."
    ::= { tmnxSonetEntry 13 }

tmnxSonetApsHoldTime      OBJECT-TYPE
    SYNTAX      TimeInterval
    UNITS       "milliseconds"
    MAX-ACCESS  read-write
    STATUS      obsolete
    DESCRIPTION
        "Automatic Protection Switching (APS) is supported on 7x50 systems
         by the APS-MIB and TIMETRA-APS-MIB."
    DEFVAL { 3000 }
    ::= { tmnxSonetEntry 14 }

tmnxSonetApsHoldTimeLeft   OBJECT-TYPE
    SYNTAX      TimeInterval
    UNITS       "milliseconds"
    MAX-ACCESS  read-only
    STATUS      obsolete
    DESCRIPTION
        "Automatic Protection Switching (APS) is supported on 7x50 systems
         by the APS-MIB and TIMETRA-APS-MIB."
   ::= { tmnxSonetEntry 15 }

tmnxSonetLoopback   OBJECT-TYPE
    SYNTAX      INTEGER {
                    none(0),
                    line(1),
                    internal(2)
                }
    MAX-ACCESS  read-write
    STATUS      current
    DESCRIPTION
        "Activate a loopback on the SONET port. The SONET port must be in a
        shutdown state to activate any type of loopback."
   ::= { tmnxSonetEntry 16 }

tmnxSonetReportAlarmStatus  OBJECT-TYPE
    SYNTAX      BITS {
                    notUsed (0),
                    loc(1),
                    lais(2),
                    lrdi(3),
                    ss1f(4),
                    sb1err(5),
                    lb2erSd(6),
                    lb2erSf(7),
                    slof(8),
                    slos(9),
                    stxptr(10),
                    srxptr(11),
                    lrei(12)
                }
    MAX-ACCESS      read-only
    STATUS          current
    DESCRIPTION
        "The bits in this object are used for indicating the alarms. The bits
         are explained as follows:
            loc(1)      Indicates a loss of clock which causes the operational
                        state of the port to be downed.
            lais(2)     Indicates line alarm indication signal errors.
            lrdi(3)     Indicates line remote defect indication errors.  LRDIs
                        are caused by remote LOF, LOC, and LOS.
            ss1f(4)     Indicates section synchronization failure as reported by
                        the S1 byte.
            sb1err(5)   Indicates section B1 errors.
            lb2erSd(6)  Indicates line signal degradation BER errors.
            lb2erSf(7)  Indicates line signal failure BER errors.
            slof(8)     Indicates section loss of frame errors.
            slos(9)     Indicates section loss of signal errors.
            stxptr(10)  Indicates a section synchronization error on the
                        transmit side. Indicates if there is a positive or
                        negative justification count per channel.
            srxptr(11)  Indicates a section synchronization error on the receive
                        side.  Indicates if there is a positive or negative
                        justification count per sonet path.
            lrei(12)    Indicates a line error condition raised by the remote
                        as a result of B1 errors received from this node.
        "
    ::= { tmnxSonetEntry 17 }

tmnxSonetSectionTraceMode  OBJECT-TYPE
    SYNTAX      INTEGER {
                    increment-z0(1),
                    byte(2),
                    string(3)
                }
    MAX-ACCESS  read-write
    STATUS      current
    DESCRIPTION
        "The tmnxSonetSectionTraceMode variable along with the
        tmnxSonetJ0String object determines the contents of
        the section trace bytes (j0/z0) in the SONET Section Header. If the
        mode is set to 'increment-z0', then the j0 byte is 0x01, and the
        z0 byte increments. If the mode is set to 'byte', then the j0 byte is
        the first octet of the tmnxSonetJ0String object and the z0 byte
        is 0xcc. If the mode is set to 'string', then the J0 byte is set to
        the 16 values in the tmnxSonetJ0String object and the z0 byte is
        0xcc."
    DEFVAL { byte }
    ::= { tmnxSonetEntry 18 }

tmnxSonetJ0String   OBJECT-TYPE
    SYNTAX      OCTET STRING (SIZE(0..16))
    MAX-ACCESS  read-write
    STATUS      current
    DESCRIPTION
        "The tmnxSonetJ0String is used with the tmnxSonetSectionTraceMode
        variable to determine the contents of the j0 byte in the SONET Section
        Header. If the tmnxSonetSectionTraceMode is increment-z0, this object
        is ignored. If the mode is byte, then the first octet of this object is
        used for the J0 byte.  The default J0 byte is 0. If the mode is string, 
        then the 16 bytes in this object are used for the J0 byte. If set to 
        less than 16 bytes it, will be padded out to 16 with zeros. The default
        value is 'Alcatel' appended with platform and product name (example: 
        `Alcatel 7x50 SR` )"
    DEFVAL { '01'H }
    ::= { tmnxSonetEntry 19 }

tmnxSonetMonS1Byte     OBJECT-TYPE
    SYNTAX      Unsigned32 (0..255)
    MAX-ACCESS  read-only
    STATUS      current
    DESCRIPTION
        "The tmnxSonetMonS1Byte variable reports the Synchronization Status
        Message from the S1 byte in the Line Overhead Header. A value of 0x00
        indicates unknown quality. A value of 0xF0 indicates
        `Do not use for synchronization`. Other values are documented in
        Telcordia GR253 and ITU G.707"
    DEFVAL { 'cc'H }
    ::= { tmnxSonetEntry 20 }

tmnxSonetMonJ0String   OBJECT-TYPE
    SYNTAX      OCTET STRING (SIZE(0..16))
    MAX-ACCESS  read-only
    STATUS      current
    DESCRIPTION
        "The tmnxSonetMonJ0String variable reports the contents of the j0 byte
         in the SONET Section Header."
    ::= { tmnxSonetEntry 21 }

tmnxSonetMonK1Byte     OBJECT-TYPE
    SYNTAX      Unsigned32 (0..255)
    MAX-ACCESS  read-only
    STATUS      current
    DESCRIPTION
        "The tmnxSonetMonK1Byte variable reports the Automatic Protection
         Switching(APS) signalling status from the K1 byte in the SONET
         Line Overhead Header."
    ::= { tmnxSonetEntry 22 }

tmnxSonetMonK2Byte     OBJECT-TYPE
    SYNTAX      Unsigned32 (0..255)
    MAX-ACCESS  read-only
    STATUS      current
    DESCRIPTION
        "The tmnxSonetMonK1Byte variable reports the Automatic Protection
         Switching(APS) signalling status from the K2 byte in the SONET
         Line Overhead Header."
    ::= { tmnxSonetEntry 23 }

tmnxSonetSingleFiber     OBJECT-TYPE
    SYNTAX      TruthValue
    MAX-ACCESS  read-write
    STATUS      current
    DESCRIPTION
        "tmnxSonetSingleFiber is used to enable/disable packet gathering and
         redirection of IP packets from a single fiber on RX port of the
         SONET interface and redistribute packets to other interfaces
         through either state routes or policy-based forwarding."
    DEFVAL { false }
    ::= { tmnxSonetEntry 24 }

tmnxSonetHoldTimeUp  OBJECT-TYPE
    SYNTAX      TmnxHoldTime (0..100)
    UNITS       "100s of milliseconds"
    MAX-ACCESS  read-write
    STATUS      current
    DESCRIPTION
        "The value of tmnxSonetHoldTimeUp is used to configure the
         hold-timer for link up event dampening.

         A value of zero (0) indicates that an up transition is reported
         immediately."
    DEFVAL { 5 }
    ::= { tmnxSonetEntry 25 }

tmnxSonetHoldTimeDown    OBJECT-TYPE
    SYNTAX      TmnxHoldTime (0..100)
    UNITS       "100s of milliseconds"
    MAX-ACCESS  read-write
    STATUS      current
    DESCRIPTION
        "The value of tmnxSonetHoldTimeDown is used to configure the
         hold-timer for link down event dampening.

         A value of zero (0) indicates that a down transition is reported
         immediately."
    DEFVAL { 0 }
    ::= { tmnxSonetEntry 26 }

tmnxSonetSuppressLoOrderAlarm  OBJECT-TYPE
    SYNTAX      TruthValue
    MAX-ACCESS  read-write
    STATUS      current
    DESCRIPTION
        "The value of tmnxSonetSuppressLoOrderAlarm specifies whether
         or not the lower order alarms on Sonet ports are suppressed."
    DEFVAL { false }
    ::= { tmnxSonetEntry 27 }

tmnxSonetTxDus                 OBJECT-TYPE
    SYNTAX      TruthValue
    MAX-ACCESS  read-write
    STATUS      current
    DESCRIPTION
        "The value of tmnxSonetTxDus specifies whether or not the value
         0xF (dus/dnu) is forced in the S1 overhead byte."
    DEFVAL      { false }
    ::= { tmnxSonetEntry 28 }

tmnxSonetTxS1Byte                OBJECT-TYPE
    SYNTAX      Unsigned32
    MAX-ACCESS  read-only
    STATUS      current
    DESCRIPTION
        "The value of tmnxSonetTxS1Byte indicates the transmitted S1 Byte."
    ::= { tmnxSonetEntry 29 }

--
--  Sonet Path Table
--
tmnxSonetPathTable OBJECT-TYPE
    SYNTAX      SEQUENCE OF TmnxSonetPathEntry
    MAX-ACCESS  not-accessible
    STATUS      current
    DESCRIPTION
        "The tmnxSonetPathTable has an entry for each sonet path
         configured in each packet over Sonet port on each IOM card
         in each chassis in the TMNX system."
    ::= { tmnxPortObjs 6 }

tmnxSonetPathEntry       OBJECT-TYPE
    SYNTAX      TmnxSonetPathEntry
    MAX-ACCESS  not-accessible
    STATUS      current
    DESCRIPTION
        "Each row entry represents a configured sonet path in a packet
         over Sonet port on a IOM card in a chassis in the system.
         The tmnxSonetPathEntry contains attributes that are
         unique to a sonet path of a 'sonet' TmnxPortType. The
         tmnxPortPortID for a sonet port includes a sonet path number
         in the lower bits.  If the sonet path number is zero, '0', it
         represents a single (clear) sonet path on the port that uses
         the full bandwidth of the sonet port.  Entries in this table
         that have the sonet path number part of their tmnxPortPortID
         index value set to zero cannot be created and deleted via
         SNMP SET operations.  They are created by the SNMP agent
         when the corresponding entry in the tmnxSonetTable is
         created.

         Entries with non-zero sonet path numbers can be created and
         deleted via SNMP SET operations using tmnxSonetPathRowStatus.
         When a row is created in the tmnxSonetPathTable, the
         agent also creates a row with the same index values in the
         tmnxPortTable.  In order to delete an entry,
         tmnxPortAdminStatus must first be set to 'outOfService'.  When
         the tmnxSonetPathEntry is deleted, the agent also deletes
         the corresponding row in the tmnxPortTable."
    INDEX   { tmnxChassisIndex, tmnxPortPortID }
    ::= { tmnxSonetPathTable 1 }

TmnxSonetPathEntry ::=
    SEQUENCE {
        tmnxSonetPathRowStatus          RowStatus,
        tmnxSonetPathLastChangeTime     TimeStamp,
        tmnxSonetPathMTU                Unsigned32,
        tmnxSonetPathScramble           TruthValue,
        tmnxSonetPathC2Byte             Unsigned32,
        tmnxSonetPathJ1String           OCTET STRING,
        tmnxSonetPathCRC                INTEGER,
        tmnxSonetPathOperMTU            Unsigned32,
        tmnxSonetPathOperMRU            Unsigned32,
        tmnxSonetPathReportAlarm        BITS,
        tmnxSonetPathAcctPolicyId       Unsigned32,
        tmnxSonetPathCollectStats       TruthValue,
        tmnxSonetPathReportAlarmStatus  BITS,
        tmnxSonetPathMonC2Byte          Unsigned32,
        tmnxSonetPathMonJ1String        OCTET STRING,
        tmnxSonetPathType                INTEGER,
        tmnxSonetPathChildType          TmnxMDAChanType
    }

tmnxSonetPathRowStatus        OBJECT-TYPE
    SYNTAX      RowStatus
    MAX-ACCESS  read-create
    STATUS      current
    DESCRIPTION
        "tmnxSonetPathRowStatus controls the creation and deletion of
         row entries in the tmnxSonetPathTable. The tmnxPortPortID
         for a sonet port includes a sonet path number in the lower bits.
         If the sonet path number is zero, '0', it represents a single
         (clear) sonet path on the port that uses the full bandwidth of
         the sonet port.  Entries in this table that have the sonet path
         number part of their tmnxPortPortID index value set to zero
         cannot be created and deleted via SNMP SET operations. They
         are created by the SNMP agent when the corresponding entry in
         the tmnxSonetTable is created.

         Entries with non-zero sonet path numbers can be created and deleted
         via SNMP SET operations.  When a row is created in the
         tmnxSonetPathTable, the agent also creates a row with the
         same index values in the tmnxPortTable.  In order to delete an
         entry, tmnxPortAdminStatus must first be set to 'outOfService'.
         When the tmnxSonetPathEntry is deleted, the agent also
         deletes the corresponding row in the tmnxPortTable for this
         sonet path port."
    ::= { tmnxSonetPathEntry 1 }

tmnxSonetPathLastChangeTime    OBJECT-TYPE
    SYNTAX      TimeStamp
    MAX-ACCESS  read-only
    STATUS      current
    DESCRIPTION
        "The tmnxSonetPathLastChangeTime variable contains the sysUpTime
         value of the most recently modified writable variable in the
         tmnxSonetPathEntry row for this sonet path."
    ::= { tmnxSonetPathEntry 2 }

tmnxSonetPathMTU  OBJECT-TYPE
    SYNTAX      Unsigned32 (0|512..9208)
    UNITS       "bytes"
    MAX-ACCESS  read-create
    STATUS      current
    DESCRIPTION
        "The size of the largest packet which can be sent/received
         on the sonet path, specified in octets.  For paths that
         are used for transmitting network datagrams, this is the
         size of the largest network datagram that can be sent on the
         sonet path.

         Setting tmnxSonetPathMTU to a value of zero (0), causes the agent
         to recalculate the default MTU size which can vary based on the
         current setting of tmnxPortMode and tmnxPortEncapType variables.
         Some typical default values are:
                1522 with mode access and encap-type bcp-null
                1526 with mode access and encap-type bcp-dot1q
                1502 with mode access and encap-type ipcp
                1506 with mode access and encap-type mplscp
                1524 with mode access and encap-type atm
                9208 with mode network
        "
    ::= { tmnxSonetPathEntry 3 }

tmnxSonetPathScramble     OBJECT-TYPE
    SYNTAX      TruthValue
    MAX-ACCESS  read-create
    STATUS      current
    DESCRIPTION
        "If the tmnxSonetPathScramble variable is set to 'true',
         SONET (SDH) payload scrambling is enabled on this sonet path.
         Both ends of the connection must use the same scrambling
         algorithm.  If tmnxSonetPathScramble is set to 'false',
         scrambling is disabled.
         The default value for non-ATM paths is 'false'.
         The default value for ATM paths is 'true'

         If the value of tmnxSonetPathC2Byte is set to the default for
         the currently configured tmnxSonetPathScramble, then changing
         the value of tmnxSonetPathScramble  for non-ATM paths causes a change
         to tmnxSonetPathC2Byte to a default value for a new scrambling
         option. The default values are as follows:
         scrambled non-ATM sonet/sdh path - C2 Byte value is 0x16
         unscrambled non-ATM sonet/sdh path - C2 Byte value is 0xCF"
    ::= { tmnxSonetPathEntry 4 }

tmnxSonetPathC2Byte     OBJECT-TYPE
    SYNTAX      Unsigned32 (0..254)
    MAX-ACCESS  read-create
    STATUS      current
    DESCRIPTION
        "The tmnxSonetPathC2Byte variable is used configure the value
         used in the SONET/SDH C2 header byte.

         For paths on an MDA that does not support channelization:
         Setting C2 equal to 0x16 indicates scrambled sonet.

         Setting C2 equal to 0xCF indicates unscrambled sonet.

         Setting C2 equal to 0x13 indicates ATM.

         For paths on an MDA that supports channelization, the default
         value is based on the value of tmnxMDAMaxChannelization.
         For 'pdhDs3' or 'pdhE3' channelization, the default value is 0x04.

         Setting tmnxSonetPathC2Byte to a value of zero(0) causes the agent
         to assign the default value to this object."
    ::= { tmnxSonetPathEntry 5 }

tmnxSonetPathJ1String   OBJECT-TYPE
    SYNTAX      OCTET STRING (SIZE(0..62))
    MAX-ACCESS  read-create
    STATUS      current
    DESCRIPTION
        "The tmnxSonetPathJ1String variable is used to configure the sonet path
        trace string to be sent in the J1 Path Overhead bytes. The bytes
        must be printable ASCII. If the string is less than 62 bytes, it
        will be padded with NULLs. For SONET framing, an additional CR (0x0D)
        / LF (0x0A) pair will be added by the driver. For SDH framing only
        16 bytes are sent in the J1 bytes. The driver will set the MSB of
        the first byte, and put the first 15 bytes of the user configured string
        as the following bytes. The driver will set the CRC-7 of the 16 bytes
        into the other 7 bits of the first byte.

        The default value is `Alcatel 7x50 SR`.
        Setting a 1-byte long string containing 0xFF will restore the default.
        Setting the string 'zeros' will send all-zeros (ASCII NULL characters
        without CR/LF or CRC-7)in the J1 bytes."
    ::= { tmnxSonetPathEntry 6 }

tmnxSonetPathCRC  OBJECT-TYPE
    SYNTAX      INTEGER {
                    crc16 (1),
                    crc32 (2)
                }
    MAX-ACCESS  read-create
    STATUS      current
    DESCRIPTION
        "The value of tmnxSonetPathCRC variable indicates the precision of
         the cyclic redundancy check.  A value of 'crc16' is a 16-bit
         CRC calculation.  A value of 'crc32' is a 32-bit CRC
         calculation.  32-bit CRC increases the error detection ability,
         but it also adds some performance overhead.

         For paths with encapsulation set to ATM the default and only
         supported value is crc32 and applies to AAL5 CRC calculations
         on that path."
    DEFVAL { crc32 }
    ::= { tmnxSonetPathEntry 7 }

tmnxSonetPathOperMTU        OBJECT-TYPE
    SYNTAX      Unsigned32
    UNITS       "bytes"
    MAX-ACCESS  read-only
    STATUS      current
    DESCRIPTION
        "The negotiated size of the largest packet which can be sent on
         the sonet path, specified in octets.  For sonet paths that are used
         for transmitting network datagrams, this is the size of the largest
         network datagram that can be sent on the sonet path."
    ::= { tmnxSonetPathEntry 8 }

tmnxSonetPathOperMRU        OBJECT-TYPE
    SYNTAX      Unsigned32
    UNITS       "bytes"
    MAX-ACCESS  read-only
    STATUS      current
    DESCRIPTION
        "The negotiated size of the largest packet that can be received
         on the sonet path, specified in octets."
    ::= { tmnxSonetPathEntry 9 }

tmnxSonetPathReportAlarm        OBJECT-TYPE
    SYNTAX      BITS {
                    notUsed (0),
                    pais(1),
                    plop(2),
                    prdi(3),
                    pb3err(4),
                    pplm(5),
                    prei(6),
                    puneq(7),
                    plcd(8)
                }
    MAX-ACCESS  read-create
    STATUS      current
    DESCRIPTION
        "The value of tmnxSonetPathReportAlarm determines when and if to
         generate tmnxEqPortSonetPathAlarm and tmnxEqPortSonetPathAlarmClear
         notifications for this port:
            pais(1)     Reports path alarm indication signal errors. Not set by
                        default.
            plop(2)     Reports path loss of pointer (per tributary) errors.
                        Set by default.
            prdi(3)     Reports path remote defect indication errors.  Not set
                        by default.
            pb3err(4)   Reports path B3 errors.  Not set by default.
            pplm(5)     Reports a path payload mismatch.  As a result the
                        path will be operationally downed.  Set by default.
            prei(6)     Reports a path error condition raised by the remote as
                        a result of B3 errors received from this node.  Not
                        set by default.
            puneq(7)    Reports unequipped path errors. Set by default.
            plcd(8)     Reports path loss of codegroup delineation error.
                        It is applicable only when the value of
                        tmnxPortEtherXGigMode is set to 'wan'.
                        Not set by default.
        "
    DEFVAL { {plop, pplm, puneq} }
    ::= { tmnxSonetPathEntry 10 }

tmnxSonetPathAcctPolicyId  OBJECT-TYPE
    SYNTAX      Unsigned32 (0..99)
    MAX-ACCESS  read-create
    STATUS      current
    DESCRIPTION
        "The value of the accounting policy must be defined prior to associating
         the policy with the sonet path. Accounting policies can only be
         associated with network sonet path.
         A non-zero value indicates the tmnxLogApPolicyId index identifying the
         policy entry in the tmnxLogApTable from the TIMETRA-LOG-MIB which is
         associated with this port.  A zero value indicates that there is no
         accounting policy associated with this port"
    DEFVAL { 0 }
    ::= { tmnxSonetPathEntry 11 }

tmnxSonetPathCollectStats        OBJECT-TYPE
    SYNTAX      TruthValue
    MAX-ACCESS  read-create
    STATUS      current
    DESCRIPTION
        "Enable/disable the collection of accounting and statistical data
         for the network sonet path. When applying accounting policies the
         data by default will be collected in the appropriate records and
         written to the designated billing file.
         When the value is set to false, the statistics are still accumulated
         by the IOM cards, however, the CPU will not obtain the results and
         write them to the billing file."
    DEFVAL { true }
    ::= { tmnxSonetPathEntry 12 }

tmnxSonetPathReportAlarmStatus        OBJECT-TYPE
    SYNTAX      BITS {
                    notUsed (0),
                    pais(1),
                    plop(2),
                    prdi(3),
                    pb3err(4),
                    pplm(5),
                    prei(6),
                    puneq(7),
                    plcd(8)
                }
    MAX-ACCESS  read-only
    STATUS      current
    DESCRIPTION
        "The bits in this object are used for indicating the alarms. The bits
         are explained as follows:
            pais(1)     Indicates path alarm indication signal errors.
            plop(2)     Indicates path loss of pointer (per tributary) errors.
            prdi(3)     Indicates path remote defect indication errors.
            pb3err(4)   Indicates path B3 errors.
            pplm(5)     Indicates a path payload mismatch.
            prei(6)     Indicates a path error condition raised by the remote as
                        a result of B3 errors received from this node.
            puneq(7)    Indicates a far-end unequipped error.
            plcd(8)     Indicates a path loss of codegroup delineation error.
                        It is applicable only when the value of
                        tmnxPortEtherXGigMode is set to 'wan'.
                        Not set by default.
        "
    ::= { tmnxSonetPathEntry 13 }

tmnxSonetPathMonC2Byte     OBJECT-TYPE
    SYNTAX      Unsigned32 (0..255)
    MAX-ACCESS  read-only
    STATUS      current
    DESCRIPTION
        "The tmnxSonetPathC2Byte variable reports the value in the SONET/SDH
         C2 header byte."
    ::= { tmnxSonetPathEntry 14 }

tmnxSonetPathMonJ1String   OBJECT-TYPE
    SYNTAX      OCTET STRING (SIZE(0..64))
    MAX-ACCESS  read-only
    STATUS      current
    DESCRIPTION
        "The tmnxSonetPathJ1String variable reports the sonet path
         trace string received in the J1 Path Overhead bytes."
    ::= { tmnxSonetPathEntry 15 }

tmnxSonetPathType       OBJECT-TYPE
    SYNTAX      INTEGER {
                    ds3 (1),
                    e3  (2),
                    vtg (3),
                    tug-2 (4),
                    tug-3 (5)
                }
    MAX-ACCESS  read-create
    STATUS      obsolete
    DESCRIPTION
        "tmnxSonetPathType specifies if the associated SONET/SDH Path
         is an asynchronous circuit, a virtual tributary group or
         a tributary unit group.
            ds3   - Configures the port or channel as service access(ds3)
            e3    - Configures the port or channel as service access(e3)
            vtg   - Configures the path as a virtual tributary group.
            tug-2 - Configures the path as a tributary unit group.
            tug-3 - Configures the port or channel for transport network use."
    DEFVAL       { ds3 }
    ::= { tmnxSonetPathEntry 16 }

tmnxSonetPathChildType      OBJECT-TYPE
    SYNTAX      TmnxMDAChanType
    MAX-ACCESS  read-create
    STATUS      current
    DESCRIPTION
        "tmnxSonetPathChildType is used to configure the type of this path.
         Some typical default values are:
           pdhDs3 for STS-1 paths
           pdhE3 for TU3 paths
           pdhE1 for VT2 paths
           pdhDs1 for VT15 paths
         Examples of valid child path types are sonetSts3, sdhTug3,
         pdhDs3, pdhE3, sonetVt15, sonetVt2, pdhDs1 and pdhE1."
    ::= { tmnxSonetPathEntry 17 }
--
--  Alcatel-Lucent SROS series Port Type Definition Table
--
tmnxPortTypeTable OBJECT-TYPE
    SYNTAX      SEQUENCE OF TmnxPortTypeEntry
    MAX-ACCESS  not-accessible
    STATUS      current
    DESCRIPTION
        "The Port type table has an entry for each Alcatel-Lucent SROS series
         port model."
    ::= { tmnxPortObjs 7 }

tmnxPortTypeEntry    OBJECT-TYPE
    SYNTAX      TmnxPortTypeEntry
    MAX-ACCESS  not-accessible
    STATUS      current
    DESCRIPTION
        "Each row entry represents an Alcatel-Lucent SROS series port model.
         Rows in this table are created by the agent at initialization and
         cannot be created or destroyed by SNMP Get or Set requests."
    INDEX   { tmnxPortTypeIndex }
    ::= { tmnxPortTypeTable 1 }

TmnxPortTypeEntry ::=
    SEQUENCE {
        tmnxPortTypeIndex        TmnxPortType,
        tmnxPortTypeName         TNamedItemOrEmpty,
        tmnxPortTypeDescription  TItemDescription,
        tmnxPortTypeStatus       TruthValue
    }

tmnxPortTypeIndex    OBJECT-TYPE
    SYNTAX      TmnxPortType
    MAX-ACCESS  not-accessible
    STATUS      current
    DESCRIPTION
        "The unique index value which identifies this type of Alcatel-Lucent
         SROS series port model."
    ::= { tmnxPortTypeEntry 1 }

tmnxPortTypeName     OBJECT-TYPE
    SYNTAX      TNamedItemOrEmpty
    MAX-ACCESS  read-only
    STATUS      current
    DESCRIPTION
        "The administrative name that identifies this type of Alcatel-Lucent
         SROS series port model.  This name string may be used in CLI
         commands to specify a particular Port model type."
    ::= { tmnxPortTypeEntry 2 }

tmnxPortTypeDescription  OBJECT-TYPE
    SYNTAX      TItemDescription
    MAX-ACCESS  read-only
    STATUS      current
    DESCRIPTION
        "A detailed description of this Alcatel-Lucent SROS series port model."
    ::= { tmnxPortTypeEntry 3 }

tmnxPortTypeStatus       OBJECT-TYPE
    SYNTAX      TruthValue
    MAX-ACCESS  read-only
    STATUS      current
    DESCRIPTION
        "When tmnxPortTypeStatus has a value of 'true' it indicates that
         this port model is supported in this revision of the management
         software.  When it has a value of 'false' there is no support."
    ::= { tmnxPortTypeEntry 4 }

--
--  Alcatel-Lucent SROS series Port Connector Type Definition Table
--
tmnxPortConnectTypeTable OBJECT-TYPE
    SYNTAX      SEQUENCE OF TmnxPortConnectTypeEntry
    MAX-ACCESS  not-accessible
    STATUS      current
    DESCRIPTION
        "The Port Connector type table has an entry for each Alcatel-Lucent
         SROS series port connector model."
    ::= { tmnxPortObjs 8 }

tmnxPortConnectTypeEntry    OBJECT-TYPE
    SYNTAX      TmnxPortConnectTypeEntry
    MAX-ACCESS  not-accessible
    STATUS      current
    DESCRIPTION
        "Each row entry represents an Alcatel-Lucent SROS series port
         Connector model.  Rows in this table are created by the agent
         at initialization and cannot be created or destroyed by SNMP
         Get or Set requests."
    INDEX   { tmnxPortConnectTypeIndex }
    ::= { tmnxPortConnectTypeTable 1 }

TmnxPortConnectTypeEntry ::=
    SEQUENCE {
        tmnxPortConnectTypeIndex        TmnxPortConnectorType,
        tmnxPortConnectTypeName         TNamedItemOrEmpty,
        tmnxPortConnectTypeDescription  TItemDescription,
        tmnxPortConnectTypeStatus       TruthValue
    }

tmnxPortConnectTypeIndex    OBJECT-TYPE
    SYNTAX      TmnxPortConnectorType
    MAX-ACCESS  not-accessible
    STATUS      current
    DESCRIPTION
        "The unique index value which identifies this type of Alcatel-Lucent
         SROS series port connector model."
    ::= { tmnxPortConnectTypeEntry 1 }

tmnxPortConnectTypeName     OBJECT-TYPE
    SYNTAX      TNamedItemOrEmpty
    MAX-ACCESS  read-only
    STATUS      current
    DESCRIPTION
        "The administrative name that identifies this type of Alcatel-Lucent
         SROS series port connector model.  This name string may be
         used in CLI commands to specify a particular port connector
         model type."
    ::= { tmnxPortConnectTypeEntry 2 }

tmnxPortConnectTypeDescription  OBJECT-TYPE
    SYNTAX      TItemDescription
    MAX-ACCESS  read-only
    STATUS      current
    DESCRIPTION
        "A detailed description of this Alcatel-Lucent SROS series port
         connector model."
    ::= { tmnxPortConnectTypeEntry 3 }

tmnxPortConnectTypeStatus       OBJECT-TYPE
    SYNTAX      TruthValue
    MAX-ACCESS  read-only
    STATUS      current
    DESCRIPTION
        "When tmnxPortConnectTypeStatus has a value of 'true' it indicates that
         this port connector model is supported in this revision of the
         chassis management software.  When it has a value of 'false' there
         is no support."
    ::= { tmnxPortConnectTypeEntry 4 }

--
--  Network Port FC Stats Table
--
tmnxPortFCStatsTable OBJECT-TYPE
    SYNTAX      SEQUENCE OF TmnxPortNetworkFCStatsEntry
    MAX-ACCESS  not-accessible
    STATUS      obsolete
    DESCRIPTION
        "The Network Port FC Stats table has an entry for each forwarding
         class defined on each network port."
    ::= { tmnxPortObjs 9 }

tmnxPortFCStatsEntry    OBJECT-TYPE
    SYNTAX      TmnxPortNetworkFCStatsEntry
    MAX-ACCESS  not-accessible
    STATUS      obsolete
    DESCRIPTION
        "Each row entry represents a set of ingress and egress packet and
         octet statistics for the given network port and forwarding class.
         Rows in this table are created by the agent when the network port
         is provisioned and cannot be created or destroyed by SNMP Get or
         Set requests."
    INDEX   { tmnxChassisIndex, tmnxPortPortID, tmnxPortFCStatsIndex }
    ::= { tmnxPortFCStatsTable 1 }

TmnxPortNetworkFCStatsEntry ::=
    SEQUENCE {
        tmnxPortFCStatsIndex             TFCName,
        tmnxPortFCStatsIngFwdInProfPkts  Counter64,
        tmnxPortFCStatsIngFwdOutProfPkts Counter64,
        tmnxPortFCStatsIngFwdInProfOcts  Counter64,
        tmnxPortFCStatsIngFwdOutProfOcts Counter64,
        tmnxPortFCStatsIngDroInProfPkts  Counter64,
        tmnxPortFCStatsIngDroOutProfPkts Counter64,
        tmnxPortFCStatsIngDroInProfOcts  Counter64,
        tmnxPortFCStatsIngDroOutProfOcts Counter64,
        tmnxPortFCStatsEgrFwdInProfPkts  Counter64,
        tmnxPortFCStatsEgrFwdOutProfPkts Counter64,
        tmnxPortFCStatsEgrFwdInProfOcts  Counter64,
        tmnxPortFCStatsEgrFwdOutProfOcts Counter64,
        tmnxPortFCStatsEgrDroInProfPkts  Counter64,
        tmnxPortFCStatsEgrDroOutProfPkts Counter64,
        tmnxPortFCStatsEgrDroInProfOcts  Counter64,
        tmnxPortFCStatsEgrDroOutProfOcts Counter64
    }

tmnxPortFCStatsIndex OBJECT-TYPE
    SYNTAX      TFCName
    MAX-ACCESS  not-accessible
    STATUS      obsolete
    DESCRIPTION
        "The forwarding class associated with these stats
         on this network port."
    ::= { tmnxPortFCStatsEntry 1 }

tmnxPortFCStatsIngFwdInProfPkts OBJECT-TYPE
    SYNTAX      Counter64
    MAX-ACCESS  read-only
    STATUS      obsolete
    DESCRIPTION
        "The number of in-profile packets (rate below CIR)
         forwarded by the ingress Qchip."
    ::= { tmnxPortFCStatsEntry 2 }

tmnxPortFCStatsIngFwdOutProfPkts OBJECT-TYPE
    SYNTAX      Counter64
    MAX-ACCESS  read-only
    STATUS      obsolete
    DESCRIPTION
        "The number of out-of-profile packets (rate above CIR)
         forwarded by the ingress Qchip."
    ::= { tmnxPortFCStatsEntry 3 }

tmnxPortFCStatsIngFwdInProfOcts OBJECT-TYPE
    SYNTAX      Counter64
    MAX-ACCESS  read-only
    STATUS      obsolete
    DESCRIPTION
        "The number of in-profile octets (rate below CIR)
         forwarded by the ingress Qchip."
    ::= { tmnxPortFCStatsEntry 4 }

tmnxPortFCStatsIngFwdOutProfOcts OBJECT-TYPE
    SYNTAX      Counter64
    MAX-ACCESS  read-only
    STATUS      obsolete
    DESCRIPTION
        "The number of out-of-profile octets (rate above CIR)
         forwarded by the ingress Qchip."
    ::= { tmnxPortFCStatsEntry 5 }

tmnxPortFCStatsIngDroInProfPkts OBJECT-TYPE
    SYNTAX      Counter64
    MAX-ACCESS  read-only
    STATUS      obsolete
    DESCRIPTION
        "The number of in-profile packets (rate below CIR)
         dropped by the ingress Qchip due to: MBS exceeded,
         buffer pool limit exceeded, etc."
    ::= { tmnxPortFCStatsEntry 6 }

tmnxPortFCStatsIngDroOutProfPkts OBJECT-TYPE
    SYNTAX      Counter64
    MAX-ACCESS  read-only
    STATUS      obsolete
    DESCRIPTION
        "The number of out-of-profile packets (rate above CIR)
         dropped by the ingress Qchip due to: MBS exceeded,
         buffer pool limit exceeded, etc."
    ::= { tmnxPortFCStatsEntry 7 }

tmnxPortFCStatsIngDroInProfOcts OBJECT-TYPE
    SYNTAX      Counter64
    MAX-ACCESS  read-only
    STATUS      obsolete
    DESCRIPTION
        "The number of in-profile octets (rate below CIR)
         dropped by the ingress Qchip due to: MBS exceeded,
         buffer pool limit exceeded, etc."
    ::= { tmnxPortFCStatsEntry 8 }

tmnxPortFCStatsIngDroOutProfOcts OBJECT-TYPE
    SYNTAX      Counter64
    MAX-ACCESS  read-only
    STATUS      obsolete
    DESCRIPTION
        "The number of out-of-profile octets (rate above CIR)
         dropped by the ingress Qchip due to: MBS exceeded,
         buffer pool limit exceeded, etc."
    ::= { tmnxPortFCStatsEntry 9 }

tmnxPortFCStatsEgrFwdInProfPkts OBJECT-TYPE
    SYNTAX      Counter64
    MAX-ACCESS  read-only
    STATUS      obsolete
    DESCRIPTION
        "The number of in-profile packets (rate below CIR)
         forwarded by the egress Qchip."
    ::= { tmnxPortFCStatsEntry 10 }

tmnxPortFCStatsEgrFwdOutProfPkts OBJECT-TYPE
    SYNTAX      Counter64
    MAX-ACCESS  read-only
    STATUS      obsolete
    DESCRIPTION
        "The number of out-of-profile packets (rate above CIR)
         forwarded by the egress Qchip."
    ::= { tmnxPortFCStatsEntry 11 }

tmnxPortFCStatsEgrFwdInProfOcts OBJECT-TYPE
    SYNTAX      Counter64
    MAX-ACCESS  read-only
    STATUS      obsolete
    DESCRIPTION
        "The number of in-profile octets (rate below CIR)
         forwarded by the egress Qchip."
    ::= { tmnxPortFCStatsEntry 12 }

tmnxPortFCStatsEgrFwdOutProfOcts OBJECT-TYPE
    SYNTAX      Counter64
    MAX-ACCESS  read-only
    STATUS      obsolete
    DESCRIPTION
        "The number of out-of-profile octets (rate above CIR)
         forwarded by the egress Qchip."
    ::= { tmnxPortFCStatsEntry 13 }

tmnxPortFCStatsEgrDroInProfPkts OBJECT-TYPE
    SYNTAX      Counter64
    MAX-ACCESS  read-only
    STATUS      obsolete
    DESCRIPTION
        "The number of in-profile packets (rate below CIR)
         dropped by the egress Qchip due to: MBS exceeded,
         buffer pool limit exceeded, etc."
    ::= { tmnxPortFCStatsEntry 14 }

tmnxPortFCStatsEgrDroOutProfPkts OBJECT-TYPE
    SYNTAX      Counter64
    MAX-ACCESS  read-only
    STATUS      obsolete
    DESCRIPTION
        "The number of out-of-profile packets (rate above CIR)
         dropped by the egress Qchip due to: MBS exceeded,
         buffer pool limit exceeded, etc."
    ::= { tmnxPortFCStatsEntry 15 }

tmnxPortFCStatsEgrDroInProfOcts OBJECT-TYPE
    SYNTAX      Counter64
    MAX-ACCESS  read-only
    STATUS      obsolete
    DESCRIPTION
        "The number of in-profile octets (rate below CIR)
         dropped by the egress Qchip due to: MBS exceeded,
         buffer pool limit exceeded, etc."
    ::= { tmnxPortFCStatsEntry 16 }

tmnxPortFCStatsEgrDroOutProfOcts OBJECT-TYPE
    SYNTAX      Counter64
    MAX-ACCESS  read-only
    STATUS      obsolete
    DESCRIPTION
        "The number of out-of-profile octets (rate above CIR)
         dropped by the egress Qchip due to: MBS exceeded,
         buffer pool limit exceeded, etc."
    ::= { tmnxPortFCStatsEntry 17 }

--
-- DS3 table
--
tmnxDS3Table OBJECT-TYPE
    SYNTAX      SEQUENCE OF TmnxDS3Entry
    MAX-ACCESS  not-accessible
    STATUS      current
    DESCRIPTION
        "The tmnxDS3Table has an entry for a DS3 physical port."
    ::= { tmnxPortObjs 10 }

tmnxDS3Entry       OBJECT-TYPE
    SYNTAX      TmnxDS3Entry
    MAX-ACCESS  not-accessible
    STATUS      current
    DESCRIPTION
        "Each row entry represents a physical DS3 port on a
         IOM card in a chassis in the system.  Entries cannot be created
         and deleted via SNMP SET operations.  Entries in this table will
         be created automatically when the tmnxMDAAssignedType object is
         set to the DS3 MDA type The tmnxDS3Entry contains attributes that are
         unique to the 'ds3e3' TmnxPortType. The tmnxPortPortID contains
         the slot, mda and port numbers encoded into it.

         For each tmnxDS3Entry, there will be a corresponding entry
         in the tmnxPortTable and the ifTable."
    INDEX       { tmnxChassisIndex, tmnxPortPortID }
    ::= { tmnxDS3Table 1 }

TmnxDS3Entry ::=
    SEQUENCE {
        tmnxDS3Buildout                 INTEGER,
        tmnxDS3LastChangeTime           TimeStamp,
        tmnxDS3Type                     INTEGER,
        tmnxDS3HoldTimeUp               TmnxHoldTime,
        tmnxDS3HoldTimeDown             TmnxHoldTime
    }

tmnxDS3Buildout    OBJECT-TYPE
    SYNTAX      INTEGER {
                    short (1),
                    long  (2)
                }
    MAX-ACCESS  read-create
    STATUS      current
    DESCRIPTION
        "tmnxDS3Buildout configures the T3 line buildout. A T3 port has two
         settings for the T3 line buildout: a short setting, which is less
         than 225 feet, and a long setting, which is greater than 225 feet.
         This object applies to copper-cable-based T3 ports only."
    DEFVAL      { short }
    ::= { tmnxDS3Entry 1 }

tmnxDS3LastChangeTime    OBJECT-TYPE
    SYNTAX      TimeStamp
    MAX-ACCESS  read-only
    STATUS      current
    DESCRIPTION
        "The tmnxDS3LastChangeTime variable contains the sysUpTime
         value of the most recently modified writable variable in the
         tmnxDS3Entry row for this port."
    ::= { tmnxDS3Entry 2 }

tmnxDS3Type     OBJECT-TYPE
    SYNTAX      INTEGER {
                    ds3(1),
                    e3(2)
                }
    MAX-ACCESS  read-create
    STATUS      current
    DESCRIPTION
        "tmnxDS3Type configures the type of the physical port to 'ds3' or 'e3'."
    DEFVAL      { ds3 }
    ::= { tmnxDS3Entry 3 }

tmnxDS3HoldTimeUp               OBJECT-TYPE
    SYNTAX      TmnxHoldTime (0..100)
    UNITS       "100s of milliseconds"
    MAX-ACCESS  read-write
    STATUS      current
    DESCRIPTION
        "The value of tmnxDS3HoldTimeUp is used to configure the
         hold-timer for link up event dampening.

         A value of zero (0) indicates that an up transition is reported
         immediately."
    DEFVAL { 0 }
    ::= { tmnxDS3Entry 4 }

tmnxDS3HoldTimeDown    OBJECT-TYPE
    SYNTAX      TmnxHoldTime (0..100)
    UNITS       "100s of milliseconds"
    MAX-ACCESS  read-write
    STATUS      current
    DESCRIPTION
        "The value of tmnxDS3HoldTimeDown is used to configure the
         hold-timer for link down event dampening.

         A value of zero (0) indicates that a down transition is reported
         immediately."
    DEFVAL { 5 }
    ::= { tmnxDS3Entry 5 }

--
-- DS3 Channel table
--
tmnxDS3ChannelTable OBJECT-TYPE
    SYNTAX      SEQUENCE OF TmnxDS3ChannelEntry
    MAX-ACCESS  not-accessible
    STATUS      current
    DESCRIPTION
        "The tmnxDS3ChannelTable has an entry for a DS3 channel."
    ::= { tmnxPortObjs 11 }

tmnxDS3ChannelEntry       OBJECT-TYPE
    SYNTAX      TmnxDS3ChannelEntry
    MAX-ACCESS  not-accessible
    STATUS      current
    DESCRIPTION
        "Each row entry represents a DS3 channel. Entries can be created
         and deleted via SNMP SET operations.  The tmnxDS3ChannelEntry
         contains attributes that are applicable to a DS3 channel which
         can belong to the DS3 physical port or belong to a container
         on a sonet path. The tmnxPortPortID contains the slot, mda and
         port numbers encoded into it.

         For each tmnxDS3ChannelEntry, there will be a corresponding entry
         in the tmnxPortTable and the ifTable."
    INDEX       { tmnxChassisIndex, tmnxPortPortID }
    ::= { tmnxDS3ChannelTable 1 }

TmnxDS3ChannelEntry ::=
    SEQUENCE {
        tmnxDS3ChannelRowStatus                RowStatus,
        tmnxDS3ChannelType                     INTEGER,
        tmnxDS3ChannelFraming                  INTEGER,
        tmnxDS3ChannelClockSource              TmnxDSXClockSource,
        tmnxDS3ChannelChannelized              INTEGER,
        tmnxDS3ChannelSubrateCSUMode           INTEGER,
        tmnxDS3ChannelSubrate                  Unsigned32,
        tmnxDS3ChannelIdleCycleFlags           TmnxDSXIdleCycleFlags,
        tmnxDS3ChannelLoopback                 TmnxDS3Loopback,
        tmnxDS3ChannelBitErrorInsertionRate    Integer32,
        tmnxDS3ChannelBERTPattern              TmnxDSXBertPattern,
        tmnxDS3ChannelBERTDuration             Unsigned32,
        tmnxDS3ChannelMDLEicString             DisplayString,
        tmnxDS3ChannelMDLLicString             DisplayString,
        tmnxDS3ChannelMDLFicString             DisplayString,
        tmnxDS3ChannelMDLUnitString            DisplayString,
        tmnxDS3ChannelMDLPfiString             DisplayString,
        tmnxDS3ChannelMDLPortString            DisplayString,
        tmnxDS3ChannelMDLGenString             DisplayString,
        tmnxDS3ChannelMDLMessageType           BITS,
        tmnxDS3ChannelFEACLoopRespond          TruthValue,
        tmnxDS3ChannelCRC                      INTEGER,
        tmnxDS3ChannelMTU                      Unsigned32,
        tmnxDS3ChannelOperMTU                  Unsigned32,
        tmnxDS3ChannelReportAlarm              TmnxDSXReportAlarm,
        tmnxDS3ChannelReportAlarmStatus        TmnxDSXReportAlarm,
        tmnxDS3ChannelLastChangeTime           TimeStamp,
        tmnxDS3ChannelInFEACLoop               TruthValue,
        tmnxDS3ChannelMDLMonPortString         DisplayString,
        tmnxDS3ChannelMDLMonGenString          DisplayString,
        tmnxDS3ChannelBERTOperStatus           TmnxDSXBertOperStatus,
        tmnxDS3ChannelBERTSynched              Unsigned32,
        tmnxDS3ChannelBERTErrors               Counter64,
        tmnxDS3ChannelBERTTotalBits            Counter64,
        tmnxDS3ChannelScramble                 TruthValue,
        tmnxDS3ChannelAcctPolicyId             Unsigned32,
        tmnxDS3ChannelCollectStats             TruthValue,
        tmnxDS3ChannelClockSyncState           TmnxDSXClockSyncState,
        tmnxDS3ChannelClockMasterPortId        TmnxPortID
    }

tmnxDS3ChannelRowStatus    OBJECT-TYPE
    SYNTAX      RowStatus
    MAX-ACCESS  read-create
    STATUS      current
    DESCRIPTION
        "tmnxDS3ChannelRowStatus controls the creation and deletion of
         row entries in the tmnxDS3ChannelTable.
         For row creation, the manager has to first calculate the
         tmnxPortPortID based on the TiMOS encoding scheme."
    ::= { tmnxDS3ChannelEntry 1 }

tmnxDS3ChannelType    OBJECT-TYPE
    SYNTAX      INTEGER {
                    ds3 (1),
                    e3  (2)
                }
    MAX-ACCESS  read-only
    STATUS      current
    DESCRIPTION
        "The value of tmnxDS3ChannelType indicates whether the channel is
         in DS3 or E3 mode."
    ::= { tmnxDS3ChannelEntry 2 }

tmnxDS3ChannelFraming    OBJECT-TYPE
    SYNTAX      INTEGER {
                    cbit (1),
                    m23  (2),
                    g751 (3),
                    g832 (4),
                    e3-unframed (5),
                    ds3-unframed (6)
                }
    MAX-ACCESS  read-create
    STATUS      current
    DESCRIPTION
        "The value of tmnxDS3ChannelFraming indicates the type of framing
         associated with the DS3 channel.
         If tmnxDS3ChannelType is set to 'ds3', the default framing is 'cbit'.
         If tmnxDS3ChannelType is set to 'e3', the default framing is 'g751'."
    DEFVAL      { cbit }
    ::= { tmnxDS3ChannelEntry 3 }

tmnxDS3ChannelClockSource    OBJECT-TYPE
    SYNTAX      TmnxDSXClockSource
    MAX-ACCESS  read-create
    STATUS      current
    DESCRIPTION
        "tmnxDS3ChannelClockSource configures the clock for transmitted data
         from either the internal clock ('nodeTimed'), or from a clock
         recovered from the line's receive data stream ('loopTimed')."
    DEFVAL      { loopTimed }
    ::= { tmnxDS3ChannelEntry 4 }

tmnxDS3ChannelChannelized    OBJECT-TYPE
    SYNTAX      INTEGER {
                    none(1),
                    ds1 (2),
                    e1  (3),
                    j1  (4)
                }
    MAX-ACCESS  read-create
    STATUS      current
    DESCRIPTION
        "tmnxDS3ChannelChannelized is used to create sub-channels of type
         'ds1' or 'e1' or 'j1' on the interface. Setting the value to 'none'
         removes the sub-channels on the interface."
    DEFVAL      { none }
    ::= { tmnxDS3ChannelEntry 5 }

tmnxDS3ChannelSubrateCSUMode    OBJECT-TYPE
    SYNTAX      INTEGER {
                    notUsed      (0),
                    digital-link (1),
                    reserved2 (2),
                    larscom      (3),
                    reserved4 (4),
                    reserved5 (5)
                }
    MAX-ACCESS  read-create
    STATUS      current
    DESCRIPTION
        "tmnxDS3ChannelSubrateCSUMode configures the channel service unit (CSU)
         compatibility mode to interoperate with existing DS3 subrate
         standards.
         This configuration applies only for a non-channelized DS3.

         Changing the value of tmnxDS3ChannelSubrateCSUMode to notUsed resets
         the value of tmnxDS3ChannelScramble to 'false'.

         Changing the value of tmnxDS3ChannelSubrateCSUMode
         resets the value of tmnxDS3ChannelSubrate to default for the mode if
         tmnxDS3ChannelSubrate is not provided."
    DEFVAL      { notUsed }
    ::= { tmnxDS3ChannelEntry 6 }

tmnxDS3ChannelSubrate    OBJECT-TYPE
    SYNTAX      Unsigned32
    MAX-ACCESS  read-create
    STATUS      current
    DESCRIPTION
        "tmnxDS3ChannelSubrate configures the subrate step.

         tmnxDS3ChannelSubrate multiplied by the granularity for a
         particular mode as defined by tmnxDS3ChannelSubrateCSUMode gives
         the absoulte subrate in kbps.

         -----------------------------------------------------------------------
          Subrate CSU Mode|Granularity|Default|Range     |Subrate speed range
         -----------------------------------------------------------------------
          notUsed         | N/A       | 0     | 0        |N/A
          digital-link    | 301 kbps  | 1     | 1 to 147 |301 kbps to 44.2 mbps
          larscom         | 3158 kbps | 1     | 1 to 14  |3158 kbps to 44.2 mbps
         ----------------------------------------------------------------------"
    ::= { tmnxDS3ChannelEntry 7 }

tmnxDS3ChannelIdleCycleFlags    OBJECT-TYPE
    SYNTAX      TmnxDSXIdleCycleFlags
    MAX-ACCESS  read-create
    STATUS      current
    DESCRIPTION
        "tmnxDS3ChannelIdleCycleFlags configures the value that the
         DS3 port transmits during idle cycle.

         The default value applies to HDLC channels only. For ATM
         channels the object does not really apply so a default value
         of 'none' is used and cannot be changed."
    DEFVAL      { flags }
    ::= { tmnxDS3ChannelEntry 8 }

tmnxDS3ChannelLoopback    OBJECT-TYPE
    SYNTAX      TmnxDS3Loopback
    MAX-ACCESS  read-create
    STATUS      current
    DESCRIPTION
        "tmnxDS3ChannelLoopback is used to put the channel into a loopback mode.
         The value of tmnxPortAdminStatus should be set to 'outOfService'
         in order for the loopback to be enabled.
         A 'line' loopback loops frames received on this port back to the
         remote system.
         A 'internal' loopback loops the frames from the local system back at
         the framer.
         When the value is set to 'remote', a signal is sent to the remote
         system to provide a line loopback."
    DEFVAL      { none }
    ::= { tmnxDS3ChannelEntry 9 }

tmnxDS3ChannelBitErrorInsertionRate    OBJECT-TYPE
    SYNTAX      Integer32 (0 | 2..7)
    MAX-ACCESS  read-create
    STATUS      current
    DESCRIPTION
        "tmnxDS3ChannelBitErrorInsertionRate is used to insert bit errors for a
         BERT test. The number of error corresponds to 10^(-rate). A rate of 7
         will cause an error rate of 10^(-7), or 1 error in every 10
         million bits transmitted.
         If the value is set to 0, it disables the insertion of bit errors
         into the BERT.
         Change in this value while the test is running is accepted but
         does not take effect until the test gets restarted."
    DEFVAL      { 0 }
    ::= { tmnxDS3ChannelEntry 10 }

tmnxDS3ChannelBERTPattern    OBJECT-TYPE
    SYNTAX      TmnxDSXBertPattern
    MAX-ACCESS  read-create
    STATUS      current
    DESCRIPTION
        "tmnxDS3ChannelBERTPattern indicates the pattern used for the
         Bit Error Rate Test (BERT). The value of tmnxDS3ChannelBERTDuration
         indicates the duration of the test.
         Setting the value of this object to 'none' terminates the test."
    DEFVAL      { none }
    ::= { tmnxDS3ChannelEntry 11 }

tmnxDS3ChannelBERTDuration    OBJECT-TYPE
    SYNTAX      Unsigned32 (0..86400)
    UNITS       "seconds"
    MAX-ACCESS  read-create
    STATUS      current
    DESCRIPTION
        "tmnxDS3ChannelBERTDuration is used to set the duration of the
         BERT test."
    ::= { tmnxDS3ChannelEntry 12 }

tmnxDS3ChannelMDLEicString    OBJECT-TYPE
    SYNTAX      DisplayString (SIZE (0..10))
    MAX-ACCESS  read-create
    STATUS      current
    DESCRIPTION
        "tmnxDS3ChannelMDLEicString configures the Equipment ID Code(EIC) of the
         Message Data Link (MDL)."
    ::= { tmnxDS3ChannelEntry 13 }

tmnxDS3ChannelMDLLicString    OBJECT-TYPE
    SYNTAX      DisplayString (SIZE (0..11))
    MAX-ACCESS  read-create
    STATUS      current
    DESCRIPTION
        "tmnxDS3ChannelMDLLicString configures the Location ID Code(LIC) of the
         Message Data Link (MDL)."
    ::= { tmnxDS3ChannelEntry 14 }

tmnxDS3ChannelMDLFicString    OBJECT-TYPE
    SYNTAX      DisplayString (SIZE (0..10))
    MAX-ACCESS  read-create
    STATUS      current
    DESCRIPTION
        "tmnxDS3ChannelMDLFicString configures the Frame ID Code(FIC) of the
         Message Data Link (MDL)."
    ::= { tmnxDS3ChannelEntry 15 }

tmnxDS3ChannelMDLUnitString    OBJECT-TYPE
    SYNTAX      DisplayString (SIZE (0..6))
    MAX-ACCESS  read-create
    STATUS      current
    DESCRIPTION
        "tmnxDS3ChannelMDLUnitString configures the Unit ID Code(UIC) of the
         Message Data Link (MDL)."
    ::= { tmnxDS3ChannelEntry 16 }

tmnxDS3ChannelMDLPfiString    OBJECT-TYPE
    SYNTAX      DisplayString (SIZE (0..38))
    MAX-ACCESS  read-create
    STATUS      current
    DESCRIPTION
        "tmnxDS3ChannelMDLPfiString configures the Facility ID Code sent in
         the Message Data Link (MDL) Path message."
    ::= { tmnxDS3ChannelEntry 17 }

tmnxDS3ChannelMDLPortString    OBJECT-TYPE
    SYNTAX      DisplayString (SIZE (0..38))
    MAX-ACCESS  read-create
    STATUS      current
    DESCRIPTION
        "tmnxDS3ChannelMDLPortString configures the port number string sent in
         the Message Data Link (MDL) idle signal message."
    ::= { tmnxDS3ChannelEntry 18 }

tmnxDS3ChannelMDLGenString    OBJECT-TYPE
    SYNTAX      DisplayString (SIZE (0..38))
    MAX-ACCESS  read-create
    STATUS      current
    DESCRIPTION
        "tmnxDS3ChannelMDLGenString configures the generator number string
         sent in the Message Data Link (MDL) test signal message."
    ::= { tmnxDS3ChannelEntry 19 }

tmnxDS3ChannelMDLMessageType    OBJECT-TYPE
    SYNTAX      BITS {
                    none (0),
                    ds3Path (1),
                    idleSignal (2),
                    testSignal (3)
                }
    MAX-ACCESS  read-create
    STATUS      current
    DESCRIPTION
        "tmnxDS3ChannelMDLMessageType configures the type of MDL message that
         is transmitted over the DS3 interface. If the value of this object is
         set to 'none', MDL messages are not transmitted.
         ds3Path(0)   - Enables transmission of the MDL path message.
                        An MDL path message, as defined by ANSI T1.107, is
                        distinguished from idle and test signal messages in
                        that it contains a facility identification code as its
                        final data element.
        idleSignal(1) - Enables transmission of the MDL idle signal message.
                        An MDL idle signal message, as defined by ANSI T1.107,
                        is distinguished from path and test signal messages in
                        that it contains a port number as its final data
                        element.
        testSignal(2) - Enables transmission of the MDL test signal message.
                        An MDL test signal message, as defined by ANSI T1.107,
                        is distinguished from path and idle signal messages in
                        that it contains a generator number as its final data
                        element."
    DEFVAL      { { none } }
    ::= { tmnxDS3ChannelEntry 20 }

tmnxDS3ChannelFEACLoopRespond    OBJECT-TYPE
    SYNTAX      TruthValue
    MAX-ACCESS  read-create
    STATUS      current
    DESCRIPTION
        "When tmnxDS3ChannelFEACLoopRespond has a value of 'true', the channel
        is enabled to respond to remote loop signals.  When it has
        a value of 'false' the port will not respond."
    DEFVAL      { false }
    ::= { tmnxDS3ChannelEntry 21 }

tmnxDS3ChannelCRC    OBJECT-TYPE
    SYNTAX      INTEGER {
                    crc16 (1),
                    crc32 (2)
                }
    MAX-ACCESS  read-create
    STATUS      current
    DESCRIPTION
        "The value of tmnxDS3ChannelCRC variable indicates the precision of
         the cyclic redundancy check.  A value of 'crc16' is a 16-bit
         CRC calculation.  A value of 'crc32' is a 32-bit CRC
         calculation.  32-bit CRC increases the error detection ability,
         but it also adds some performance overhead.

         For ATM channels, crc32 is the default and the only value supported
         and applies to AAL5 CRC calculation on that channel."
    DEFVAL      { crc16 }
    ::= { tmnxDS3ChannelEntry 22 }

tmnxDS3ChannelMTU  OBJECT-TYPE
    SYNTAX      Unsigned32 (0|512..9208)
    UNITS       "bytes"
    MAX-ACCESS  read-create
    STATUS      current
    DESCRIPTION
        "The size of the largest packet which can be sent/received
         on the port, specified in octets.  For ports that
         are used for transmitting network datagrams, this is the
         size of the largest network datagram that can be sent on the
         sonet path.

         Setting tmnxDS3ChannelMTU to a value of zero (0), causes the agent
         to recalculate the default MTU size which can vary based on the
         current setting of tmnxPortMode and tmnxPortEncapType variables.
         Some typical default values are:
                1522 with mode access and encap-type bcp-null
                1526 with mode access and encap-type bcp-dot1q
                1502 with mode access and encap-type ipcp
                4474 with mode access and encap-type frame-relay
                1524 with mode access and encap-type atm
                2092 with mode access and encap-type cem
        "
    ::= { tmnxDS3ChannelEntry 23 }

tmnxDS3ChannelOperMTU    OBJECT-TYPE
    SYNTAX      Unsigned32
    UNITS       "bytes"
    MAX-ACCESS  read-only
    STATUS      current
    DESCRIPTION
        "The negotiated size of the largest packet which can be sent on
         the channel, specified in octets.  For channels that are used
         for transmitting network datagrams, this is the size of the largest
         network datagram that can be sent."
    ::= { tmnxDS3ChannelEntry 24 }

tmnxDS3ChannelReportAlarm    OBJECT-TYPE
    SYNTAX      TmnxDSXReportAlarm
    MAX-ACCESS  read-create
    STATUS      current
    DESCRIPTION
        "The value of tmnxDS3ChannelReportAlarm determines when and if to
         generate notifications for this channel:
         ais - Reports alarm indication signal errors.
               ais alarms are issued by default.
         los - Reports loss of signal errors.
               los alarms are issued by default.
         oof - Reports out-of-frame errors.
               oof alarms are not issued by default.
         rai - Reports resource availability indicator events.
               rai alarms are not issued by default.
         looped - Reports if the far end has forced the near end to loopback.
               looped alarms are not issued by default.
         berSd - Reports DS3/E3 signal degradation bit errors.
                 berSd alarms are not issued by default.
         berSf - Reports DS3/E3 signal failure bit errors.
                 berSf alarms are not issued by default"
    DEFVAL      { {ais, los} }
    ::= { tmnxDS3ChannelEntry 25 }

tmnxDS3ChannelReportAlarmStatus    OBJECT-TYPE
    SYNTAX      TmnxDSXReportAlarm
    MAX-ACCESS  read-only
    STATUS      current
    DESCRIPTION
        "The value of tmnxDS3ChannelReportAlarmStatus indicates the current
         alarms on this port."
    ::= { tmnxDS3ChannelEntry 26 }

tmnxDS3ChannelLastChangeTime    OBJECT-TYPE
    SYNTAX      TimeStamp
    MAX-ACCESS  read-only
    STATUS      current
    DESCRIPTION
        "The tmnxDS3ChannelLastChangeTime variable contains the sysUpTime
         value of the most recently modified writable variable in the
         tmnxDS3ChannelEntry row for this port."
    ::= { tmnxDS3ChannelEntry 27 }

tmnxDS3ChannelInFEACLoop    OBJECT-TYPE
    SYNTAX      TruthValue
    MAX-ACCESS  read-only
    STATUS      current
    DESCRIPTION
        "tmnxDS3ChannelInFEACLoop indicates whether the remote end has put
         this channel in FEAC(Far End Alarm Control) loopback."
    ::= { tmnxDS3ChannelEntry 28 }

tmnxDS3ChannelMDLMonPortString    OBJECT-TYPE
    SYNTAX      DisplayString (SIZE (0..38))
    MAX-ACCESS  read-only
    STATUS      current
    DESCRIPTION
        "tmnxDS3ChannelMDLMonPortString indicates the port number string
         received in the Message Data Link (MDL) idle signal message."
    ::= { tmnxDS3ChannelEntry 29 }

tmnxDS3ChannelMDLMonGenString    OBJECT-TYPE
    SYNTAX      DisplayString (SIZE (0..38))
    MAX-ACCESS  read-only
    STATUS      current
    DESCRIPTION
        "tmnxDS3ChannelMDLMonGenString indicates the generator number string
         received in the Message Data Link (MDL) test signal message."
    ::= { tmnxDS3ChannelEntry 30 }

tmnxDS3ChannelBERTOperStatus    OBJECT-TYPE
    SYNTAX      TmnxDSXBertOperStatus
    MAX-ACCESS  read-only
    STATUS      current
    DESCRIPTION
        "tmnxDS3ChannelBERTOperStatus indicates the status of the BERT test
         as specified by TmnxDSXBertOperStatus."
    ::= { tmnxDS3ChannelEntry 31 }

tmnxDS3ChannelBERTSynched    OBJECT-TYPE
    SYNTAX      Unsigned32
    UNITS       "seconds"
    MAX-ACCESS  read-only
    STATUS      current
    DESCRIPTION
        "tmnxDS3ChannelBERTSynched is the number of seconds for which the
         BERT hardware was synchronized. This will be less than or equal to
         the duration of the last BERT test. It is valid only after
         tmnxDS3ChannelBERTOperStatus transitioned from 'active' to 'idle'
         the last time BERT was activated."
    ::= { tmnxDS3ChannelEntry 32 }

tmnxDS3ChannelBERTErrors    OBJECT-TYPE
    SYNTAX      Counter64
    MAX-ACCESS  read-only
    STATUS      current
    DESCRIPTION
        "tmnxDS3ChannelBERTErrors is the number of bit errors detected during
         the last BERT test. It is valid only after tmnxDS3ChannelBERTOperStatus
         transitioned from 'active' to 'idle' the last time BERT
         was activated."
    ::= { tmnxDS3ChannelEntry 33 }

tmnxDS3ChannelBERTTotalBits    OBJECT-TYPE
    SYNTAX      Counter64
    MAX-ACCESS  read-only
    STATUS      current
    DESCRIPTION
        "tmnxDS3ChannelBERTTotalBits is the total number of bits received
         during the last BERT test. Bits are only counted when the BERT
         hardware is synchronized. It is valid only after
         tmnxDS3ChannelBERTOperStatus transitioned from 'active' to 'idle'
         the last time BERT was activated."
    ::= { tmnxDS3ChannelEntry 34 }

tmnxDS3ChannelScramble     OBJECT-TYPE
    SYNTAX      TruthValue
    MAX-ACCESS  read-create
    STATUS      current
    DESCRIPTION
        "When tmnxDS3ChannelScramble indicates whether scrambling
         is enabled on this channel.  Both ends of the connection
         must use the same scrambling algorithm.  The default value
         is 'true' if the tmnxPortEncapType is atmEncap for this
         channel and indicates ATM payload scrambling; otherwise
         (tmnxPortEncapType is not atmEncap) the default is 'false'
         and can only be changed to true if the value of
         tmnxDS3ChannelSubrateCSUMode is digital-link (1)"
    ::= { tmnxDS3ChannelEntry 35 }

tmnxDS3ChannelAcctPolicyId     OBJECT-TYPE
    SYNTAX      Unsigned32 (0..99)
    MAX-ACCESS  read-create
    STATUS      current
    DESCRIPTION
        "The value of tmnxDS3ChannelAcctPolicyId specifies an existing
         accounting policy to use for the ds3 channel. Accounting policies can
         only be associated with network ports or channels.

         A non-zero value indicates the tmnxLogApPolicyId index identifying the
         policy entry in the tmnxLogApTable from the TIMETRA-LOG-MIB which is
         associated with this channel.  A zero value indicates that there is no
         accounting policy associated with this channel"
    DEFVAL { 0 }
    ::= { tmnxDS3ChannelEntry 36 }

tmnxDS3ChannelCollectStats     OBJECT-TYPE
    SYNTAX      TruthValue
    MAX-ACCESS  read-create
    STATUS      current
    DESCRIPTION
        "The value of tmnxDS3ChannelCollectStats specifies whether or not the
         collection of accounting and statistical data for the network ds3
         channel is collected.

         When the value is set to false, the statistics are still accumulated
         by the IOM cards, however, the CPM will not obtain the results and
         write them to the billing file.

         When applying accounting policies the data by default will be collected
         in the appropriate records and written to the designated billing file."
    DEFVAL { true }
    ::= { tmnxDS3ChannelEntry 37 }

tmnxDS3ChannelClockSyncState    OBJECT-TYPE
    SYNTAX      TmnxDSXClockSyncState
    MAX-ACCESS  read-only
    STATUS      current
    DESCRIPTION
        "The value of tmnxDS3ChannelClockSyncState indicates the current clock
         synchronization state if tmnxDS3ChannelClockSource is 'adaptive' or
         'differential'."
    ::= { tmnxDS3ChannelEntry 38 }

tmnxDS3ChannelClockMasterPortId    OBJECT-TYPE
    SYNTAX      TmnxPortID
    MAX-ACCESS  read-only
    STATUS      current
    DESCRIPTION
        "The value of tmnxDS3ChannelClockMasterPortId indicates the current
         clock synchronization master port id if tmnxDS3ChannelClockSource
         is 'adaptive' or 'differential'."
    ::= { tmnxDS3ChannelEntry 39 }


--
-- DS1 table
--
tmnxDS1Table OBJECT-TYPE
    SYNTAX      SEQUENCE OF TmnxDS1Entry
    MAX-ACCESS  not-accessible
    STATUS      current
    DESCRIPTION
        "The tmnxDS1Table has an entry for each DS1 channel."
    ::= { tmnxPortObjs 12 }

tmnxDS1Entry       OBJECT-TYPE
    SYNTAX      TmnxDS1Entry
    MAX-ACCESS  not-accessible
    STATUS      current
    DESCRIPTION
        "Each row entry represents a DS1 channel on a IOM card
         in a chassis in the system.  DS1 channel entries for DS3
         ports cannot be created and deleted via SNMP SET operations.
         Entries in this table will be created automatically when
         tmnxDS3ChannelChannelized is set to 'true'. DS1 channel entries
         for DS1 ports can be created and deleted via SNMP SET operations.
         For each tmnxDS1Entry, there will be a corresponding entry
         in the tmnxPortTable and the ifTable."
    INDEX       { tmnxChassisIndex, tmnxPortPortID }
    ::= { tmnxDS1Table 1 }

TmnxDS1Entry ::=
    SEQUENCE {
        tmnxDS1RowStatus                RowStatus,
        tmnxDS1Type                     INTEGER,
        tmnxDS1Framing                  INTEGER,
        tmnxDS1IdleCycleFlags           TmnxDSXIdleCycleFlags,
        tmnxDS1Loopback                 TmnxDS1Loopback,
        tmnxDS1InvertData               TruthValue,
        tmnxDS1BitErrorInsertionRate    Integer32,
        tmnxDS1BERTPattern              TmnxDSXBertPattern,
        tmnxDS1BERTDuration             Unsigned32,
        tmnxDS1ReportAlarm              TmnxDSXReportAlarm,
        tmnxDS1ReportAlarmStatus        TmnxDSXReportAlarm,
        tmnxDS1LastChangeTime           TimeStamp,
        tmnxDS1ClockSource              TmnxDSXClockSource,
        tmnxDS1BERTOperStatus           TmnxDSXBertOperStatus,
        tmnxDS1BERTSynched              Unsigned32,
        tmnxDS1BERTErrors               Counter64,
        tmnxDS1BERTTotalBits            Counter64,
        tmnxDS1RemoteLoopRespond        TruthValue,
        tmnxDS1InRemoteLoop             TruthValue,
        tmnxDS1InsertSingleBitError     TmnxActionType,
        tmnxDS1SignalMode               INTEGER,
        tmnxDS1ClockSyncState           TmnxDSXClockSyncState,
        tmnxDS1ClockMasterPortId        TmnxPortID,
        tmnxDS1BerSdThreshold           Unsigned32,
        tmnxDS1BerSfThreshold           Unsigned32,
        tmnxDS1NationalUseBits          BITS
    }

tmnxDS1RowStatus    OBJECT-TYPE
    SYNTAX      RowStatus
    MAX-ACCESS  read-create
    STATUS      current
    DESCRIPTION
        "tmnxDS1RowStatus controls the creation and deletion of
         row entries in the tmnxDS1Table.
         For row creation, the manager has to first calculate the
         tmnxPortPortID based on the TiMOS encoding scheme."
    ::= { tmnxDS1Entry 1 }

tmnxDS1Type    OBJECT-TYPE
    SYNTAX      INTEGER {
                    ds1(1),
                    e1 (2),
                    j1 (3)
                }
    MAX-ACCESS  read-only
    STATUS      current
    DESCRIPTION
        "The value of tmnxDS1Type indicates whether the DS1 channel is
         in DS1, E1 or J1 mode."
    ::= { tmnxDS1Entry 2 }

tmnxDS1Framing    OBJECT-TYPE
    SYNTAX      INTEGER {
                    esf (1),
                    sf  (2),
                    g704-no-crc (3),
                    g704 (4),
                    e1-unframed (5),
                    ds1-unframed (6)
                }
    MAX-ACCESS  read-create
    STATUS      current
    DESCRIPTION
        "The value of tmnxDS1Framing indicates the type of framing associated
         with the channel:
         esf            ESF (extended super frame) mode for T1 interfaces.
         sf             SF (super frame) mode for T1 interfaces.
         g704           G.704 framing format for E1 interfaces.
         g704-no-crc4   G.704 framing with no CRC4 for E1 interfaces.
         e1-unframed    E1 Unframed (G.703) mode for E1 interfaces.
         ds1-unframed   Unframed mode for T1 interfaces.

         If tmnxDS1Type is set to 'ds1', the default framing is 'esf'.
         If tmnxDS1Type is set to 'e1', the default framing is 'g704'.

         Changing the value of tmnxDS1Framing resets the values of
         tmnxDS1BerSdThreshold and tmnxDS1BerSfThreshold to defaults
         and turns off reporting of berSd and berSf alarms
         in tmnxDS1ReportAlarm."
    DEFVAL      { esf }
    ::= { tmnxDS1Entry 3 }

tmnxDS1IdleCycleFlags    OBJECT-TYPE
    SYNTAX      TmnxDSXIdleCycleFlags
    MAX-ACCESS  read-create
    STATUS      obsolete
    DESCRIPTION
        "tmnxDS1IdleCycleFlags configures the value that the DS1
         channel transmits during idle cycle."
    DEFVAL      { flags }
    ::= { tmnxDS1Entry 4 }

tmnxDS1Loopback    OBJECT-TYPE
    SYNTAX      TmnxDS1Loopback
    MAX-ACCESS  read-create
    STATUS      current
    DESCRIPTION
        "tmnxDS1Loopback is used to put the channel into a loopback mode. The
         value of tmnxPortAdminStatus should be set to 'outOfService' in order
         for the loopback to be enabled.
         A 'line' loopback loops frames received on this port back to the
         remote system.
         A 'internal' loopback loops frames from the local system back at
         the framer.
         A 'fdlAnsi' requests loopback of type FDL ANSI T1.403. This is valid
         with tmnxDS1Framing set to 'esf' framing.
         A 'fdlBellcore' requests loopback of type FDL Bellcore TR-TSY-000312.
         This is valid with tmnxDS1Framing set to 'esf'.
         A 'inbandAnsi' requests loopback of type inband ANSI T1.403. This is
         valid with tmnxDS1Framing set to 'sf'."
    DEFVAL      { none }
    ::= { tmnxDS1Entry 5 }

tmnxDS1InvertData    OBJECT-TYPE
    SYNTAX      TruthValue
    MAX-ACCESS  read-create
    STATUS      current
    DESCRIPTION
        "Setting tmnxDS1InvertData to 'true' causes all data bits to
         be inverted, to guarantee ones density. It is typically used with
         AMI line encoding."
    DEFVAL      { false }
    ::= { tmnxDS1Entry 6 }

tmnxDS1BitErrorInsertionRate    OBJECT-TYPE
    SYNTAX      Integer32 (0 | 2..7)
    MAX-ACCESS  read-create
    STATUS      current
    DESCRIPTION
        "tmnxDS1BitErrorInsertionRate is used to insert bit errors for a
         BERT test. The number of error corresponds to 10^(-rate). A rate of 7
         will cause an error rate of 10^(-7), or 1 error in every 10
         million bits transmitted.
         If the value is set to 0, disables the insertion of bit errors into
         the BERT.
         Change in this value while the test is running is accepted but
         does not take effect until the test gets restarted."
    DEFVAL      { 0 }
    ::= { tmnxDS1Entry 7 }

tmnxDS1BERTPattern    OBJECT-TYPE
    SYNTAX      TmnxDSXBertPattern
    MAX-ACCESS  read-create
    STATUS      current
    DESCRIPTION
        "tmnxDS1BERTPattern object indicates the pattern used for the
         Bit Error Rate Test (BERT). The value of tmnxDS1BERTDuration
         indicates the duration of the test.
         Setting the value to 'none' terminates the test."
    DEFVAL      { none }
    ::= { tmnxDS1Entry 8 }

tmnxDS1BERTDuration    OBJECT-TYPE
    SYNTAX      Unsigned32 (0..86400)
    UNITS       "seconds"
    MAX-ACCESS  read-create
    STATUS      current
    DESCRIPTION
        "tmnxDS1BERTDuration is used to set the duration of the BERT test."
    ::= { tmnxDS1Entry 9 }

tmnxDS1ReportAlarm    OBJECT-TYPE
    SYNTAX      TmnxDSXReportAlarm
    MAX-ACCESS  read-create
    STATUS      current
    DESCRIPTION
        "The value of tmnxDS1ReportAlarm determines when and if to
         generate notifications for this channel:
         ais - Reports alarm indication signal errors.
               ais alarms are issued by default.
         los - Reports loss of signal errors.
               los alarms are issued by default.
         oof - Reports out-of-frame errors.
               oof alarms are not issued by default.
         rai - Reports resource availability indicator events.
               rai alarms are not issued by default.
         looped - Reports if the far end has forced the near end to loopback.
               looped alarms are not issued by default.
         berSd - Reports DS1/E1/J1 signal degradation bit errors.
                 berSd alarms are not issued by default.
         berSf - Reports DS1/E1/J1 signal failure bit errors.
                 berSf alarms are not issued by default"
    DEFVAL      { {ais, los} }
    ::= { tmnxDS1Entry 10 }

tmnxDS1ReportAlarmStatus    OBJECT-TYPE
    SYNTAX      TmnxDSXReportAlarm
    MAX-ACCESS  read-only
    STATUS      current
    DESCRIPTION
        "The value of tmnxDS1ReportAlarmStatus indicates the current alarms
         on this channel."
    ::= { tmnxDS1Entry 11 }

tmnxDS1LastChangeTime    OBJECT-TYPE
    SYNTAX      TimeStamp
    MAX-ACCESS  read-only
    STATUS      current
    DESCRIPTION
        "The tmnxDS1LastChangeTime variable contains the sysUpTime
         value of the most recently modified writable variable in the
         tmnxDS1Entry row for this channel."
    ::= { tmnxDS1Entry 12 }

tmnxDS1ClockSource    OBJECT-TYPE
    SYNTAX      TmnxDSXClockSource
    MAX-ACCESS  read-create
    STATUS      current
    DESCRIPTION
        "tmnxDS1ClockSource configures the clock for transmitted data from
         either the internal clock ('nodeTimed'), or from a clock recovered
         from the line's receive data stream ('loopTimed'), or recovered
         adaptively from the rate at which the data that is received and not
         from the physical layer ('adaptive'), or recovered from the
         differential timestamp in the RTP header ('differential')."
    DEFVAL      { loopTimed }
    ::= { tmnxDS1Entry 13 }

tmnxDS1BERTOperStatus    OBJECT-TYPE
    SYNTAX      TmnxDSXBertOperStatus
    MAX-ACCESS  read-only
    STATUS      current
    DESCRIPTION
        "tmnxDS1BERTOperStatus indicates the status of the BERT test as
         specified by TmnxDSXBertOperStatus."
    ::= { tmnxDS1Entry 14 }

tmnxDS1BERTSynched    OBJECT-TYPE
    SYNTAX      Unsigned32
    UNITS       "seconds"
    MAX-ACCESS  read-only
    STATUS      current
    DESCRIPTION
        "tmnxDS1BERTSynched is the number of seconds for which the
         BERT hardware was synchronized. This will be less than or equal to
         the duration of the last BERT test. It is valid only after
         tmnxDS1BERTOperStatus transitioned from 'active' to 'idle'
         the last time BERT was activated."
    ::= { tmnxDS1Entry 15 }

tmnxDS1BERTErrors    OBJECT-TYPE
    SYNTAX      Counter64
    MAX-ACCESS  read-only
    STATUS      current
    DESCRIPTION
        "tmnxDS1BERTErrors is the number of bit errors detected during
         the last BERT test. It is valid only after tmnxDS1BERTOperStatus
         transitioned from 'active' to 'idle' the last time BERT
         was activated."
    ::= { tmnxDS1Entry 16 }

tmnxDS1BERTTotalBits    OBJECT-TYPE
    SYNTAX      Counter64
    MAX-ACCESS  read-only
    STATUS      current
    DESCRIPTION
        "tmnxDS1BERTTotalBits is the total number of bits received
         during the last BERT test. Bits are only counted when the BERT
         hardware is synchronized. It is valid only after
         tmnxDS1BERTOperStatus transitioned from 'active' to 'idle'
         the last time BERT was activated."
    ::= { tmnxDS1Entry 17 }

tmnxDS1RemoteLoopRespond    OBJECT-TYPE
    SYNTAX      TruthValue
    MAX-ACCESS  read-create
    STATUS      current
    DESCRIPTION
        "When tmnxDS1RemoteLoopRespond has a value of 'true', the channel
        is enabled to respond to remote loop signals.  When it has
        a value of 'false' the port will not respond."
    DEFVAL      { false }
    ::= { tmnxDS1Entry 18 }

tmnxDS1InRemoteLoop    OBJECT-TYPE
    SYNTAX      TruthValue
    MAX-ACCESS  read-only
    STATUS      current
    DESCRIPTION
        "tmnxDS1InRemoteLoop indicates whether the remote end has put
         this channel in remote loopback."
    ::= { tmnxDS1Entry 19 }

tmnxDS1InsertSingleBitError    OBJECT-TYPE
    SYNTAX      TmnxActionType
    MAX-ACCESS  read-create
    STATUS      current
    DESCRIPTION
        "tmnxDS1InsertSingleBitError is used to insert a single bit error for a
         BERT test."
    ::= { tmnxDS1Entry 20 }

tmnxDS1SignalMode    OBJECT-TYPE
    SYNTAX      INTEGER {
                    none (1),
                    cas  (2)
                }
    MAX-ACCESS  read-create
    STATUS      current
    DESCRIPTION
        "The value of tmnxDS1SignalMode indicates the type of signalling
         associated with the channel:
         none  - Indicates no signalling on this channel.
         cas   - Indicates Channel Associated Signalling (CAS) on this channel.
         The default signalling is 'none'. "
    DEFVAL      { none }
    ::= { tmnxDS1Entry 21 }

tmnxDS1ClockSyncState    OBJECT-TYPE
    SYNTAX      TmnxDSXClockSyncState
    MAX-ACCESS  read-only
    STATUS      current
    DESCRIPTION
        "The value of tmnxDS1ClockSyncState indicates the current clock
         synchronization state if tmnxDS1ClockSource is 'adaptive' or
         'differential'."
    ::= { tmnxDS1Entry 22 }

tmnxDS1ClockMasterPortId    OBJECT-TYPE
    SYNTAX      TmnxPortID
    MAX-ACCESS  read-only
    STATUS      current
    DESCRIPTION
        "The value of tmnxDS1ClockMasterPortId indicates the current clock
         synchronization master port id if tmnxDS1ClockSource is 'adaptive'
         or 'differential'."
    ::= { tmnxDS1Entry 23 }

tmnxDS1BerSdThreshold       OBJECT-TYPE
    SYNTAX      Unsigned32 (1|5|10|50|100)
    UNITS       "error bits in million bits received"
    MAX-ACCESS  read-create
    STATUS      current
    DESCRIPTION
        "The value of tmnxDS1BerSdThreshold specifies a bit error rate (BER)
         threshold used to determine when to send a tmnxEqPortDS1Alarm
         notification for a BER SD failure and a tmnxEqPortDS1AlarmClear
         notification for a BER SD failure clear. Bit error computed must
         reach/exceed threshold value over a pre-defined period of time
         for the tmnxEqPortSonetAlarm notification to be sent.

         The value of tmnxDS1Framing defines how the bit error is
         computed and what values of tmnxDS1BerSdThreshold are allowed.
         The following table defines this dependency:

         tmnxDS1Framing   Bit error calculation and value supported
         --------------   -----------------------------------------
           esf  (1)       each CRC error is counted as one bit error
           g704 (4)       values supported are 1,5,10,50,100

           other values   bit error alarms not supported, value
                          of tmnxDS1BerSdThreshold set to default and
                          cannot be changed

         tmnxDS1BerSdThreshold value must not exceed the value of
         tmnxDS1BerSfThreshold."
    DEFVAL { 5 }
    ::= { tmnxDS1Entry 24 }

tmnxDS1BerSfThreshold       OBJECT-TYPE
    SYNTAX      Unsigned32 (1|5|10|50|100)
    UNITS       "error bits in million bits received"
    MAX-ACCESS  read-create
    STATUS      current
    DESCRIPTION
        "The value of tmnxDS1BerSfThreshold specifies a bit error rate (BER)
         threshold used to determine when to send a tmnxEqPortDS1Alarm
         notification for a BER SF failure and a tmnxEqPortDS1AlarmClear
         notification for a BER SF failure clear. Bit error computed must
         reach/exceed threshold value over a pre-defined period of time
         for the tmnxEqPortSonetAlarm notification to be sent.

         The value of tmnxDS1Framing defines how the bit errors are
         computed and what values of tmnxDS1BerSfThreshold are allowed.
         The following table defines this dependency:

         tmnxDS1Framing   Bit error calculation and value supported
         --------------   -----------------------------------------
           esf  (1)       each CRC error is counted as one bit error
           g704 (4)       values supported are 1,5,10,50,100

           other values   bit error alarms not supported, value
                          of tmnxDS1BerSfThreshold set to default and
                          cannot be changed

         tmnxDS1BerSfThreshold value must not be smaller than
         tmnxDS1BerSdThreshold value"
    DEFVAL { 50 }
    ::= { tmnxDS1Entry 25 }

tmnxDS1NationalUseBits           OBJECT-TYPE
    SYNTAX      BITS {
                    sa4 (0),
                    sa5 (1),
                    sa6 (2),
                    sa7 (3),
                    sa8 (4)
                }
    MAX-ACCESS  read-create
    STATUS      current
    DESCRIPTION
        "The tmnxDS1NationalUseBits specifies the transmitted value for each of
         the E1 national use bits (Sa4 to Sa8).  This object is only
         applicable on E1 channels with tmnxDS1Framing set to g704-no-crc (3),
         or g704 (4)."
    DEFVAL { {} }
    ::= { tmnxDS1Entry 26 }

--
-- DS0 Channel Group Table
--
tmnxDS0ChanGroupTable   OBJECT-TYPE
    SYNTAX      SEQUENCE OF TmnxDS0ChanGroupEntry
    MAX-ACCESS  not-accessible
    STATUS      current
    DESCRIPTION
        "The tmnxDS0ChanGroupTable has an entry for DS0 channels
         grouped together and belonging to a particular DS1 channel."
    ::= { tmnxPortObjs 13 }

tmnxDS0ChanGroupEntry       OBJECT-TYPE
    SYNTAX      TmnxDS0ChanGroupEntry
    MAX-ACCESS  not-accessible
    STATUS      current
    DESCRIPTION
        "Each row entry represents one or more DS0 channels on a
         DS1 interface.  tmnxDS0ChanGroupTimeSlots object is used to add or
         remove DS0 channels from the group.

         Entries can be created and deleted via SNMP SET operations
         using the tmnxDS0ChanGroupRowStatus object.

         For each tmnxDS0ChanGroupEntry, there will be a corresponding entry
         in the tmnxPortTable and the ifTable."
    INDEX       { tmnxChassisIndex, tmnxPortPortID }
    ::= { tmnxDS0ChanGroupTable 1 }

TmnxDS0ChanGroupEntry ::=
    SEQUENCE {
        tmnxDS0ChanGroupRowStatus           RowStatus,
        tmnxDS0ChanGroupTimeSlots           TmnxDs0ChannelList,
        tmnxDS0ChanGroupSpeed               INTEGER,
        tmnxDS0ChanGroupCRC                 INTEGER,
        tmnxDS0ChanGroupMTU                 Unsigned32,
        tmnxDS0ChanGroupOperMTU             Unsigned32,
        tmnxDS0ChanGroupLastChangeTime      TimeStamp,
        tmnxDS0ChanGroupIdleCycleFlags      TmnxDSXIdleCycleFlags,
        tmnxDS0ChanGroupScramble            TruthValue,
        tmnxDS0ChanGroupAcctPolicyId        Unsigned32,
        tmnxDS0ChanGroupCollectStats        TruthValue,
        tmnxDS0ChanGroupPayloadFillType     TmnxDSXIdleFillType,
        tmnxDS0ChanGroupPayloadPattern      Unsigned32,
        tmnxDS0ChanGroupSignalFillType      TmnxDSXIdleFillType,
        tmnxDS0ChanGroupSignalPattern       Unsigned32,
        tmnxDS0ChanGroupBerSfLinkDown       TruthValue
    }

tmnxDS0ChanGroupRowStatus    OBJECT-TYPE
    SYNTAX      RowStatus
    MAX-ACCESS  read-create
    STATUS      current
    DESCRIPTION
        "tmnxDS0ChanGroupRowStatus controls the creation and deletion of
         row entries in the tmnxDS0ChanGroupTable. The tmnxPortPortID
         for a channel group includes a group ID in the lower bits.
         The manager has to first calculate the tmnxPortPortID based on the
         TiMOS encoding scheme."
    ::= { tmnxDS0ChanGroupEntry 1 }

tmnxDS0ChanGroupTimeSlots    OBJECT-TYPE
    SYNTAX      TmnxDs0ChannelList
    MAX-ACCESS  read-create
    STATUS      current
    DESCRIPTION
        "tmnxDS0ChanGroupTimeSlots is a bitmap which is used to
         add/remove DS0 timeslots from a channel group.
         The description for TmnxDs0ChannelList contains details of the
         bitmap organization.

         When a channel group is created on unframed DS1/E1, all timeslots
         as applicable to a given speed are auto-allocated and cannot be
         changed.

         When a channel group is created on a framed DS1/E1 or
         existing channel group's encapsulation is changed from ATM,
         the default of no timeslots is auto-assigned to the group.

         When a channel group  on a framed DS1/E1 is configured for
         ATM encapsulation, the ATM defaults of 0x00FFFFFF (DS1)
         and 0XFFFEFFFE (E1) are auto-assigned and cannot be changed."
    ::= { tmnxDS0ChanGroupEntry 2 }

tmnxDS0ChanGroupSpeed    OBJECT-TYPE
    SYNTAX      INTEGER {
                    speed-56 (1),
                    speed-64 (2)
                }
    MAX-ACCESS  read-create
    STATUS      current
    DESCRIPTION
        "tmnxDS0ChanGroupSpeed configures the required link speed
         for all the time slots included in this channel group."
    ::= { tmnxDS0ChanGroupEntry 3 }

tmnxDS0ChanGroupCRC    OBJECT-TYPE
    SYNTAX      INTEGER {
                    crc16 (1),
                    crc32 (2)
                }
    MAX-ACCESS  read-create
    STATUS      current
    DESCRIPTION
        "The value of tmnxDS0ChanGroupCRC variable indicates the precision of
         the cyclic redundancy check.  A value of 'crc16' is a 16-bit
         CRC calculation.  A value of 'crc32' is a 32-bit CRC
         calculation.  32-bit CRC increases the error detection ability,
         but it also adds some performance overhead.

         For channel groups with encapsulation set to ATM, the default and
         only supported value is crc32 and applies to AAL5 CRC calculations
         on that channel group."
    DEFVAL      { crc16 }
    ::= { tmnxDS0ChanGroupEntry 4 }

tmnxDS0ChanGroupMTU  OBJECT-TYPE
    SYNTAX      Unsigned32 (0|512..9208)
    UNITS       "bytes"
    MAX-ACCESS  read-create
    STATUS      current
    DESCRIPTION
        "The size of the largest packet which can be sent/received
         on the channel group, specified in octets.  For groups that
         are used for transmitting network datagrams, this is the
         size of the largest network datagram that can be sent.

         Setting tmnxDS0ChanGroupMTU to a value of zero (0), causes the agent
         to recalculate the default MTU size which can vary based on the
         current setting of tmnxPortMode and tmnxPortEncapType variables.
         Some typical default values are:
                1522 with mode access and encap-type bcp-null
                1526 with mode access and encap-type bcp-dot1q
                1502 with mode access and encap-type ipcp
                4474 with mode access and encap-type frame-relay
                1524 with mode access and encap-type atm
                2092 with mode access and encap-type cem
        "
    ::= { tmnxDS0ChanGroupEntry 5 }

tmnxDS0ChanGroupOperMTU    OBJECT-TYPE
    SYNTAX      Unsigned32
    UNITS       "bytes"
    MAX-ACCESS  read-only
    STATUS      current
    DESCRIPTION
        "The negotiated size of the largest packet which can be sent on
         the channel group, specified in octets.  For channel groups that
         are used for transmitting network datagrams, this is the size of
         the largest network datagram that can be sent."
    ::= { tmnxDS0ChanGroupEntry 6 }

tmnxDS0ChanGroupLastChangeTime    OBJECT-TYPE
    SYNTAX      TimeStamp
    MAX-ACCESS  read-only
    STATUS      current
    DESCRIPTION
        "The tmnxDS0ChanGroupLastChangeTime variable contains the sysUpTime
         value of the most recently modified writable variable in the
         tmnxDS0ChanGroupEntry row for this channel group."
    ::= { tmnxDS0ChanGroupEntry 7 }

tmnxDS0ChanGroupIdleCycleFlags    OBJECT-TYPE
    SYNTAX      TmnxDSXIdleCycleFlags
    MAX-ACCESS  read-create
    STATUS      current
    DESCRIPTION
        "tmnxDS0ChanGroupIdleCycleFlags configures the value that the
         channel group transmits during idle cycle.

         The default value applies to HDLC channels only. For ATM and CEM
         channels the object does not really apply so a default value of
         'none' is used and cannot be changed."
    DEFVAL      { flags }
    ::= { tmnxDS0ChanGroupEntry 8 }

tmnxDS0ChanGroupScramble     OBJECT-TYPE
    SYNTAX      TruthValue
    MAX-ACCESS  read-create
    STATUS      current
    DESCRIPTION
        "tmnxDS0ChanGroupScramble indicates whether payload scrambling
         is enabled on this ATM channel.  Both ends of the connection
         must use the same scrambling algorithm.  The default value
         is 'true' if the tmnxPortEncapType is atmEncap for this
         channel, otherwise the default is 'false' and not allowed to
         change."
    ::= { tmnxDS0ChanGroupEntry 9 }

tmnxDS0ChanGroupAcctPolicyId OBJECT-TYPE
    SYNTAX      Unsigned32 (0..99)
    MAX-ACCESS  read-create
    STATUS      current
    DESCRIPTION
        "The value of tmnxDS0ChanGroupAcctPolicyId specifies an existing
         accounting policy to use for the ds0 channel-group. Accounting policies
         can only be associated with network ports or channels.

         A non-zero value indicates the tmnxLogApPolicyId index identifying the
         policy entry in the tmnxLogApTable from the TIMETRA-LOG-MIB which is
         associated with this channel-group.  A zero value indicates that there
         is no accounting policy associated with this channel"
    DEFVAL { 0 }
    ::= { tmnxDS0ChanGroupEntry 10 }

tmnxDS0ChanGroupCollectStats     OBJECT-TYPE
    SYNTAX      TruthValue
    MAX-ACCESS  read-create
    STATUS      current
    DESCRIPTION
        "The value of tmnxDS0ChanGroupCollectStats specifies whether or not the
         collection of accounting and statistical data for the network ds0
         channel-group is collected.

         When the value is set to false, the statistics are still accumulated
         by the IOM cards, however, the CPM will not obtain the results and
         write them to the billing file.

         When applying accounting policies the data by default will be collected
         in the appropriate records and written to the designated billing file."
    DEFVAL { true }
    ::= { tmnxDS0ChanGroupEntry 11 }

tmnxDS0ChanGroupPayloadFillType  OBJECT-TYPE
    SYNTAX      TmnxDSXIdleFillType
    MAX-ACCESS  read-create
    STATUS      current
    DESCRIPTION
        "The value of tmnxDS0ChanGroupPayloadFillType specifies the type of
         idle payload fill to be sent when the CEM channel group experiences
         an underrun.

         If the type is set to 'userDefinedPattern' then the value of
         tmnxDS0ChanGroupPayloadPattern is used to define the payload pattern.

         The default value depends on the encap type of the channel group:
         For CEM encap           - 'allOnes'
         For all other encaps    - 'notApplicable'

         For a ds1-unframed and e1-unframed CEM encap DS0 channel group the
         only supported value is 'allOnes'.

         For non-CEM encap channel groups the value cannot be changed."
    DEFVAL { notApplicable }
    ::= { tmnxDS0ChanGroupEntry 12 }

tmnxDS0ChanGroupPayloadPattern   OBJECT-TYPE
    SYNTAX      Unsigned32 (0..255)
    MAX-ACCESS  read-create
    STATUS      current
    DESCRIPTION
        "The value of tmnxDS0ChanGroupPayloadPattern specifies the idle payload
         fill pattern when the CEM channel group experiences an underrun and
         tmnxDS0ChanGroupPayloadFillType is set to 'userDefinedPattern'.

         The default value depends on the encap type of the channel group:
         For CEM encap channel group             - 255 (Valid range 0..255)
         For non-CEM encap channel group         -   0 (Valid range 0..0)."
    DEFVAL { 0 }
    ::= { tmnxDS0ChanGroupEntry 13 }

tmnxDS0ChanGroupSignalFillType   OBJECT-TYPE
    SYNTAX      TmnxDSXIdleFillType
    MAX-ACCESS  read-create
    STATUS      current
    DESCRIPTION
        "The value of tmnxDS0ChanGroupSignalFillType specifies the type of
         idle signal fill to be sent when the CAS CEM channel group experiences
         an underrun.

         If the type is set to 'userDefinedPattern' then the value of
         tmnxDS0ChanGroupSignalPattern is used to define the signal pattern.

         The default value depends on the encap of the DS0 channel group and
         the signal-mode of the DS1/E1:
         For CEM encap on DS1/E1 with CAS signal mode    - 'allOnes'
         For all other encaps or non-CAS CEM DS1/E1      - 'notApplicable'

         For CEM channel groups on DS1/E1 with no CAS signalling and non-CEM
         encap channel groups the value cannot be changed."
    DEFVAL {  notApplicable }
    ::= { tmnxDS0ChanGroupEntry 14 }

tmnxDS0ChanGroupSignalPattern   OBJECT-TYPE
    SYNTAX      Unsigned32 (0..15)
    MAX-ACCESS  read-create
    STATUS      current
    DESCRIPTION
        "The value of tmnxDS0ChanGroupSignalPattern specifies the idle signal
         fill pattern when the CAS CEM channel group experiences an underrun
         and tmnxDS0ChanGroupSignalFillType is set to 'userDefinedPattern'.

         CAS ESF DS1 and CAS E1 support 4 signalling bits per timeslot (ABCD)
         CAS SF DS1 supports 2 signalling bits per timeslot (AB)

         The default value depends on the type of channel group:
         For CAS DS1 ESF or CAS E1 channel group -  15 (Valid range 0..15)
         For CAS DS1 SF channel group            -   3 (Valid range 0..3)
         For non-CAS or non-CEM channel group    -   0 (Valid range 0..0)"
    DEFVAL { 0 }
    ::= { tmnxDS0ChanGroupEntry 15 }

tmnxDS0ChanGroupBerSfLinkDown    OBJECT-TYPE
    SYNTAX      TruthValue
    MAX-ACCESS  read-create
    STATUS      current
    DESCRIPTION
        "The value of tmnxDS0ChanGroupBerSfLinkDown specifies whether or not
         the DS0 channel-group will become operationally down when a BER-SF
         alarm is raised. If tmnxDS0ChanGroupBerSfLinkDown is false then the
         channel-group will not operationally change state due to BER-SF
         alarms."
    DEFVAL { false }
    ::= { tmnxDS0ChanGroupEntry 16 }

--
-- Bundle Table
--
tmnxBundleTable   OBJECT-TYPE
    SYNTAX      SEQUENCE OF TmnxBundleEntry
    MAX-ACCESS  not-accessible
    STATUS      current
    DESCRIPTION
        "The tmnxBundleTable has an entry for a bundle created on the system."
    ::= { tmnxPortObjs 14 }

tmnxBundleEntry       OBJECT-TYPE
    SYNTAX      TmnxBundleEntry
    MAX-ACCESS  not-accessible
    STATUS      current
    DESCRIPTION
        "Each row entry represents a multilink bundle on a MDA.
         Entries can be created and deleted via SNMP SET operations
         using the tmnxBundleRowStatus object. The tmnxBundleBundleID will
         contain the bundle number encoded in it. The bundle number is
         unique for a MDA.
         For each tmnxBundleEntry, there will be a corresponding entry
         in the tmnxPortTable and the ifTable."
    INDEX       { tmnxChassisIndex, tmnxBundleBundleID }
    ::= { tmnxBundleTable 1 }

TmnxBundleEntry ::=
    SEQUENCE {
        tmnxBundleBundleID            TmnxBundleID,
        tmnxBundleRowStatus           RowStatus,
        tmnxBundleType                INTEGER,
        tmnxBundleMinimumLinks        Unsigned32,
        tmnxBundleNumLinks            Unsigned32,
        tmnxBundleNumActiveLinks      Unsigned32,
        tmnxBundleMRRU                Unsigned32,
        tmnxBundleOperMRRU            Unsigned32,
        tmnxBundlePeerMRRU            Unsigned32,
        tmnxBundleOperMTU             Unsigned32,
        tmnxBundleRedDiffDelay        Unsigned32,
        tmnxBundleRedDiffDelayAction  INTEGER,
        tmnxBundleYellowDiffDelay     Unsigned32,
        tmnxBundleShortSequence       TruthValue,
        tmnxBundleLastChangeTime      TimeStamp,
        tmnxBundleFragmentThreshold   Unsigned32,
        tmnxBundleUpTime              Unsigned32,
        tmnxBundleInputDiscards       Counter32,
        tmnxBundlePrimaryMemberPortID TmnxPortID,
        tmnxBundleLFI                 TruthValue,
        tmnxBundleProtectedType       INTEGER,
        tmnxBundleParentBundle        TmnxBundleID
   }

tmnxBundleBundleID    OBJECT-TYPE
    SYNTAX      TmnxBundleID
    MAX-ACCESS  not-accessible
    STATUS      current
    DESCRIPTION
        "tmnxBundleBundleID identifies this multilink bundle. The value of
         this object is calculated using the TiMOS encoding scheme described
         in TmnxBundleID.
         tmnxBundleBundleID is used as an index into the ifTable and the
         tmnxPortTable to access an entry corresponding to this entry."
    ::= { tmnxBundleEntry 1 }

tmnxBundleRowStatus    OBJECT-TYPE
    SYNTAX      RowStatus
    MAX-ACCESS  read-create
    STATUS      current
    DESCRIPTION
        "tmnxBundleRowStatus controls the creation and deletion of
         row entries in the tmnxBundleTable.

         The manager has to first calculate the tmnxBundleBundleID
         based on the TiMOS encoding."
    ::= { tmnxBundleEntry 2 }

tmnxBundleType    OBJECT-TYPE
    SYNTAX      INTEGER {
                    mlppp (1),
                    mlfr  (2),
                    imagrp (3)
                }
    MAX-ACCESS  read-create
    STATUS      current
    DESCRIPTION
        "tmnxBundleType specifies the type of this multilink bundle.
         It provides a reference as to the type of bundle this row
         refers to but does not map to the direct value of
         bndle type defined in TmnxBundleID."
    DEFVAL      { mlppp }
    ::= { tmnxBundleEntry 3 }

tmnxBundleMinimumLinks    OBJECT-TYPE
    SYNTAX      Unsigned32 (1..8)
    MAX-ACCESS  read-create
    STATUS      current
    DESCRIPTION
        "tmnxBundleMinimumLinks is the minimum number of links that must be
         active for a bundle to be active. If the number of links drop below
         the given minimum then the multilink bundle will transition to an
         operation down state."
    ::= { tmnxBundleEntry 4 }

tmnxBundleNumLinks    OBJECT-TYPE
    SYNTAX      Unsigned32
    MAX-ACCESS  read-only
    STATUS      current
    DESCRIPTION
        "tmnxBundleNumLinks indicates the total number of links configured
         for this bundle."
    ::= { tmnxBundleEntry 5 }

tmnxBundleNumActiveLinks    OBJECT-TYPE
    SYNTAX      Unsigned32
    MAX-ACCESS  read-only
    STATUS      current
    DESCRIPTION
        "tmnxBundleNumActiveLinks indicates the current number of active links
         belonging to this bundle."
    ::= { tmnxBundleEntry 6 }

tmnxBundleMRRU    OBJECT-TYPE
    SYNTAX      Unsigned32 (0|1500..9206)
    UNITS       "bytes"
    MAX-ACCESS  read-create
    STATUS      current
    DESCRIPTION
        "tmnxBundleMRRU is used to configure the
         Max Received Reconstructed Unit (MRRU). This is the maximum frame that
         can be reconstructed from multilink fragments.
         This object is only applicable to tmnxBundleType value of mlppp.
         All non applicable types have a value of zero."
    DEFVAL      { 1524 }
    ::= { tmnxBundleEntry 7 }

tmnxBundleOperMRRU    OBJECT-TYPE
    SYNTAX      Unsigned32
    UNITS       "bytes"
    MAX-ACCESS  read-only
    STATUS      current
    DESCRIPTION
        "tmnxBundleOperMRRU indicates the operational value of
         Max Received Reconstructed Unit (MRRU).
         This object is only applicable to tmnxBundleType value of mlppp.
         All non applicable types have a value of zero."
    ::= { tmnxBundleEntry 8 }

tmnxBundlePeerMRRU    OBJECT-TYPE
    SYNTAX      Unsigned32
    UNITS       "bytes"
    MAX-ACCESS  read-only
    STATUS      current
    DESCRIPTION
        "tmnxBundlePeerMRRU indicates the MRRU value sent by the peer
         during negotiation.
         This object is only applicable to tmnxBundleType value of mlppp.
         All non applicable types have a value of zero."
    ::= { tmnxBundleEntry 9 }

tmnxBundleOperMTU    OBJECT-TYPE
    SYNTAX      Unsigned32
    UNITS       "bytes"
    MAX-ACCESS  read-only
    STATUS      current
    DESCRIPTION
        "tmnxBundleOperMTU indicates the operational MTU of the bundle."
    ::= { tmnxBundleEntry 10 }

tmnxBundleRedDiffDelay    OBJECT-TYPE
    SYNTAX      Unsigned32 (0..25|0..50)
    UNITS       "milliseconds"
    MAX-ACCESS  read-create
    STATUS      current
    DESCRIPTION
        "tmnxBundleRedDiffDelay configures the maximum acceptable differential
         delay for individual circuits within this multilink bundle. If
         the delay exceeds this threshold, a tmnxEqPortBndlRedDiffExceeded
         trap is issued.

         For a tmnxBundleType value of 'imagrp' a range of 0 to 50 is supported,
         0 to 25 otherwise."
    ::= { tmnxBundleEntry 11 }

tmnxBundleRedDiffDelayAction    OBJECT-TYPE
    SYNTAX      INTEGER {
                    none (0),
                    down (1)
                }
    MAX-ACCESS  read-create
    STATUS      current
    DESCRIPTION
        "tmnxBundleRedDiffDelayAction specifies the action to be taken
         when the differential delay exceeds the threshold configured in
         tmnxBundleRedDiffDelay.
         For a tmnxBundleType value of 'imagrp', only the down action is
         supported."
    DEFVAL      { none }
    ::= { tmnxBundleEntry 12 }

tmnxBundleYellowDiffDelay    OBJECT-TYPE
    SYNTAX      Unsigned32 (0..25)
    UNITS       "milliseconds"
    MAX-ACCESS  read-create
    STATUS      current
    DESCRIPTION
        "tmnxBundleYellowDiffDelay configures the yellow warning
         threshold for the differential delay for the circuits
         within a given multilink bundle. If the delay exceeds this
         threshold, a tmnxEqPortBndlYellowDiffExceeded trap is issued.
         This object is only applicable to tmnxBundleType values of
         'mlppp' or 'mlfr'. All non applicable types have a value
         of zero."
    ::= { tmnxBundleEntry 13 }

tmnxBundleShortSequence    OBJECT-TYPE
    SYNTAX      TruthValue
    MAX-ACCESS  read-create
    STATUS      current
    DESCRIPTION
        "tmnxBundleShortSequence command specifies that the MLPPP bundle
         should use short (12 bit) sequence numbers. Instead of the
         standard long (24 bits) sequence number.
         This object is only applicable to tmnxBundleType value of mlppp."
    DEFVAL      { false }
    ::= { tmnxBundleEntry 14 }

tmnxBundleLastChangeTime    OBJECT-TYPE
    SYNTAX      TimeStamp
    MAX-ACCESS  read-only
    STATUS      current
    DESCRIPTION
        "The tmnxBundleLastChangeTime variable contains the sysUpTime
         value of the most recently modified writable variable in the
         tmnxBundleEntry row for this channel group."
    ::= { tmnxBundleEntry 15 }

tmnxBundleFragmentThreshold     OBJECT-TYPE
    SYNTAX      Unsigned32(0|128..512)
    UNITS       "bytes"
    MAX-ACCESS  read-create
    STATUS      current
    DESCRIPTION
        "The value of tmnxBundleFragmentThreshold specifies the maximum length
         of a fragment transmitted across the multilink bundle. Values supported
         within each bundle type are hardware dependent. The value of 0
         specifies no fragmentation.

         Currently, the following values are supported depending upon the
         tmnxBundleType value:

             tmnxBundleType         tmnxBundleFragmentThreshold values supported
              mlppp                   0; 128 to 512 inclusive
              imagrp                  128
              mlfr                    0; 128 to 512 inclusive"
    DEFVAL      { 128 }
    ::= { tmnxBundleEntry 16 }

tmnxBundleUpTime    OBJECT-TYPE
    SYNTAX      Unsigned32
    UNITS       "seconds"
    MAX-ACCESS  read-only
    STATUS      current
    DESCRIPTION
        "tmnxBundleUpTime indicates the time since the bundle is operationally
         'inService'."
    ::= { tmnxBundleEntry 17 }

tmnxBundleInputDiscards    OBJECT-TYPE
    SYNTAX      Counter32
    MAX-ACCESS  read-only
    STATUS      current
    DESCRIPTION
        "tmnxBundleInputDiscards indicates the number of LCP packets that
         were discarded. This object is only supported for a
         tmnxBundleType value of mlppp."
    ::= { tmnxBundleEntry 18 }

tmnxBundlePrimaryMemberPortID    OBJECT-TYPE
    SYNTAX      TmnxPortID
    MAX-ACCESS  read-only
    STATUS      current
    DESCRIPTION
        "tmnxBundlePrimaryMemberPortID indicates the TmnxPortID of the primary
         member of this bundle. The value of this object will be zero if
         there are no members configured in this bundle."
    ::= { tmnxBundleEntry 19 }

tmnxBundleLFI    OBJECT-TYPE
    SYNTAX      TruthValue
    MAX-ACCESS  read-create
    STATUS      current
    DESCRIPTION
        "tmnxBundleLFI specifies if Link Fragmentation and
         Interleaving is enabled on the multilink bundle. A value of 'false'
         indicates that Link Fragmentation and Interleaving is disabled on the
         multilink bundle while a value of 'true' indicates that Link
         Fragmentation and Interleaving is enabled on the multilink bundle.

         This object is only supported for tmnxBundleType value of mlppp.

         The value of tmnxBundleLFI may be modified only when no members are
         part of the bundle.

         This object cannot be set to true when tmnxBundleMlpppClassCount object
         value is set to enable Multiclass MLPPP on the bundle."
    DEFVAL      { false }
    ::= { tmnxBundleEntry 20 }

tmnxBundleProtectedType OBJECT-TYPE
    SYNTAX      INTEGER {
                    none       (0),
                    working    (1),
                    protection (2)
                }
    MAX-ACCESS  read-create
    STATUS      current
    DESCRIPTION
        "tmnxBundleProtectedType identifies how this bundle is part
         of a tmnxBundleParentBundle. A value of 'none' identifies no
         protection, 'working' identifies it to be a working bundle of a
         tmnxBundleParentBundle and 'protection' identifies it to be a
         protection bundle of a tmnxBundleParentBundle.
        tmnxBundleProtectedType can only be set at row creation."
    DEFVAL { none }
    ::= { tmnxBundleEntry 21 }

tmnxBundleParentBundle OBJECT-TYPE
    SYNTAX      TmnxBundleID
    MAX-ACCESS  read-create
    STATUS      current
    DESCRIPTION
        "tmnxBundleParentBundle specifies the parent to which this bundle
         belongs.  A row for the given non zero walue of tmnxBundleParentBundle
         must exist for this row to be successfully created. If a bundle has no
         parent, its value is zero. tmnxBundleParentBundle can only be set at
         row creation."
    DEFVAL { 0 }
    ::= { tmnxBundleEntry 22 }

--
-- Bundle Link Table
--
tmnxBundleMemberTable   OBJECT-TYPE
    SYNTAX      SEQUENCE OF TmnxBundleMemberEntry
    MAX-ACCESS  not-accessible
    STATUS      current
    DESCRIPTION
        "The tmnxBundleMemberTable has an entry for a member port
         associated with a multilink bundle."
    ::= { tmnxPortObjs 15 }

tmnxBundleMemberEntry       OBJECT-TYPE
    SYNTAX      TmnxBundleMemberEntry
    MAX-ACCESS  not-accessible
    STATUS      current
    DESCRIPTION
        "Each row represents a port associated with a bundle. Entries
         can be added or removed from this table using SNMP SET operation."
    INDEX   { tmnxBundleBundleID, tmnxPortPortID }
    ::= { tmnxBundleMemberTable 1 }

TmnxBundleMemberEntry ::=
    SEQUENCE {
        tmnxBundleMemberRowStatus           RowStatus,
        tmnxBundleMemberActive              TruthValue,
        tmnxBundleMemberDownReason          INTEGER,
        tmnxBundleMemberUpTime              Unsigned32
    }

tmnxBundleMemberRowStatus    OBJECT-TYPE
    SYNTAX      RowStatus
    MAX-ACCESS  read-create
    STATUS      current
    DESCRIPTION
        "tmnxBundleMemberRowStatus controls the creation and deletion of
         row entries in the tmnxBundleMemberTable.
         tmnxPortPortID identifies the port to be associated with the bundle.
         A bundle entry with tmnxBundleBundleID has to exist in the
         tmnxBundleTable before creating an entry in this table."
    ::= { tmnxBundleMemberEntry 1 }

tmnxBundleMemberActive    OBJECT-TYPE
    SYNTAX      TruthValue
    MAX-ACCESS  read-only
    STATUS      current
    DESCRIPTION
        "tmnxBundleMemberActive is set to 'false' for one of reasons in
         tmnxBundleMemberDownReason."
    ::= { tmnxBundleMemberEntry 2 }

tmnxBundleMemberDownReason    OBJECT-TYPE
    SYNTAX      INTEGER {
                    none (0),
                    outOfService (1),
                    redDiffDelayExceeded (2),
                    mismatchEndPtDiscriminator (3),
                    peerNotBundleMember (4),
                    underNegotiation (5),
                    peerInvalidMlHdrFmt(6),
                    other(7)
                }
    MAX-ACCESS  read-only
    STATUS      current
    DESCRIPTION
        "tmnxBundleMemberDownReason contains the reason code for marking
         the member link of the bundle to down (i.e. tmnxBundleMemberActive
         will be set to false):
             none - The link is active and the value of tmnxBundleMemberActive
                    is 'true'.
             outOfService - The link operational status is down.
             redDiffDelayExceeded - The differential delay of the link
                    exceeded the configured value of red differential delay
                    and tmnxBundleRedDiffDelayAction was configured as 'down'.
             mismatchEndPtDiscriminator - Detected inconsistent peer endpoint
                    discriminator for the bundle.
             peerNotBundleMember - When the peer is either not added to the
                    bundle or is removed from the bundle.
             underNegotiation - When the local end is trying to negotiate with
                    the peer.
             peerInvalidMlHdrFmt - The peer does not support the required ML-PPP
                    header format. The remote peer must support the same
                    short/long sequence code, and at least as many classes as
                    configured for the local bundle.
             other - Refer to the corresponding member table, if any, for more
                     information based on the tmnxBundleType.
        "
    ::= { tmnxBundleMemberEntry 3 }

tmnxBundleMemberUpTime    OBJECT-TYPE
    SYNTAX      Unsigned32
    UNITS       "seconds"
    MAX-ACCESS  read-only
    STATUS      current
    DESCRIPTION
        "tmnxBundleMemberUpTime indicates the time since the bundle member is
         active as indicated by tmnxBundleMemberActive."
    ::= { tmnxBundleMemberEntry 4 }

--
-- Physical Port to Channel Mapping Table
--
tmnxPortToChannelTable   OBJECT-TYPE
    SYNTAX      SEQUENCE OF TmnxPortToChannelEntry
    MAX-ACCESS  not-accessible
    STATUS      current
    DESCRIPTION
        "The tmnxPortToChannelTable is a mapping table. Given a chassis index,
         physical port index and channel string, it maps it to the index
         of the channel. This channel index can then be used as an index
         into the ifTable or the tmnxPortTable."
    ::= { tmnxPortObjs 16 }

tmnxPortToChannelEntry       OBJECT-TYPE
    SYNTAX      TmnxPortToChannelEntry
    MAX-ACCESS  not-accessible
    STATUS      current
    DESCRIPTION
        "Each row represents a mapping of the physical port index and the
         channel index string to the index of the channel."
    INDEX   { tmnxChassisIndex, tmnxPortPortID, tmnxChannelIdxString }
    ::= { tmnxPortToChannelTable 1 }

TmnxPortToChannelEntry ::=
    SEQUENCE {
        tmnxChannelIdxString     DisplayString,
        tmnxChannelPortID        TmnxPortID
    }

tmnxChannelIdxString    OBJECT-TYPE
    SYNTAX      DisplayString
    MAX-ACCESS  not-accessible
    STATUS      current
    DESCRIPTION
        "tmnxChannelIdxString is an index into the table. It contains
         a string identifying a channel on the physical port."
    ::= { tmnxPortToChannelEntry 1 }

tmnxChannelPortID    OBJECT-TYPE
    SYNTAX      TmnxPortID
    MAX-ACCESS  read-only
    STATUS      current
    DESCRIPTION
        "tmnxChannelPortID contains the port ID of the channel. This value
         is used to identify the entry for this channel in the ifTable or
         the tmnxPortTable."
    ::= { tmnxPortToChannelEntry 2 }

--
--  Port Ingress MDA QoS Queue Drop Stats Table
--
tmnxPortIngrMdaQosStatTable OBJECT-TYPE
    SYNTAX      SEQUENCE OF TmnxPortIngrMdaQosStatEntry
    MAX-ACCESS  not-accessible
    STATUS      current
    DESCRIPTION
        "The table tmnxPortIngrMdaQosStatTable contains a row for each ethernet
         or SONET/SDH port located on an oversubscribed MDA.

         Each object in a row refers to a QoS priority and forwarding class,
         which is a decimal value between 00 and 15 inclusive.  The following
         table describes each decimal value:

                              | Priority
                              |------------------
         Forwarding Class     | High       Low
         ----------------------------------------
         NC (Network Control) | 00         01
         H1 (Voice)           | 02         03
         EF (Premium)         | 04         05
         H2 (Video)           | 06         07
         L1 (Management)      | 08         09
         AF (Assured)         | 10         11
         L2 (Priority)        | 12         13
         BE (Best Effort)     | 14         15"
    ::= { tmnxPortObjs 17 }

tmnxPortIngrMdaQosStatEntry    OBJECT-TYPE
    SYNTAX      TmnxPortIngrMdaQosStatEntry
    MAX-ACCESS  not-accessible
    STATUS      current
    DESCRIPTION
        "Each row indicates the MDA QoS discard statistics on an ethernet or
         SONET/SDH port located on an oversubscribed MDA. For ethernet ports,
         the tmnxPortEtherIngressRate object indicates the ingress shaping
         rate configured."
    INDEX   { tmnxChassisIndex, tmnxPortPortID }
    ::= { tmnxPortIngrMdaQosStatTable 1 }

TmnxPortIngrMdaQosStatEntry ::=
    SEQUENCE {
        tmnxPortIngrMdaQos00StatDropPkts   Counter64,
        tmnxPortIngrMdaQos00StatDropOcts   Counter64,
        tmnxPortIngrMdaQos01StatDropPkts   Counter64,
        tmnxPortIngrMdaQos01StatDropOcts   Counter64,
        tmnxPortIngrMdaQos02StatDropPkts   Counter64,
        tmnxPortIngrMdaQos02StatDropOcts   Counter64,
        tmnxPortIngrMdaQos03StatDropPkts   Counter64,
        tmnxPortIngrMdaQos03StatDropOcts   Counter64,
        tmnxPortIngrMdaQos04StatDropPkts   Counter64,
        tmnxPortIngrMdaQos04StatDropOcts   Counter64,
        tmnxPortIngrMdaQos05StatDropPkts   Counter64,
        tmnxPortIngrMdaQos05StatDropOcts   Counter64,
        tmnxPortIngrMdaQos06StatDropPkts   Counter64,
        tmnxPortIngrMdaQos06StatDropOcts   Counter64,
        tmnxPortIngrMdaQos07StatDropPkts   Counter64,
        tmnxPortIngrMdaQos07StatDropOcts   Counter64,
        tmnxPortIngrMdaQos08StatDropPkts   Counter64,
        tmnxPortIngrMdaQos08StatDropOcts   Counter64,
        tmnxPortIngrMdaQos09StatDropPkts   Counter64,
        tmnxPortIngrMdaQos09StatDropOcts   Counter64,
        tmnxPortIngrMdaQos10StatDropPkts   Counter64,
        tmnxPortIngrMdaQos10StatDropOcts   Counter64,
        tmnxPortIngrMdaQos11StatDropPkts   Counter64,
        tmnxPortIngrMdaQos11StatDropOcts   Counter64,
        tmnxPortIngrMdaQos12StatDropPkts   Counter64,
        tmnxPortIngrMdaQos12StatDropOcts   Counter64,
        tmnxPortIngrMdaQos13StatDropPkts   Counter64,
        tmnxPortIngrMdaQos13StatDropOcts   Counter64,
        tmnxPortIngrMdaQos14StatDropPkts   Counter64,
        tmnxPortIngrMdaQos14StatDropOcts   Counter64,
        tmnxPortIngrMdaQos15StatDropPkts   Counter64,
        tmnxPortIngrMdaQos15StatDropOcts   Counter64
    }

tmnxPortIngrMdaQos00StatDropPkts OBJECT-TYPE
    SYNTAX      Counter64
    MAX-ACCESS  read-only
    STATUS      current
    DESCRIPTION
        "tmnxPortIngrMdaQos00StatDropPkts indicates the number of packets
         dropped on the oversubscribed MDA for QoS classifier result threshold
         00 because of an overload condition on the MDA."
    ::= { tmnxPortIngrMdaQosStatEntry 1 }

tmnxPortIngrMdaQos00StatDropOcts OBJECT-TYPE
    SYNTAX      Counter64
    MAX-ACCESS  read-only
    STATUS      current
    DESCRIPTION
        "tmnxPortIngrMdaQos00StatDropOcts indicates the number of octets
         dropped on the oversubscribed MDA for QoS classifier result threshold
         00 because of an overload condition on the MDA."
    ::= { tmnxPortIngrMdaQosStatEntry 2 }

tmnxPortIngrMdaQos01StatDropPkts OBJECT-TYPE
    SYNTAX      Counter64
    MAX-ACCESS  read-only
    STATUS      current
    DESCRIPTION
        "tmnxPortIngrMdaQos01StatDropPkts indicates the number of packets
         dropped on the oversubscribed MDA for QoS classifier result threshold
         01 because of an overload condition on the MDA."
    ::= { tmnxPortIngrMdaQosStatEntry 3 }

tmnxPortIngrMdaQos01StatDropOcts OBJECT-TYPE
    SYNTAX      Counter64
    MAX-ACCESS  read-only
    STATUS      current
    DESCRIPTION
        "tmnxPortIngrMdaQos01StatDropOcts indicates the number of octets
         dropped on the oversubscribed MDA for QoS classifier result threshold
         01 because of an overload condition on the MDA."
    ::= { tmnxPortIngrMdaQosStatEntry 4 }

tmnxPortIngrMdaQos02StatDropPkts OBJECT-TYPE
    SYNTAX      Counter64
    MAX-ACCESS  read-only
    STATUS      current
    DESCRIPTION
        "tmnxPortIngrMdaQos02StatDropPkts indicates the number of packets
         dropped on the oversubscribed MDA for QoS classifier result threshold
         02 because of an overload condition on the MDA."
    ::= { tmnxPortIngrMdaQosStatEntry 5 }

tmnxPortIngrMdaQos02StatDropOcts OBJECT-TYPE
    SYNTAX      Counter64
    MAX-ACCESS  read-only
    STATUS      current
    DESCRIPTION
        "tmnxPortIngrMdaQos02StatDropOcts indicates the number of octets
         dropped on the oversubscribed MDA for QoS classifier result threshold
         02 because of an overload condition on the MDA."
    ::= { tmnxPortIngrMdaQosStatEntry 6 }

tmnxPortIngrMdaQos03StatDropPkts OBJECT-TYPE
    SYNTAX      Counter64
    MAX-ACCESS  read-only
    STATUS      current
    DESCRIPTION
        "tmnxPortIngrMdaQos03StatDropPkts indicates the number of packets
         dropped on the oversubscribed MDA for QoS classifier result threshold
         03 because of an overload condition on the MDA."
    ::= { tmnxPortIngrMdaQosStatEntry 7 }

tmnxPortIngrMdaQos03StatDropOcts OBJECT-TYPE
    SYNTAX      Counter64
    MAX-ACCESS  read-only
    STATUS      current
    DESCRIPTION
        "tmnxPortIngrMdaQos03StatDropOcts indicates the number of octets
         dropped on the oversubscribed MDA for QoS classifier result threshold
         03 because of an overload condition on the MDA."
    ::= { tmnxPortIngrMdaQosStatEntry 8 }

tmnxPortIngrMdaQos04StatDropPkts OBJECT-TYPE
    SYNTAX      Counter64
    MAX-ACCESS  read-only
    STATUS      current
    DESCRIPTION
        "tmnxPortIngrMdaQos04StatDropPkts indicates the number of packets
         dropped on the oversubscribed MDA for QoS classifier result threshold
         04 because of an overload condition on the MDA."
    ::= { tmnxPortIngrMdaQosStatEntry 9 }

tmnxPortIngrMdaQos04StatDropOcts OBJECT-TYPE
    SYNTAX      Counter64
    MAX-ACCESS  read-only
    STATUS      current
    DESCRIPTION
        "tmnxPortIngrMdaQos04StatDropOcts indicates the number of octets
         dropped on the oversubscribed MDA for QoS classifier result threshold
         04 because of an overload condition on the MDA."
    ::= { tmnxPortIngrMdaQosStatEntry 10 }

tmnxPortIngrMdaQos05StatDropPkts OBJECT-TYPE
    SYNTAX      Counter64
    MAX-ACCESS  read-only
    STATUS      current
    DESCRIPTION
        "tmnxPortIngrMdaQos05StatDropPkts indicates the number of packets
         dropped on the oversubscribed MDA for QoS classifier result threshold
         05 because of an overload condition on the MDA."
    ::= { tmnxPortIngrMdaQosStatEntry 11 }

tmnxPortIngrMdaQos05StatDropOcts OBJECT-TYPE
    SYNTAX      Counter64
    MAX-ACCESS  read-only
    STATUS      current
    DESCRIPTION
        "tmnxPortIngrMdaQos05StatDropOcts indicates the number of octets
         dropped on the oversubscribed MDA for QoS classifier result threshold
         05 because of an overload condition on the MDA."
    ::= { tmnxPortIngrMdaQosStatEntry 12 }

tmnxPortIngrMdaQos06StatDropPkts OBJECT-TYPE
    SYNTAX      Counter64
    MAX-ACCESS  read-only
    STATUS      current
    DESCRIPTION
        "tmnxPortIngrMdaQos06StatDropPkts indicates the number of packets
         dropped on the oversubscribed MDA for QoS classifier result threshold
         06 because of an overload condition on the MDA."
    ::= { tmnxPortIngrMdaQosStatEntry 13 }

tmnxPortIngrMdaQos06StatDropOcts OBJECT-TYPE
    SYNTAX      Counter64
    MAX-ACCESS  read-only
    STATUS      current
    DESCRIPTION
        "tmnxPortIngrMdaQos06StatDropOcts indicates the number of octets
         dropped on the oversubscribed MDA for QoS classifier result threshold
         06 because of an overload condition on the MDA."
    ::= { tmnxPortIngrMdaQosStatEntry 14 }

tmnxPortIngrMdaQos07StatDropPkts OBJECT-TYPE
    SYNTAX      Counter64
    MAX-ACCESS  read-only
    STATUS      current
    DESCRIPTION
        "tmnxPortIngrMdaQos07StatDropPkts indicates the number of packets
         dropped on the oversubscribed MDA for QoS classifier result threshold
         07 because of an overload condition on the MDA."
    ::= { tmnxPortIngrMdaQosStatEntry 15 }

tmnxPortIngrMdaQos07StatDropOcts OBJECT-TYPE
    SYNTAX      Counter64
    MAX-ACCESS  read-only
    STATUS      current
    DESCRIPTION
        "tmnxPortIngrMdaQos07StatDropOcts indicates the number of octets
         dropped on the oversubscribed MDA for QoS classifier result threshold
         07 because of an overload condition on the MDA."
    ::= { tmnxPortIngrMdaQosStatEntry 16 }

tmnxPortIngrMdaQos08StatDropPkts OBJECT-TYPE
    SYNTAX      Counter64
    MAX-ACCESS  read-only
    STATUS      current
    DESCRIPTION
        "tmnxPortIngrMdaQos08StatDropPkts indicates the number of packets
         dropped on the oversubscribed MDA for QoS classifier result threshold
         08 because of an overload condition on the MDA."
    ::= { tmnxPortIngrMdaQosStatEntry 17 }

tmnxPortIngrMdaQos08StatDropOcts OBJECT-TYPE
    SYNTAX      Counter64
    MAX-ACCESS  read-only
    STATUS      current
    DESCRIPTION
        "tmnxPortIngrMdaQos08StatDropOcts indicates the number of octets
         dropped on the oversubscribed MDA for QoS classifier result threshold
         08 because of an overload condition on the MDA."
    ::= { tmnxPortIngrMdaQosStatEntry 18 }

tmnxPortIngrMdaQos09StatDropPkts OBJECT-TYPE
    SYNTAX      Counter64
    MAX-ACCESS  read-only
    STATUS      current
    DESCRIPTION
        "tmnxPortIngrMdaQos09StatDropPkts indicates the number of packets
         dropped on the oversubscribed MDA for QoS classifier result threshold
         09 because of an overload condition on the MDA."
    ::= { tmnxPortIngrMdaQosStatEntry 19 }

tmnxPortIngrMdaQos09StatDropOcts OBJECT-TYPE
    SYNTAX      Counter64
    MAX-ACCESS  read-only
    STATUS      current
    DESCRIPTION
        "tmnxPortIngrMdaQos09StatDropOcts indicates the number of octets
         dropped on the oversubscribed MDA for QoS classifier result threshold
         09 because of an overload condition on the MDA."
    ::= { tmnxPortIngrMdaQosStatEntry 20 }

tmnxPortIngrMdaQos10StatDropPkts OBJECT-TYPE
    SYNTAX      Counter64
    MAX-ACCESS  read-only
    STATUS      current
    DESCRIPTION
        "tmnxPortIngrMdaQos10StatDropPkts indicates the number of packets
         dropped on the oversubscribed MDA for QoS classifier result threshold
         10 because of an overload condition on the MDA."
    ::= { tmnxPortIngrMdaQosStatEntry 21 }

tmnxPortIngrMdaQos10StatDropOcts OBJECT-TYPE
    SYNTAX      Counter64
    MAX-ACCESS  read-only
    STATUS      current
    DESCRIPTION
        "tmnxPortIngrMdaQos10StatDropOcts indicates the number of octets
         dropped on the oversubscribed MDA for QoS classifier result threshold
         10 because of an overload condition on the MDA."
    ::= { tmnxPortIngrMdaQosStatEntry 22 }

tmnxPortIngrMdaQos11StatDropPkts OBJECT-TYPE
    SYNTAX      Counter64
    MAX-ACCESS  read-only
    STATUS      current
    DESCRIPTION
        "tmnxPortIngrMdaQos11StatDropPkts indicates the number of packets
         dropped on the oversubscribed MDA for QoS classifier result threshold
         11 because of an overload condition on the MDA."
    ::= { tmnxPortIngrMdaQosStatEntry 23 }

tmnxPortIngrMdaQos11StatDropOcts OBJECT-TYPE
    SYNTAX      Counter64
    MAX-ACCESS  read-only
    STATUS      current
    DESCRIPTION
        "tmnxPortIngrMdaQos11StatDropOcts indicates the number of octets
         dropped on the oversubscribed MDA for QoS classifier result threshold
         11 because of an overload condition on the MDA."
    ::= { tmnxPortIngrMdaQosStatEntry 24 }

tmnxPortIngrMdaQos12StatDropPkts OBJECT-TYPE
    SYNTAX      Counter64
    MAX-ACCESS  read-only
    STATUS      current
    DESCRIPTION
        "tmnxPortIngrMdaQos12StatDropPkts indicates the number of packets
         dropped on the oversubscribed MDA for QoS classifier result threshold
         12 because of an overload condition on the MDA."
    ::= { tmnxPortIngrMdaQosStatEntry 25 }

tmnxPortIngrMdaQos12StatDropOcts OBJECT-TYPE
    SYNTAX      Counter64
    MAX-ACCESS  read-only
    STATUS      current
    DESCRIPTION
        "tmnxPortIngrMdaQos12StatDropOcts indicates the number of octets
         dropped on the oversubscribed MDA for QoS classifier result threshold
         12 because of an overload condition on the MDA."
    ::= { tmnxPortIngrMdaQosStatEntry 26 }

tmnxPortIngrMdaQos13StatDropPkts OBJECT-TYPE
    SYNTAX      Counter64
    MAX-ACCESS  read-only
    STATUS      current
    DESCRIPTION
        "tmnxPortIngrMdaQos13StatDropPkts indicates the number of packets
         dropped on the oversubscribed MDA for QoS classifier result threshold
         13 because of an overload condition on the MDA."
    ::= { tmnxPortIngrMdaQosStatEntry 27 }

tmnxPortIngrMdaQos13StatDropOcts OBJECT-TYPE
    SYNTAX      Counter64
    MAX-ACCESS  read-only
    STATUS      current
    DESCRIPTION
        "tmnxPortIngrMdaQos13StatDropOcts indicates the number of octets
         dropped on the oversubscribed MDA for QoS classifier result threshold
         13 because of an overload condition on the MDA."
    ::= { tmnxPortIngrMdaQosStatEntry 28 }

tmnxPortIngrMdaQos14StatDropPkts OBJECT-TYPE
    SYNTAX      Counter64
    MAX-ACCESS  read-only
    STATUS      current
    DESCRIPTION
        "tmnxPortIngrMdaQos14StatDropPkts indicates the number of packets
         dropped on the oversubscribed MDA for QoS classifier result threshold
         14 because of an overload condition on the MDA."
    ::= { tmnxPortIngrMdaQosStatEntry 29 }

tmnxPortIngrMdaQos14StatDropOcts OBJECT-TYPE
    SYNTAX      Counter64
    MAX-ACCESS  read-only
    STATUS      current
    DESCRIPTION
        "tmnxPortIngrMdaQos14StatDropOcts indicates the number of octets
         dropped on the oversubscribed MDA for QoS classifier result threshold
         14 because of an overload condition on the MDA."
    ::= { tmnxPortIngrMdaQosStatEntry 30 }

tmnxPortIngrMdaQos15StatDropPkts OBJECT-TYPE
    SYNTAX      Counter64
    MAX-ACCESS  read-only
    STATUS      current
    DESCRIPTION
        "tmnxPortIngrMdaQos15StatDropPkts indicates the number of packets
         dropped on the oversubscribed MDA for QoS classifier result threshold
         15 because of an overload condition on the MDA."
    ::= { tmnxPortIngrMdaQosStatEntry 31 }

tmnxPortIngrMdaQos15StatDropOcts OBJECT-TYPE
    SYNTAX      Counter64
    MAX-ACCESS  read-only
    STATUS      current
    DESCRIPTION
        "tmnxPortIngrMdaQos15StatDropOcts indicates the number of octets
         dropped on the oversubscribed MDA for QoS classifier result threshold
         15 because of an overload condition on the MDA."
    ::= { tmnxPortIngrMdaQosStatEntry 32 }

--
--  Sonet Group Table
--

tmnxSonetGroupTable OBJECT-TYPE
    SYNTAX      SEQUENCE OF TmnxSonetGroupEntry
    MAX-ACCESS  not-accessible
    STATUS      current
    DESCRIPTION
        "The tmnxSonetGroupTable has an entry for each
         Tributary Unit Group(TUG3) on a path. On a port which supports
         unchannelized STS-3's, rows in this table are created when a
         channelized STS-3 has its tmnxSonetPathChildType set to sdhTug3.
         On a port which does not support unchannelized STS-3's, the rows
         in this table are implicitly created when a STS-3 is created
         in the tmnxSonetPathTable.  Entries in this table are implicitly
         deleted when the parent entry of this group is deleted from the
         tmnxSonetPathTable or if the tmnxSonetPathChildType of the parent
         is set to something other than sdhTug3."
    ::= { tmnxPortObjs 18 }

tmnxSonetGroupEntry       OBJECT-TYPE
    SYNTAX      TmnxSonetGroupEntry
    MAX-ACCESS  not-accessible
    STATUS      current
    DESCRIPTION
        "Each row entry represents a Tributary Unit Group(TUG3) on a path."
    INDEX   { tmnxChassisIndex, tmnxPortPortID }
    ::= { tmnxSonetGroupTable 1 }

TmnxSonetGroupEntry ::=
    SEQUENCE {
        tmnxSonetGroupType              TmnxMDAChanType,
        tmnxSonetGroupParentPortID      TmnxPortID,
        tmnxSonetGroupChildType         TmnxMDAChanType,
        tmnxSonetGroupName              TNamedItemOrEmpty
    }

tmnxSonetGroupType     OBJECT-TYPE
    SYNTAX      TmnxMDAChanType
    MAX-ACCESS  read-only
    STATUS      current
    DESCRIPTION
        "tmnxSonetGroupType indicates the sonet group type of this entry.
         For STS-3/STM-1 channelization, the value of this object will
         be 'sdhTug3'."
    ::= { tmnxSonetGroupEntry 1 }

tmnxSonetGroupParentPortID     OBJECT-TYPE
    SYNTAX      TmnxPortID
    MAX-ACCESS  read-only
    STATUS      current
    DESCRIPTION
        "tmnxSonetGroupParentPortID indicates the TmnxPortID of the parent of
         this group."
    ::= { tmnxSonetGroupEntry 2 }

tmnxSonetGroupChildType     OBJECT-TYPE
    SYNTAX      TmnxMDAChanType
    MAX-ACCESS  read-write
    STATUS      current
    DESCRIPTION
        "tmnxSonetGroupChildType is used to configure the type of the children
         of this group. Based on the value of this object, entries of
         a certain channel type can be created in the tmnxSonetPathTable.
         For example, if the value of this object is set to 'sonetVt15',
         then 28 entries of type 'sonetVt15' can be created in
         the tmnxSonetPathTable."
    ::= { tmnxSonetGroupEntry 3 }

tmnxSonetGroupName     OBJECT-TYPE
    SYNTAX      TNamedItemOrEmpty
    MAX-ACCESS  read-only
    STATUS      current
    DESCRIPTION
        "tmnxSonetGroupName is the textual name for this sonet group."
    ::= { tmnxSonetGroupEntry 4 }

--
--  Cisco HDLC Table
--

tmnxCiscoHDLCTable OBJECT-TYPE
    SYNTAX      SEQUENCE OF TmnxCiscoHDLCEntry
    MAX-ACCESS  not-accessible
    STATUS      current
    DESCRIPTION
        "The tmnxCiscoHDLCTable has an entry for each port in the system
         that is configured for Cisco HDLC. It contains the parameters related
         to Cisco HDLC protocol on this port."
    ::= { tmnxPortObjs 20 }

tmnxCiscoHDLCEntry       OBJECT-TYPE
    SYNTAX      TmnxCiscoHDLCEntry
    MAX-ACCESS  not-accessible
    STATUS      current
    DESCRIPTION
        "The tmnxCiscoHDLCEntry specifies parameters for a particular
         interfaces running Cisco HDLC encapsulation. Entries cannot be created
         and deleted via SNMP SET operations."
    INDEX   { tmnxChassisIndex, tmnxPortPortID }
    ::= { tmnxCiscoHDLCTable 1 }

TmnxCiscoHDLCEntry ::=
    SEQUENCE {
        tmnxCiscoHDLCKeepAliveInt        Unsigned32,
        tmnxCiscoHDLCUpCount             Unsigned32,
        tmnxCiscoHDLCDownCount           Unsigned32,
        tmnxCiscoHDLCOperState           TmnxOperState
    }

tmnxCiscoHDLCKeepAliveInt      OBJECT-TYPE
    SYNTAX      Unsigned32 (0..300)
    UNITS       "seconds"
    MAX-ACCESS  read-create
    STATUS      current
    DESCRIPTION
        "tmnxCiscoHDLCKeepAliveInt specifies the interval in seconds
         used for sending periodic keepalive packets. The default value is set
         to 10 seconds. A value of 0 specifies that the keepalive function is
         turned off.

         It is expected that the nodes at the two endpoints of
         the Cisco HDLC link are provisioned with the same values."
    DEFVAL      {10}
    ::= { tmnxCiscoHDLCEntry 1 }

tmnxCiscoHDLCUpCount      OBJECT-TYPE
    SYNTAX        Unsigned32 (1..3)
    MAX-ACCESS    read-create
    STATUS        current
    DESCRIPTION
        "tmnxCiscoHDLCUpCount specifies the number of continual
         keepalive packets that has to be received to declare the link up.

         It is expected that the nodes at the two endpoints of
         the Cisco HDLC link are provisioned with the same values."
    DEFVAL      {1}
    ::= { tmnxCiscoHDLCEntry 2 }

tmnxCiscoHDLCDownCount        OBJECT-TYPE
    SYNTAX        Unsigned32 (3..16)
    MAX-ACCESS    read-create
    STATUS        current
    DESCRIPTION
        "tmnxCiscoHDLCDownCount specifies the number of
         'tmnxCiscoHDLCKeepAliveInt' intervals that must
         pass without receiving a keepalive packet before the
         link is declared down.

         It is expected that the nodes at the two endpoints of
         the Cisco HDLC link are provisioned with the same values."
    DEFVAL      {3}
    ::= { tmnxCiscoHDLCEntry 3 }

tmnxCiscoHDLCOperState     OBJECT-TYPE
    SYNTAX      TmnxOperState
    MAX-ACCESS  read-only
    STATUS      current
    DESCRIPTION
        "The value of tmnxCiscoHDLCOperState indicates the operational
         status of the Cisco HDLC protocol for this port."
    ::= { tmnxCiscoHDLCEntry 4 }


--
--  Cisco HDLC statisctics Table
--

tmnxCiscoHDLCStatsTable OBJECT-TYPE
    SYNTAX  SEQUENCE OF TmnxCiscoHDLCStatsEntry
    MAX-ACCESS  not-accessible
    STATUS      current
    DESCRIPTION
        "The tmnxCiscoHDLCStatsTable has an entry for each port in the
         system that is configured for Cisco HDLC encapsulation. It contains
         Cisco HDLC protocol statistics for the particular port."
    ::= { tmnxPortStatsObjs 3 }

tmnxCiscoHDLCStatsEntry OBJECT-TYPE
    SYNTAX     TmnxCiscoHDLCStatsEntry
    MAX-ACCESS not-accessible
    STATUS     current
    DESCRIPTION
        "An entry in the tmnxCiscoHDLCStatsTable."
    AUGMENTS      { tmnxCiscoHDLCEntry }
    ::= { tmnxCiscoHDLCStatsTable 1 }

TmnxCiscoHDLCStatsEntry ::= SEQUENCE {
    tmnxCiscoHDLCDiscardStatInPkts          Unsigned32,
    tmnxCiscoHDLCDiscardStatOutPkts         Unsigned32,
    tmnxCiscoHDLCStatInPkts                 Unsigned32,
    tmnxCiscoHDLCStatOutPkts                Unsigned32,
    tmnxCiscoHDLCStatInOctets               Unsigned32,
    tmnxCiscoHDLCStatOutOctets              Unsigned32
}

tmnxCiscoHDLCDiscardStatInPkts      OBJECT-TYPE
    SYNTAX        Unsigned32
    MAX-ACCESS    read-only
    STATUS        current
    DESCRIPTION
        "tmnxCiscoHDLCDiscardStatInPkts indicates the number of
         inbound Cisco HDLC packets discarded."
    ::= { tmnxCiscoHDLCStatsEntry 1 }

tmnxCiscoHDLCDiscardStatOutPkts     OBJECT-TYPE
    SYNTAX        Unsigned32
    MAX-ACCESS    read-only
    STATUS        current
    DESCRIPTION
        "tmnxCiscoHDLCDiscardStatOutPkts indicates the number of
         outbound Cisco HDLC packets discarded."
    ::= { tmnxCiscoHDLCStatsEntry 2 }

tmnxCiscoHDLCStatInPkts         OBJECT-TYPE
    SYNTAX        Unsigned32
    MAX-ACCESS    read-only
    STATUS        current
    DESCRIPTION
        "tmnxCiscoHDLCStatInPkts indicates the number of inbound Cisco
         HDLC packets."
    ::= { tmnxCiscoHDLCStatsEntry 3 }

tmnxCiscoHDLCStatOutPkts        OBJECT-TYPE
    SYNTAX        Unsigned32
    MAX-ACCESS    read-only
    STATUS        current
    DESCRIPTION
        "tmnxCiscoHDLCStatOutPkts indicates the number of outbound Cisco
         HDLC packets."
    ::= { tmnxCiscoHDLCStatsEntry 4 }

tmnxCiscoHDLCStatInOctets     OBJECT-TYPE
    SYNTAX        Unsigned32
    MAX-ACCESS    read-only
    STATUS        current
    DESCRIPTION
        "tmnxCiscoHDLCStatInOctets indicates the number of inbound Cisco
         HDLC octets."
    ::= { tmnxCiscoHDLCStatsEntry 5 }

tmnxCiscoHDLCStatOutOctets     OBJECT-TYPE
    SYNTAX        Unsigned32
    MAX-ACCESS    read-only
    STATUS        current
    DESCRIPTION
        "tmnxCiscoHDLCStatOutOctets indicates the number of outbound
         Cisco HDLC octets."
    ::= { tmnxCiscoHDLCStatsEntry 6 }

--
--  Frame Relay Protocol Table
--
tmnxFRDlcmiTable OBJECT-TYPE
    SYNTAX  SEQUENCE OF TmnxFRDlcmiEntry
    MAX-ACCESS  not-accessible
    STATUS      current
    DESCRIPTION
        "The tmnxFRDlcmiTable has an entry for each port in the
         system that is configured for Frame Relay. It contains
         the parameters for the Data Link Connection Management
         Interface (DLCMI) for the frame relay service on this port."
    ::= { tmnxFRObjs 1 }

tmnxFRDlcmiEntry       OBJECT-TYPE
    SYNTAX      TmnxFRDlcmiEntry
    MAX-ACCESS  not-accessible
    STATUS      current
    DESCRIPTION
        "The Parameters for a particular Data Link Connection
         Management Interface. Entries cannot be created and
         deleted via SNMP SET operations."
    INDEX   { tmnxChassisIndex, tmnxPortPortID }
    ::= { tmnxFRDlcmiTable 1 }

TmnxFRDlcmiEntry ::=
    SEQUENCE {
        tmnxFRDlcmiMode                 INTEGER,
        tmnxFRDlcmiN392Dce              INTEGER,
        tmnxFRDlcmiN393Dce              INTEGER,
        tmnxFRDlcmiT392Dce              INTEGER,
        tmnxFRDlcmiTxStatusEnqMsgs      Counter32,
        tmnxFRDlcmiRxStatusEnqMsgs      Counter32,
        tmnxFRDlcmiStatusEnqMsgTimeouts Counter32,
        tmnxFRDlcmiTxStatusMsgs         Counter32,
        tmnxFRDlcmiRxStatusMsgs         Counter32,
        tmnxFRDlcmiStatusMsgTimeouts    Counter32,
        tmnxFRDlcmiDiscardedMsgs        Counter32,
        tmnxFRDlcmiInvRxSeqNumMsgs      Counter32
    }

tmnxFRDlcmiMode OBJECT-TYPE
        SYNTAX      INTEGER {
                        dte (1),
                        dce (2),
                        bidir(3)
                    }
        MAX-ACCESS  read-write
        STATUS      current
        DESCRIPTION
            "tmnxFRDlcmiMode is used to set the mode of the interface.
             It can be set as Data terminal equipment (dte),
             Data circuit-terminating equipment (dce) or both as Data
             terminal equipment and Data circuit-terminating
             equipment (bidir). "
        DEFVAL { dte }
        ::= { tmnxFRDlcmiEntry 1 }

tmnxFRDlcmiN392Dce OBJECT-TYPE
        SYNTAX      INTEGER (1..10)
        MAX-ACCESS  read-write
        STATUS      current
        DESCRIPTION
            "tmnxFRDlcmiN392Dce is used to configure the LMI error
             threshold for DCE interface."
        DEFVAL { 3 }
        ::= { tmnxFRDlcmiEntry 2 }

tmnxFRDlcmiN393Dce OBJECT-TYPE
        SYNTAX      INTEGER (1..10)
        MAX-ACCESS  read-write
        STATUS      current
        DESCRIPTION
            "tmnxFRDlcmiN393Dce is used to configure the LMI monitored
             event count for DCE interface."
        DEFVAL { 4 }
        ::= { tmnxFRDlcmiEntry 3 }

tmnxFRDlcmiT392Dce OBJECT-TYPE
        SYNTAX      INTEGER (5..30)
        UNITS       "seconds"
        MAX-ACCESS  read-write
        STATUS      current
        DESCRIPTION
            "tmnxFRDlcmiT392Dce is used to configure the polling verification
             timer for the Frame Relay DCE interface."
        DEFVAL { 15 }
        ::= { tmnxFRDlcmiEntry 4 }

tmnxFRDlcmiTxStatusEnqMsgs OBJECT-TYPE
        SYNTAX      Counter32
        UNITS       "messages"
        MAX-ACCESS  read-only
        STATUS      current
        DESCRIPTION
            "tmnxFRDlcmiTxStatusEnqMsgs indicates the number of LMI Status
             Enquiry messages transmitted on this Frame Relay interface."
        ::= { tmnxFRDlcmiEntry 5 }

tmnxFRDlcmiRxStatusEnqMsgs OBJECT-TYPE
        SYNTAX      Counter32
        UNITS       "messages"
        MAX-ACCESS  read-only
        STATUS      current
        DESCRIPTION
            "tmnxFRDlcmiRxStatusEnqMsgs indicates the number of LMI Status
             Enquiry messages received on this Frame Relay interface."
        ::= { tmnxFRDlcmiEntry 6 }

tmnxFRDlcmiStatusEnqMsgTimeouts OBJECT-TYPE
        SYNTAX      Counter32
        UNITS       "messages"
        MAX-ACCESS  read-only
        STATUS      current
        DESCRIPTION
            "tmnxFRDlcmiStatusEnqMsgTimeouts indicates the number of times
             the LMI agent did not receive a Status Enquiry message within
             the allotted time."
        ::= { tmnxFRDlcmiEntry 7 }

tmnxFRDlcmiTxStatusMsgs OBJECT-TYPE
        SYNTAX      Counter32
        UNITS       "messages"
        MAX-ACCESS  read-only
        STATUS      current
        DESCRIPTION
            "tmnxFRDlcmiTxStatusMsgs indicates the number of LMI Status
             messages transmitted on this Frame Relay interface."
        ::= { tmnxFRDlcmiEntry 8 }

tmnxFRDlcmiRxStatusMsgs OBJECT-TYPE
        SYNTAX      Counter32
        UNITS       "messages"
        MAX-ACCESS  read-only
        STATUS      current
        DESCRIPTION
            "tmnxFRDlcmiRxStatusMsgs indicates the number of LMI Status
             messages received on this Frame Relay interface."
        ::= { tmnxFRDlcmiEntry 9 }

tmnxFRDlcmiStatusMsgTimeouts OBJECT-TYPE
        SYNTAX      Counter32
        UNITS       "messages"
        MAX-ACCESS  read-only
        STATUS      current
        DESCRIPTION
            "tmnxFRDlcmiStatusMsgTimeouts indicates the number of times
             the LMI agent did not receive a Status message within the
             allotted time."
        ::= { tmnxFRDlcmiEntry 10 }

tmnxFRDlcmiDiscardedMsgs OBJECT-TYPE
        SYNTAX      Counter32
        UNITS       "messages"
        MAX-ACCESS  read-only
        STATUS      current
        DESCRIPTION
            "tmnxFRDlcmiDiscardedMsgs indicates the number of times
             the LMI agent discarded a received message because it
             wasn't expecting it, the type of message was incorrect,
             or the contents of the message were invalid."
        ::= { tmnxFRDlcmiEntry 11 }

tmnxFRDlcmiInvRxSeqNumMsgs OBJECT-TYPE
        SYNTAX      Counter32
        UNITS       "messages"
        MAX-ACCESS  read-only
        STATUS      current
        DESCRIPTION
            "tmnxFRDlcmiInvRxSeqNumMsgs indicates the number of times
             the LMI agent received a message with an invalid receive
             sequence number: i.e. a sequence number that does not
             match the last transmitted sequence number of the agent."
        ::= { tmnxFRDlcmiEntry 12 }

--
-- QoS Policy Application Table
--
tmnxQosPoolAppTable OBJECT-TYPE
    SYNTAX      SEQUENCE OF TmnxQosPoolAppEntry
    MAX-ACCESS  not-accessible
    STATUS      current
    DESCRIPTION
        "This table maintains associations of the buffer pools with the
        individual objects."
    ::= { tmnxQosAppObjs 2 }

tmnxQosPoolAppEntry OBJECT-TYPE
    SYNTAX      TmnxQosPoolAppEntry
    MAX-ACCESS  not-accessible
    STATUS      current
    DESCRIPTION
        "This entry maintains the specifics about the association of a
        buffer pool and an object."
    INDEX {
              tmnxChassisIndex,
              tmnxObjectType,
              tmnxObjectId,
              tmnxObjectAppType,
              tmnxObjectAppPool
          }
    ::= { tmnxQosPoolAppTable 1 }

TmnxQosPoolAppEntry ::=
    SEQUENCE {
        tmnxObjectType                     INTEGER,
        tmnxObjectId                       TmnxPortID,
        tmnxObjectAppType                  INTEGER,
        tmnxObjectAppPool                  TNamedItem,
        tmnxObjectAppPoolRowStatus         RowStatus,
        tmnxObjectAppResvCbs               Integer32,
        tmnxObjectAppSlopePolicy           TNamedItem,
        tmnxObjectAppPoolSize              Integer32,
        tmnxObjectAppResvCbsAmbrAlrmStep   Integer32,
        tmnxObjectAppResvCbsAmbrAlrmMax    Integer32,
        tmnxObjectAppAmbrAlrmThresh        Integer32,
        tmnxObjectAppRedAlrmThresh         Integer32
    }

tmnxObjectType OBJECT-TYPE
    SYNTAX      INTEGER {
                    mda (1),
                    port (2),
                    unused (3),
                    bundle (4)
                }
    MAX-ACCESS  not-accessible
    STATUS      current
    DESCRIPTION
        "The object tmnxObjectType defines the type of object to which the
        pool is being setup for."
    ::= { tmnxQosPoolAppEntry 1 }

tmnxObjectId          OBJECT-TYPE
    SYNTAX      TmnxPortID
    MAX-ACCESS  not-accessible
    STATUS      current
    DESCRIPTION
        "tmnxObjectId is used to identify the specific object. If
        tmnxObjectType is 'mda', then the tmnxObjectId is encoded as a
        physical port with the port being '0'. For all other types the
        encoding is done as per the description of TmnxPortID."
    ::= { tmnxQosPoolAppEntry 2 }

tmnxObjectAppType OBJECT-TYPE
    SYNTAX      INTEGER {
                    accessIngress (1),
                    accessEgress (2),
                    networkIngress (3),
                    networkEgress (4)
                }
    MAX-ACCESS  not-accessible
    STATUS      current
    DESCRIPTION
        "The object tmnxObjectAppType specifies the nature of usage the pool
        would be used for. The pools could be used for access or network
        traffic at either ingress or egress."
    ::= { tmnxQosPoolAppEntry 3 }

tmnxObjectAppPool OBJECT-TYPE
    SYNTAX      TNamedItem
    MAX-ACCESS  not-accessible
    STATUS      current
    DESCRIPTION
        "tmnxObjectAppPool specifies the name of the pool to be used/created."
    ::= { tmnxQosPoolAppEntry 4 }

tmnxObjectAppPoolRowStatus OBJECT-TYPE
    SYNTAX      RowStatus
    MAX-ACCESS  read-write
    STATUS      current
    DESCRIPTION
        "The object tmnxObjectAppPoolRowStatus is used to create or remove a
        pool application to the object."
    ::= { tmnxQosPoolAppEntry 5 }

tmnxObjectAppResvCbs OBJECT-TYPE
    SYNTAX      Integer32 (-1|0..100)
    MAX-ACCESS  read-write
    STATUS      current
    DESCRIPTION
        "The percentage of pool size reserved for CBS. The value '-1'
        implies that the reserved CBS should be computed as the sum of
        the CBS requested by the entities using this pool if the application
        point is 'network'. For 'access' application points the value '-1'
        means a default of 30%."
    DEFVAL { -1 }
    ::= { tmnxQosPoolAppEntry 6 }

tmnxObjectAppSlopePolicy OBJECT-TYPE
    SYNTAX      TNamedItem
    MAX-ACCESS  read-write
    STATUS      current
    DESCRIPTION
        "tmnxObjectAppSlopePolicy specifies the slope policy being used for
        this pool. The Slope policies define the nature of the RED Slopes for
        the high and the low priority traffic."
    DEFVAL { "default" }
    ::= { tmnxQosPoolAppEntry 7 }

tmnxObjectAppPoolSize OBJECT-TYPE
    SYNTAX      Integer32 (-1|0..100)
    MAX-ACCESS  read-write
    STATUS      current
    DESCRIPTION
        "Size in percentage of buffer space. The value '-1' implies that
        the pool size should be computed as per fair weighing between
        all other pools."
    DEFVAL { -1 }
    ::= { tmnxQosPoolAppEntry 8 }

tmnxObjectAppResvCbsAmbrAlrmStep OBJECT-TYPE
    SYNTAX      Integer32 (0..100)
    UNITS       "percent"
    MAX-ACCESS  read-write
    STATUS      current
    DESCRIPTION
        "The value of tmnxObjectAppResvCbsAmbrAlrmStep specifies the 
         percentage step-size for the reserved CBS size of the pool. 
         When tmnxObjectAppResvCbsAmbrAlrmStep is set to default value, the 
         adaptive CBS sizing is disabled. To enable adaptive CBS sizing, 
         tmnxObjectAppResvCbsAmbrAlrmStep MUST be set to non-default value along
         with tmnxObjectAppResvCbsAmbrAlrmMax. When reserved CBS is set to 
         default value, adaptive CBS sizing cannot be enabled. The reserved CBS
         (Committed Burst Size) defines the amount of buffer space within the 
         pool that is not considered shared."
    DEFVAL { 0 }
    ::= { tmnxQosPoolAppEntry 9 }

tmnxObjectAppResvCbsAmbrAlrmMax OBJECT-TYPE
    SYNTAX      Integer32 (0..100)
    UNITS       "percent"
    MAX-ACCESS  read-write
    STATUS      current
    DESCRIPTION
        "The value of tmnxObjectAppResvCbsAmbrAlrmMax specifies the 
         maximum percentage for the reserved CBS size of the pool. 
         When tmnxObjectAppResvCbsAmbrAlrmMax is set to default value, the 
         adaptive CBS sizing is disabled. To enable adaptive CBS sizing,
         tmnxObjectAppResvCbsAmbrAlrmMax MUST be set to non-default value along
         with tmnxObjectAppResvCbsAmbrAlrmStep. When reserved CBS is set to 
         default value, adaptive CBS sizing cannot be enabled. The reserved CBS
         (Committed Burst Size) defines the amount of buffer space within the
         pool that is not considered shared.  Max reserved CBS must not be more 
         than the reserved CBS."
    DEFVAL { 0 }
    ::= { tmnxQosPoolAppEntry 10 }

tmnxObjectAppAmbrAlrmThresh OBJECT-TYPE
    SYNTAX      Integer32 (0..1000)
    UNITS       "percent"
    MAX-ACCESS  read-write
    STATUS      current
    DESCRIPTION
        "The value of tmnxObjectAppAmbrAlrmThresh specifies the 
         threshold for the amber alarm on the over-subscription allowed."
    DEFVAL { 0 }
    ::= { tmnxQosPoolAppEntry 11 }

tmnxObjectAppRedAlrmThresh OBJECT-TYPE
    SYNTAX      Integer32 (0..1000)
    UNITS       "percent"
    MAX-ACCESS  read-write
    STATUS      current
    DESCRIPTION
        "The value of tmnxObjectAppRedAlrmThresh specifies the 
         threshold for the red alarm on the over-subscription allowed."
    DEFVAL { 0 }
    ::= { tmnxQosPoolAppEntry 12 }

--
--  ATM Interface Table
--

tmnxATMIntfTable OBJECT-TYPE
    SYNTAX  SEQUENCE OF TmnxATMIntfEntry
    MAX-ACCESS  not-accessible
    STATUS      current
    DESCRIPTION
        "The tmnxATMIntfTable has an entry for each port/channel in the
         system that is configured for ATM. It contains ATM cell layer
         configuration parameters."
    ::= { tmnxATMObjs 1 }

tmnxATMIntfEntry       OBJECT-TYPE
    SYNTAX      TmnxATMIntfEntry
    MAX-ACCESS  not-accessible
    STATUS      current
    DESCRIPTION
        "The Parameters for a particular ATM Cell
         Management Interface. Entries cannot be created or
         deleted via SNMP SET operations.
         Entries will exist in this table when ATM encapsulation
         is configured on the port/channel."
    INDEX   { tmnxChassisIndex, tmnxPortPortID }
    ::= { tmnxATMIntfTable 1 }

TmnxATMIntfEntry ::=
    SEQUENCE {
        tmnxATMIntfCellFormat          INTEGER,
        tmnxATMIntfMinVpValue          Integer32,
        tmnxATMIntfMapping             INTEGER,
        tmnxATMIntfCustomBufferMode    TruthValue,
        tmnxATMIntfBufferPool          Integer32,
        tmnxATMIntfVcThreshold         Integer32
    }

tmnxATMIntfCellFormat OBJECT-TYPE
    SYNTAX      INTEGER {
                    uni (1),
                    nni (2)
                }
    MAX-ACCESS  read-write
    STATUS      current
    DESCRIPTION
        "tmnxATMIntfCellFormat is used to set the cell format
         (UNI or NNI) that is to be used on the ATM interface."
    DEFVAL { uni }
    ::= { tmnxATMIntfEntry 1 }

tmnxATMIntfMinVpValue OBJECT-TYPE
        SYNTAX      Integer32 (0..4095)
        MAX-ACCESS  read-write
        STATUS      current
        DESCRIPTION
            "tmnxATMIntfMinVpValue is used to set the minimum
             allowable VPI value that can be used on the
             ATM interface for a VPC."
        DEFVAL { 0 }
        ::= { tmnxATMIntfEntry 2 }

tmnxATMIntfMapping OBJECT-TYPE
        SYNTAX      INTEGER {
                        direct (1),
                        plcp (2)
                    }
        MAX-ACCESS  read-write
        STATUS      current
        DESCRIPTION
            "The value of tmnxATMIntfMapping specifies the cell
             mapping that is to be used on this ATM interface.  When
             tmnxPortChanType does not have a value of 'pdhDs3 (14)',
             'inconsistentValue' error will be returned to SNMP SET
             requests.  When tmnxPortChanType has a value of 'pdhDs3 (14)',
             tmnxATMIntfMapping can be set to 'plcp (2)'."
        DEFVAL { direct }
        ::= { tmnxATMIntfEntry 3 }

tmnxATMIntfCustomBufferMode OBJECT-TYPE
        SYNTAX      TruthValue
        MAX-ACCESS  read-write
        STATUS      current
        DESCRIPTION
            "The value of tmnxATMIntfCustomBufferMode specifies whether
             port is in a mode that allows custom configuration of port buffer
             pool and VC thresholds."
        DEFVAL { false }
        ::= { tmnxATMIntfEntry 4 }

tmnxATMIntfBufferPool OBJECT-TYPE
        SYNTAX      Integer32 (1..100)
        MAX-ACCESS  read-write
        STATUS      current
        DESCRIPTION
            "The value of tmnxATMIntfBufferPool specifies the percentage
             of the buffers configured on this interface over the
             maximum allowed on this interface.

             The value can only be changed if tmnxATMIntfCustomBufferMode
             is set to 'true'.  Changing tmnxATMIntfCustomBufferMode to
             'false' will reset tmnxATMIntfBufferPool back to the default
             value."
        DEFVAL { 100 }
        ::= { tmnxATMIntfEntry 5 }

tmnxATMIntfVcThreshold OBJECT-TYPE
        SYNTAX      Integer32 (190..117000)
        MAX-ACCESS  read-write
        STATUS      current
        DESCRIPTION
            "The value of tmnxATMIntfVcThreshold specifies the VC buffer
             threshold for all VCs configured on this port.

             The value can only be changed if tmnxATMIntfCustomBufferMode
             is set to 'true'.  Changing tmnxATMIntfCustomBufferMode to
             'false' will reset tmnxATMIntfVcThreshold back to the default
             value."
        DEFVAL { 190 }
        ::= { tmnxATMIntfEntry 6 }

--
--  ATM VP Shaper Table
--

tmnxPortATMVpShaperTblLastCh OBJECT-TYPE
    SYNTAX      TimeStamp
    MAX-ACCESS  read-only
    STATUS      current
    DESCRIPTION
        "The value of tmnxPortATMVpShaperTblLastCh indicates the sysUpTime
         at the time of the last modification of tmnxPortATMVpShaperTable.

         If no changes were made to the table since the last
         re-initialization of the local network management subsystem,
         then this object contains a zero value."
    ::= { tmnxATMObjs 2 }

tmnxPortATMVpShaperTable OBJECT-TYPE
    SYNTAX      SEQUENCE OF TmnxPortATMVpShaperEntry
    MAX-ACCESS  not-accessible
    STATUS      current
    DESCRIPTION
        "The tmnxPortATMVpShaperTable has an entry for each ATM port-level VP
         shaper configured on this system."
    ::= { tmnxATMObjs 3 }

tmnxPortATMVpShaperEntry OBJECT-TYPE
    SYNTAX      TmnxPortATMVpShaperEntry
    MAX-ACCESS  not-accessible
    STATUS      current
    DESCRIPTION
        "Each row represents a particular ATM port-level VP shaper.
         Entries are created and deleted by the user."
    INDEX   { tmnxChassisIndex, tmnxPortPortID, tmnxPortATMVpShaperVpi}
    ::= { tmnxPortATMVpShaperTable 1 }

TmnxPortATMVpShaperEntry ::=
    SEQUENCE {
        tmnxPortATMVpShaperVpi            AtmVpIdentifier,
        tmnxPortATMVpShaperRowStatus      RowStatus,
        tmnxPortATMVpShaperLastMgmtCh     TimeStamp,
        tmnxPortATMVpShaperEgrAtd         AtmTrafficDescrParamIndex
    }

tmnxPortATMVpShaperVpi OBJECT-TYPE
    SYNTAX      AtmVpIdentifier
    MAX-ACCESS  not-accessible
    STATUS      current
    DESCRIPTION
        "The value of tmnxPortATMVpShaperVpi specifies the ATM Virtual Path 
         identifier of this row."
    ::= { tmnxPortATMVpShaperEntry 1 }

tmnxPortATMVpShaperRowStatus OBJECT-TYPE
    SYNTAX      RowStatus
    MAX-ACCESS  read-create
    STATUS      current
    DESCRIPTION
       "The value of sapAtmVcRangeRowStatus specifies the row status of this
        row."
    ::= { tmnxPortATMVpShaperEntry 2 }

tmnxPortATMVpShaperLastMgmtCh OBJECT-TYPE
    SYNTAX      TimeStamp
    MAX-ACCESS  read-only
    STATUS      current
    DESCRIPTION
        "The value of tmnxPortATMVpShaperLastMgmtCh indicates the sysUpTime
         at the time of the most recent management-initiated change to this
         table row."
    ::= { tmnxPortATMVpShaperEntry 3 }

tmnxPortATMVpShaperEgrAtd OBJECT-TYPE
    SYNTAX      AtmTrafficDescrParamIndex (1..1000)
    MAX-ACCESS  read-create
    STATUS      current
    DESCRIPTION
        "The value of tmnxPortATMVpShaperEgrAtd specifies 
         the index of the ATM traffic descriptor in the ATM traffic 
         data encapsulation used for the egress direction over
         the AAL5 SSCS layer.
         
         The definition references RFC 2684 Multiprotocol Encapsulation over
         ATM AAL5 and to the ATM Forum LAN Emulation specification.
         
         The value of tmnxPortATMVpShaperEgrAtd must be specified when the
         conceptual row is created, and it cannot be changed afterwards."
    ::= { tmnxPortATMVpShaperEntry 4 }
        
    
--
--  Network Port Ingress Stats Table
--
tmnxPortNetIngressStatsTable OBJECT-TYPE
    SYNTAX      SEQUENCE OF TmnxPortNetIngressStatsEntry
    MAX-ACCESS  not-accessible
    STATUS      current
    DESCRIPTION
        "Defines the Alcatel-Lucent SROS series network port ingress
         statistics table for providing, via SNMP, the capability of
         retrieving the traffic statistics for the physical queues
         being used for the ports to forward the network ingress
         traffic."
    ::= { tmnxPortStatsObjs 1 }

tmnxPortNetIngressStatsEntry    OBJECT-TYPE
    SYNTAX      TmnxPortNetIngressStatsEntry
    MAX-ACCESS  not-accessible
    STATUS      current
    DESCRIPTION
        "Defines an entry in tmnxPortNetIngressStatsTable. Entries are
         created and deleted by the system depending on the queue policy
         being used at the specific port."
    INDEX   { tmnxChassisIndex, tmnxPortPortID, tmnxPortNetIngressQueueIndex }
    ::= { tmnxPortNetIngressStatsTable 1 }

TmnxPortNetIngressStatsEntry ::=
    SEQUENCE {
        tmnxPortNetIngressQueueIndex      TQueueId,
        tmnxPortNetIngressFwdInProfPkts   Counter64,
        tmnxPortNetIngressFwdOutProfPkts  Counter64,
        tmnxPortNetIngressFwdInProfOcts   Counter64,
        tmnxPortNetIngressFwdOutProfOcts  Counter64,
        tmnxPortNetIngressDroInProfPkts   Counter64,
        tmnxPortNetIngressDroOutProfPkts  Counter64,
        tmnxPortNetIngressDroInProfOcts   Counter64,
        tmnxPortNetIngressDroOutProfOcts  Counter64
    }

tmnxPortNetIngressQueueIndex OBJECT-TYPE
    SYNTAX      TQueueId (1..16)
    MAX-ACCESS  not-accessible
    STATUS      current
    DESCRIPTION
        "tmnxPortNetIngressQueueIndex serves as the tertiary index. When used
         in conjunction with tmnxChassisIndex and tmnxPortPortID, it uniquely
         identifies a network ingress queue for the specified port in the
         managed system."
    ::= { tmnxPortNetIngressStatsEntry 1 }

tmnxPortNetIngressFwdInProfPkts OBJECT-TYPE
    SYNTAX      Counter64
    MAX-ACCESS  read-only
    STATUS      current
    DESCRIPTION
        "tmnxPortNetIngressFwdInProfPkts indicates the number of conforming
         network ingress packets forwarded on this port using this queue."
    ::= { tmnxPortNetIngressStatsEntry 2 }

tmnxPortNetIngressFwdOutProfPkts OBJECT-TYPE
    SYNTAX      Counter64
    MAX-ACCESS  read-only
    STATUS      current
    DESCRIPTION
        "tmnxPortNetIngressFwdOutProfPkts indicates the number of exceeding
         network ingress packets forwarded on this port using this queue."
    ::= { tmnxPortNetIngressStatsEntry 3 }

tmnxPortNetIngressFwdInProfOcts OBJECT-TYPE
    SYNTAX      Counter64
    MAX-ACCESS  read-only
    STATUS      current
    DESCRIPTION
        "tmnxPortNetIngressFwdInProfOcts indicates the number of conforming
         network ingress octets forwarded on this port using this queue."
    ::= { tmnxPortNetIngressStatsEntry 4 }

tmnxPortNetIngressFwdOutProfOcts OBJECT-TYPE
    SYNTAX      Counter64
    MAX-ACCESS  read-only
    STATUS      current
    DESCRIPTION
        "tmnxPortNetIngressFwdOutProfOcts indicates the number of exceeding
         network ingress octets forwarded on this port using this queue."
    ::= { tmnxPortNetIngressStatsEntry 5 }

tmnxPortNetIngressDroInProfPkts OBJECT-TYPE
    SYNTAX      Counter64
    MAX-ACCESS  read-only
    STATUS      current
    DESCRIPTION
        "tmnxPortNetIngressDroInProfPkts indicates the number of conforming
         network ingress packets dropped on this port using this queue."
    ::= { tmnxPortNetIngressStatsEntry 6 }

tmnxPortNetIngressDroOutProfPkts OBJECT-TYPE
    SYNTAX      Counter64
    MAX-ACCESS  read-only
    STATUS      current
    DESCRIPTION
        "tmnxPortNetIngressDroOutProfPkts indicates the number of exceeding
         network ingress packets dropped on this port using this queue."
    ::= { tmnxPortNetIngressStatsEntry 7 }

tmnxPortNetIngressDroInProfOcts OBJECT-TYPE
    SYNTAX      Counter64
    MAX-ACCESS  read-only
    STATUS      current
    DESCRIPTION
        "tmnxPortNetIngressDroInProfOcts indicates the number of conforming
         network ingress octets dropped on this port using this queue."
    ::= { tmnxPortNetIngressStatsEntry 8 }

tmnxPortNetIngressDroOutProfOcts OBJECT-TYPE
    SYNTAX      Counter64
    MAX-ACCESS  read-only
    STATUS      current
    DESCRIPTION
        "tmnxPortNetIngressDroOutProfOcts indicates the number of exceeding
         network ingress octets dropped on this port using this queue."
    ::= { tmnxPortNetIngressStatsEntry 9 }

--
--  Network Port Egress Stats Table
--
tmnxPortNetEgressStatsTable OBJECT-TYPE
    SYNTAX      SEQUENCE OF TmnxPortNetEgressStatsEntry
    MAX-ACCESS  not-accessible
    STATUS      current
    DESCRIPTION
        "Defines the Alcatel-Lucent SROS series network port egress
         statistics table for providing, via SNMP, the capability of
         retrieving the traffic statistics for the physical queues
         being used for the ports to forward the network egress
         traffic."
    ::= { tmnxPortStatsObjs 2 }

tmnxPortNetEgressStatsEntry    OBJECT-TYPE
    SYNTAX      TmnxPortNetEgressStatsEntry
    MAX-ACCESS  not-accessible
    STATUS      current
    DESCRIPTION
        "Defines an entry in tmnxPortNetEgressStatsTable. Entries are
         created and deleted by the system depending on the queue policy
         being used at the specific port."
    INDEX   { tmnxChassisIndex, tmnxPortPortID, tmnxPortNetEgressQueueIndex }
    ::= { tmnxPortNetEgressStatsTable 1 }

TmnxPortNetEgressStatsEntry ::=
    SEQUENCE {
        tmnxPortNetEgressQueueIndex      TQueueId,
        tmnxPortNetEgressFwdInProfPkts   Counter64,
        tmnxPortNetEgressFwdOutProfPkts  Counter64,
        tmnxPortNetEgressFwdInProfOcts   Counter64,
        tmnxPortNetEgressFwdOutProfOcts  Counter64,
        tmnxPortNetEgressDroInProfPkts   Counter64,
        tmnxPortNetEgressDroOutProfPkts  Counter64,
        tmnxPortNetEgressDroInProfOcts   Counter64,
        tmnxPortNetEgressDroOutProfOcts  Counter64
    }

tmnxPortNetEgressQueueIndex OBJECT-TYPE
    SYNTAX      TQueueId (1..8)
    MAX-ACCESS  not-accessible
    STATUS      current
    DESCRIPTION
        "tmnxPortNetEgressQueueIndex serves as the tertiary index. When used
         in conjunction with tmnxChassisIndex and tmnxPortPortID, it uniquely
         identifies a network egress queue for the specified port in the
         managed system."
    ::= { tmnxPortNetEgressStatsEntry 1 }

tmnxPortNetEgressFwdInProfPkts OBJECT-TYPE
    SYNTAX      Counter64
    MAX-ACCESS  read-only
    STATUS      current
    DESCRIPTION
        "tmnxPortNetEgressFwdInProfPkts indicates the number of conforming
         network egress packets forwarded on this port using this queue."
    ::= { tmnxPortNetEgressStatsEntry 2 }

tmnxPortNetEgressFwdOutProfPkts OBJECT-TYPE
    SYNTAX      Counter64
    MAX-ACCESS  read-only
    STATUS      current
    DESCRIPTION
        "tmnxPortNetEgressFwdOutProfPkts indicates the number of exceeding
         network egress packets forwarded on this port using this queue."
    ::= { tmnxPortNetEgressStatsEntry 3 }

tmnxPortNetEgressFwdInProfOcts OBJECT-TYPE
    SYNTAX      Counter64
    MAX-ACCESS  read-only
    STATUS      current
    DESCRIPTION
        "tmnxPortNetEgressFwdInProfOcts indicates the number of conforming
         network egress octets forwarded on this port using this queue."
    ::= { tmnxPortNetEgressStatsEntry 4 }

tmnxPortNetEgressFwdOutProfOcts OBJECT-TYPE
    SYNTAX      Counter64
    MAX-ACCESS  read-only
    STATUS      current
    DESCRIPTION
        "tmnxPortNetEgressFwdOutProfOcts indicates the number of exceeding
         network egress octets forwarded on this port using this queue."
    ::= { tmnxPortNetEgressStatsEntry 5 }

tmnxPortNetEgressDroInProfPkts OBJECT-TYPE
    SYNTAX      Counter64
    MAX-ACCESS  read-only
    STATUS      current
    DESCRIPTION
        "tmnxPortNetEgressDroInProfPkts indicates the number of conforming
         network egress packets dropped on this port using this queue."
    ::= { tmnxPortNetEgressStatsEntry 6 }

tmnxPortNetEgressDroOutProfPkts OBJECT-TYPE
    SYNTAX      Counter64
    MAX-ACCESS  read-only
    STATUS      current
    DESCRIPTION
        "tmnxPortNetEgressDroOutProfPkts indicates the number of exceeding
         network egress packets dropped on this port using this queue."
    ::= { tmnxPortNetEgressStatsEntry 7 }

tmnxPortNetEgressDroInProfOcts OBJECT-TYPE
    SYNTAX      Counter64
    MAX-ACCESS  read-only
    STATUS      current
    DESCRIPTION
        "tmnxPortNetEgressDroInProfOcts indicates the number of conforming
         network egress octets dropped on this port using this queue."
    ::= { tmnxPortNetEgressStatsEntry 8 }

tmnxPortNetEgressDroOutProfOcts OBJECT-TYPE
    SYNTAX      Counter64
    MAX-ACCESS  read-only
    STATUS      current
    DESCRIPTION
        "tmnxPortNetEgressDroOutProfOcts indicates the number of exceeding
         network egress octets dropped on this port using this queue."
    ::= { tmnxPortNetEgressStatsEntry 9 }

--
--  Multiclass MLPPP Bundle Stats Table
--
--  This table provides per MClass MLPPP Bundle traffic statistics
--  The rows are created when tmnxBundleMlpppEntry has tmnxBundleMlpppClassCount
--  value set to enable Mclass MLPPP on a given bundle.
--

tmnxMcMlpppStatsTable OBJECT-TYPE
    SYNTAX      SEQUENCE OF TmnxMcMlpppStatsEntry
    MAX-ACCESS  not-accessible
    STATUS      current
    DESCRIPTION
        "Defines the Alcatel-Lucent SROS series Multiclass MLPPP
         statistics table for providing the capability of
         retrieving the traffic statistics for the physical queues
         being used for a class of a multiclass MLPPP bundle to
         forward the traffic."
    ::= { tmnxPortStatsObjs 4 }

tmnxMcMlpppStatsEntry    OBJECT-TYPE
    SYNTAX      TmnxMcMlpppStatsEntry
    MAX-ACCESS  not-accessible
    STATUS      current
    DESCRIPTION
        "Defines an entry in tmnxMcMlpppStatsTable. Entries are
         created and deleted by the system depending on the number of
         classes being used by a given MLPPP bundle."
    INDEX   { tmnxChassisIndex, tmnxBundleBundleID, tmnxMcMlpppClassIndex }
    ::= { tmnxMcMlpppStatsTable 1 }

TmnxMcMlpppStatsEntry ::=
    SEQUENCE {
        tmnxMcMlpppClassIndex          TmnxMcMlpppClassIndex,
        tmnxMcMlpppStatsIngressOct     Counter32,
        tmnxMcMlpppStatsIngressPkt     Counter32,
        tmnxMcMlpppStatsIngressErrPkt  Counter32,
        tmnxMcMlpppStatsEgressOct      Counter32,
        tmnxMcMlpppStatsEgressPkt      Counter32,
        tmnxMcMlpppStatsEgressErrPkt   Counter32
    }

tmnxMcMlpppClassIndex  OBJECT-TYPE
    SYNTAX      TmnxMcMlpppClassIndex
    MAX-ACCESS  not-accessible
    STATUS      current
    DESCRIPTION
        "tmnxMcMlpppClassIndex serves as the tertiary index. When used
         in conjunction with tmnxChassisIndex and tmnxBundleBundleID, it
         uniquely identifies a class of a multiclass MLPPP bundle in the
         managed system."
    ::= { tmnxMcMlpppStatsEntry 1 }


tmnxMcMlpppStatsIngressOct OBJECT-TYPE
    SYNTAX      Counter32
    MAX-ACCESS  read-only
    STATUS      current
    DESCRIPTION
        "The value of tmnxMcMlpppStatsIngressOct indicates the total
         number of octets in all packets received on the bundle
         for the given class on ingress before reassembly."
    ::= { tmnxMcMlpppStatsEntry 2 }

tmnxMcMlpppStatsIngressPkt OBJECT-TYPE
    SYNTAX      Counter32
    MAX-ACCESS  read-only
    STATUS      current
    DESCRIPTION
        "The value of tmnxMcMlpppStatsIngressPkt indicates the total
         number of packets forwarded on the bundle for the given
         class on ingress towards higher layer protocols."
    ::= { tmnxMcMlpppStatsEntry 3 }

tmnxMcMlpppStatsIngressErrPkt OBJECT-TYPE
    SYNTAX      Counter32
    MAX-ACCESS  read-only
    STATUS      current
    DESCRIPTION
        "The value of tmnxMcMlpppStatsIngressErrPkt indicates the total
         number of packets discarded due to reassembly errors
         on the bundle for the given class on ingress."
    ::= { tmnxMcMlpppStatsEntry 4 }

tmnxMcMlpppStatsEgressOct OBJECT-TYPE
    SYNTAX      Counter32
    MAX-ACCESS  read-only
    STATUS      current
    DESCRIPTION
        "The value of tmnxMcMlpppStatsEgressOct indicates the total
         number of octets in all packets received on the bundle
         for the given class on egress before segmentation."
    ::= { tmnxMcMlpppStatsEntry 5 }

tmnxMcMlpppStatsEgressPkt OBJECT-TYPE
    SYNTAX      Counter32
    MAX-ACCESS  read-only
    STATUS      current
    DESCRIPTION
        "The value of tmnxMcMlpppStatsEgressPkt indicates the total
         number of packets forwarded on the bundle for the given
         class on egress towards the line."
    ::= { tmnxMcMlpppStatsEntry 6 }

tmnxMcMlpppStatsEgressErrPkt OBJECT-TYPE
    SYNTAX      Counter32
    MAX-ACCESS  read-only
    STATUS      current
    DESCRIPTION
        "The value of tmnxMcMlpppStatsEgressErrPkt indicates the total
         number of packets discarded due to segmentation errors
         on the bundle for the given class on egress."
    ::= { tmnxMcMlpppStatsEntry 7 }

--
-- IMA Group Bundle Table
--
--  Sparse Dependent Extension of the tmnxBundleTable.
--
--  The same indexes are used for both the base table tmnxBundleTable,
--  and the sparse dependent table, tmnxBundleImaGrpTable.
--
--  This in effect extends the tmnxBundleTable with additional columns.
--  Rows are created in the tmnxBundleImaGrpTable only for those entries
--  in the tmnxBundleTable for a value of 'imagrp' for the bundle type.
--
--  Deletion of a row in the tmnxBundleTable results in the
--  same fate for the row in the tmnxBundleImaGrpTable.
--
tmnxBundleImaGrpTable OBJECT-TYPE
    SYNTAX      SEQUENCE OF TmnxBundleImaGrpEntry
    MAX-ACCESS  not-accessible
    STATUS      current
    DESCRIPTION
        "The tmnxBundleImaGrpTable contains IMA Group data"
    ::= { tmnxPortObjs 21 }

tmnxBundleImaGrpEntry OBJECT-TYPE
    SYNTAX      TmnxBundleImaGrpEntry
    MAX-ACCESS  not-accessible
    STATUS      current
    DESCRIPTION
        "Each row entry contains data on an IMA Group."
    INDEX       { tmnxChassisIndex, tmnxBundleBundleID }
    ::= { tmnxBundleImaGrpTable 1 }

TmnxBundleImaGrpEntry ::=
    SEQUENCE {
        tmnxBundleImaGrpLnkActTimer     Unsigned32,
        tmnxBundleImaGrpLnkDeactTimer   Unsigned32,
        tmnxBundleImaGrpSymmetryMode    INTEGER,
        tmnxBundleImaGrpTxId            INTEGER,
        tmnxBundleImaGrpRxId            INTEGER,
        tmnxBundleImaGrpTxRefLnk        TmnxPortID,
        tmnxBundleImaGrpRxRefLnk        TmnxPortID,
        tmnxBundleImaGrpSmNeState       TmnxImaGrpState,
        tmnxBundleImaGrpSmFeState       TmnxImaGrpState,
        tmnxBundleImaGrpSmFailState     TmnxImaGrpFailState,
        tmnxBundleImaGrpSmDownSecs      Counter32,
        tmnxBundleImaGrpSmOperSecs      Counter32,
        tmnxBundleImaGrpAvailTxCR       Gauge32,
        tmnxBundleImaGrpAvailRxCR       Gauge32,
        tmnxBundleImaGrpNeFails         Counter32,
        tmnxBundleImaGrpFeFails         Counter32,
        tmnxBundleImaGrpTxIcpCells      Counter32,
        tmnxBundleImaGrpRxIcpCells      Counter32,
        tmnxBundleImaGrpErrorIcpCells   Counter32,
        tmnxBundleImaGrpLostRxIcpCells  Counter32,
        tmnxBundleImaGrpTxOamLablVal    INTEGER,
        tmnxBundleImaGrpRxOamLablVal    INTEGER,
        tmnxBundleImaGrpAlphaValue      INTEGER,
        tmnxBundleImaGrpBetaValue       INTEGER,
        tmnxBundleImaGrpGammaValue      INTEGER,
        tmnxBundleImaGrpNeClockMode     TmnxImaGrpClockModes,
        tmnxBundleImaGrpFeClockMode     TmnxImaGrpClockModes,
        tmnxBundleImaGrpVersion         TmnxImaGrpVersion,
        tmnxBundleImaGrpMaxConfBw       Unsigned32,
        tmnxBundleImaGrpTestState       TmnxImaTestState,
        tmnxBundleImaGrpTestMember      TmnxPortID,
        tmnxBundleImaGrpTestPattern     INTEGER,
        tmnxBundleImaGrpDiffDelayMaxObs Unsigned32,
        tmnxBundleImaGrpLeastDelayLink  Unsigned32
    }

tmnxBundleImaGrpLnkActTimer OBJECT-TYPE
    SYNTAX      Unsigned32 (1..30000)
    UNITS       "milliseconds"
    MAX-ACCESS  read-create
    STATUS      current
    DESCRIPTION
        "tmnxBundleImaGrpLnkActTimer specifies the Link Activation Timer
         used to clear an existing LIF, LODS and FRI-IMA alarm. The time
         specified determines how long is needed for member links to
         stabilize before being activated."
    DEFVAL { 10000 }
    ::= { tmnxBundleImaGrpEntry 1 }

tmnxBundleImaGrpLnkDeactTimer OBJECT-TYPE
    SYNTAX      Unsigned32 (1..30000)
    UNITS       "milliseconds"
    MAX-ACCESS  read-create
    STATUS      current
    DESCRIPTION
        "tmnxBundleImaGrpLnkDeactTimer specifies the Link Deactivation Timer
         used to raise an LIF, LODS and FRI-IMA alarm. The time
         specified determines how long before a member link is declared in
         error and is deactivated."
    DEFVAL { 2000 }
    ::= { tmnxBundleImaGrpEntry 2 }

tmnxBundleImaGrpSymmetryMode OBJECT-TYPE
    SYNTAX      INTEGER {
                    symmetric (1)
                }
    MAX-ACCESS  read-create
    STATUS      current
    DESCRIPTION
        "tmnxBundleImaGrpSymmetryMode specifies the type of cell rate
         transfer over the virtual link."
    DEFVAL { symmetric }
    ::= { tmnxBundleImaGrpEntry 3 }

tmnxBundleImaGrpTxId OBJECT-TYPE
    SYNTAX      INTEGER
    MAX-ACCESS  read-only
    STATUS      current
    DESCRIPTION
        "tmnxBundleImaGrpTxId specifies the IMA Id generated at group
         creation time used by the near-end."
    ::= { tmnxBundleImaGrpEntry 4 }

tmnxBundleImaGrpRxId OBJECT-TYPE
    SYNTAX      INTEGER
    MAX-ACCESS  read-only
    STATUS      current
    DESCRIPTION
        "tmnxBundleImaGrpRxId specifies the IMA ID generated at group
         creation time used by the far-end."
    ::= { tmnxBundleImaGrpEntry 5 }

tmnxBundleImaGrpTxRefLnk OBJECT-TYPE
    SYNTAX      TmnxPortID
    MAX-ACCESS  read-only
    STATUS      current
    DESCRIPTION
        "tmnxBundleImaGrpTxRefLnk specifies the IMA bundle member
         that was selected to be the transmit timing reference link.
         If no member has been selected as the reference link a value
         of zero is returned. "
    ::= { tmnxBundleImaGrpEntry 6 }

tmnxBundleImaGrpRxRefLnk OBJECT-TYPE
    SYNTAX      TmnxPortID
    MAX-ACCESS  read-only
    STATUS      current
    DESCRIPTION
        "tmnxBundleImaGrpRxRefLnk specifies the IMA bundle member
         that was detected to be the receive timing reference link.
         If no member has been detected as the reference link a value
         of zero is returned. "
    ::= { tmnxBundleImaGrpEntry 7 }

tmnxBundleImaGrpSmNeState OBJECT-TYPE
    SYNTAX      TmnxImaGrpState
    MAX-ACCESS  read-only
    STATUS      current
    DESCRIPTION
        "tmnxBundleImaGrpSmNeState specifies the current state
         of the IMA Group for the near-end."
    ::= { tmnxBundleImaGrpEntry 8 }

tmnxBundleImaGrpSmFeState OBJECT-TYPE
    SYNTAX      TmnxImaGrpState
    MAX-ACCESS  read-only
    STATUS      current
    DESCRIPTION
        "tmnxBundleImaGrpSmFeState specifies the current state
         of the IMA Group for the far-end."
    ::= { tmnxBundleImaGrpEntry 9 }

tmnxBundleImaGrpSmFailState OBJECT-TYPE
    SYNTAX      TmnxImaGrpFailState
    MAX-ACCESS  read-only
    STATUS      current
    DESCRIPTION
        "tmnxBundleImaGrpSmFailState specifies the current state
         of the IMA Group."
    ::= { tmnxBundleImaGrpEntry 10 }

tmnxBundleImaGrpSmDownSecs OBJECT-TYPE
    SYNTAX      Counter32
    MAX-ACCESS  read-only
    STATUS      current
    DESCRIPTION
        "tmnxBundleImaGrpSmDownSecs specifies the number of seconds
         that the IMA Group State Machine is not Operational."
    ::= { tmnxBundleImaGrpEntry 11 }

tmnxBundleImaGrpSmOperSecs OBJECT-TYPE
    SYNTAX      Counter32
    MAX-ACCESS  read-only
    STATUS      current
    DESCRIPTION
        "tmnxBundleImaGrpSmOperSecs specifies the number of seconds
         that the IMA Group State Machine has been in the Operational
         State."
    ::= { tmnxBundleImaGrpEntry 12 }

tmnxBundleImaGrpAvailTxCR OBJECT-TYPE
    SYNTAX      Gauge32
    MAX-ACCESS  read-only
    STATUS      current
    DESCRIPTION
        "tmnxBundleImaGrpAvailTxCR specifies the available transmit
         bandwidth on this IMA group. It only considers members that
         are in the Active State."
    ::= { tmnxBundleImaGrpEntry 13 }

tmnxBundleImaGrpAvailRxCR OBJECT-TYPE
    SYNTAX      Gauge32
    MAX-ACCESS  read-only
    STATUS      current
    DESCRIPTION
        "tmnxBundleImaGrpAvailRxCR specifies the available bandwidth
         on this IMA group in the receive direction. It only considers
         members that are in the Active State."
    ::= { tmnxBundleImaGrpEntry 14 }

tmnxBundleImaGrpNeFails OBJECT-TYPE
    SYNTAX      Counter32
    MAX-ACCESS  read-only
    STATUS      current
    DESCRIPTION
        "tmnxBundleImaGrpNeFails specifies the number of reported
         IMA Group failures since boot time."
    ::= { tmnxBundleImaGrpEntry 15 }

tmnxBundleImaGrpFeFails OBJECT-TYPE
    SYNTAX      Counter32
    MAX-ACCESS  read-only
    STATUS      current
    DESCRIPTION
        "tmnxBundleImaGrpFeFails specifies the number of reported
         IMA Group far-end failures since boot time."
    ::= { tmnxBundleImaGrpEntry 16 }

tmnxBundleImaGrpTxIcpCells OBJECT-TYPE
    SYNTAX      Counter32
    MAX-ACCESS  read-only
    STATUS      current
    DESCRIPTION
        "tmnxBundleImaGrpTxIcpCells specifies number of transmitted
         ICP cells for this IMA Group."
    ::= { tmnxBundleImaGrpEntry 17 }

tmnxBundleImaGrpRxIcpCells OBJECT-TYPE
    SYNTAX      Counter32
    MAX-ACCESS  read-only
    STATUS      current
    DESCRIPTION
        "tmnxBundleImaGrpRxIcpCells specifies number of received
         ICP cells for this IMA Group."
    ::= { tmnxBundleImaGrpEntry 18 }

tmnxBundleImaGrpErrorIcpCells OBJECT-TYPE
    SYNTAX      Counter32
    MAX-ACCESS  read-only
    STATUS      current
    DESCRIPTION
        "tmnxBundleImaGrpErrorIcpCells specifies number of
         ICP cells with HEC or CRC-10 errors."
    ::= { tmnxBundleImaGrpEntry 19 }

tmnxBundleImaGrpLostRxIcpCells OBJECT-TYPE
    SYNTAX      Counter32
    MAX-ACCESS  read-only
    STATUS      current
    DESCRIPTION
        "tmnxBundleImaGrpLostRxIcpCells specifies the number of
         missing ICP cells at the expected offset."
    ::= { tmnxBundleImaGrpEntry 20 }

tmnxBundleImaGrpTxOamLablVal OBJECT-TYPE
    SYNTAX      INTEGER
    MAX-ACCESS  read-only
    STATUS      current
    DESCRIPTION
        "tmnxBundleImaGrpTxOamLablVal specifies near-end value
         to be transmitted."
    ::= { tmnxBundleImaGrpEntry 21 }

tmnxBundleImaGrpRxOamLablVal OBJECT-TYPE
    SYNTAX      INTEGER
    MAX-ACCESS  read-only
    STATUS      current
    DESCRIPTION
        "tmnxBundleImaGrpRxOamLablVal specifies far-end value
         received."
    ::= { tmnxBundleImaGrpEntry 22 }

tmnxBundleImaGrpAlphaValue OBJECT-TYPE
    SYNTAX      INTEGER
    MAX-ACCESS  read-create
    STATUS      current
    DESCRIPTION
        "tmnxBundleImaGrpAlphaValue specifies the number of
         consecutive ICP cells that need to be detected
         before moving from the IMA Sync State to the IMA Hunt
         State."
    DEFVAL { 2 }
    ::= { tmnxBundleImaGrpEntry 23 }

tmnxBundleImaGrpBetaValue OBJECT-TYPE
    SYNTAX      INTEGER
    MAX-ACCESS  read-create
    STATUS      current
    DESCRIPTION
        "tmnxBundleImaGrpBetaValue specifies the number of
         consecutive errored ICP cells that need to be detected
         before moving from the IMA Sync State to the IMA Hunt
         State"
    DEFVAL { 2 }
    ::= { tmnxBundleImaGrpEntry 24 }

tmnxBundleImaGrpGammaValue OBJECT-TYPE
    SYNTAX      INTEGER
    MAX-ACCESS  read-create
    STATUS      current
    DESCRIPTION
        "tmnxBundleImaGrpGammaValue specifies the number of
         consecutive valid ICP cells that need to be detected
         before moving from the IMA pre-Sync State to the
         IMA Hunt State."
    DEFVAL { 1 }
    ::= { tmnxBundleImaGrpEntry 25 }

tmnxBundleImaGrpNeClockMode OBJECT-TYPE
    SYNTAX      TmnxImaGrpClockModes
    MAX-ACCESS  read-create
    STATUS      current
    DESCRIPTION
        "tmnxBundleImaGrpNeClockMode specifies near-end transmit
         clock mode."
    DEFVAL { ctc }
    ::= { tmnxBundleImaGrpEntry 26 }

tmnxBundleImaGrpFeClockMode OBJECT-TYPE
    SYNTAX      TmnxImaGrpClockModes
    MAX-ACCESS  read-create
    STATUS      current
    DESCRIPTION
        "tmnxBundleImaGrpFeClockMode specifies far-end transmit
         clock mode."
    DEFVAL { ctc }
    ::= { tmnxBundleImaGrpEntry 27 }

tmnxBundleImaGrpVersion OBJECT-TYPE
    SYNTAX      TmnxImaGrpVersion
    MAX-ACCESS  read-create
    STATUS      current
    DESCRIPTION
        "tmnxBundleImaGrpVersion specifies the IMA Version for
         this group."
    DEFVAL { oneDotOne }
    ::= { tmnxBundleImaGrpEntry 28 }

tmnxBundleImaGrpMaxConfBw OBJECT-TYPE
    SYNTAX      Unsigned32 (1..8)
    MAX-ACCESS  read-create
    STATUS      current
    DESCRIPTION
        "tmnxBundleImaGrpMaxConfBw specifies the number of links
         that is used to determine the maximum configurable
         bandwidth that is allowed to be used for this IMA group."
    DEFVAL { 8 }
    ::= { tmnxBundleImaGrpEntry 29 }

tmnxBundleImaGrpTestState OBJECT-TYPE
    SYNTAX      TmnxImaTestState
    MAX-ACCESS  read-create
    STATUS      current
    DESCRIPTION
        "tmnxBundleImaGrpTestState specifies the current state of
         the test pattern procedure. A value of 'disabled' specifies
         that the group is currently not running. A value of
         'operating' enables the test pattern procedure. The test
         pattern procedure continues until it is 'disabled'."
    DEFVAL { disabled }
    ::= { tmnxBundleImaGrpEntry 30 }

tmnxBundleImaGrpTestMember OBJECT-TYPE
    SYNTAX      TmnxPortID
    MAX-ACCESS  read-create
    STATUS      current
    DESCRIPTION
        "tmnxBundleImaGrpTestMember specifies a member link to
         be used for the test pattern procedure. A value of zero
         indicates that no member link has been selected.

         When tmnxBundleImaGrpTestState does not have the value
         'disabled', an attempt to set this object will be
         rejected with an inconsistentValue error."
    DEFVAL { 0 }
    ::= { tmnxBundleImaGrpEntry 31 }

tmnxBundleImaGrpTestPattern OBJECT-TYPE
    SYNTAX      INTEGER (0..255)
    MAX-ACCESS  read-create
    STATUS      current
    DESCRIPTION
        "tmnxBundleImaGrpTestPattern specifies the Transmit Test
         Pattern in an IMA group loopback operation. This value
         may only be changed when tmnxBundleImaGrpTestState is
         'disabled'."
    DEFVAL { 0 }
    ::= { tmnxBundleImaGrpEntry 32 }

tmnxBundleImaGrpDiffDelayMaxObs OBJECT-TYPE
    SYNTAX      Unsigned32
    UNITS       "milliseconds"
    MAX-ACCESS  read-only
    STATUS      current
    DESCRIPTION
        "tmnxBundleImaGrpDiffDelayMaxObs indicates the latest
         maximum differential delay observed between links
         having the least and most link propagation delay
         among the received links configured in this IMA group."
    ::= { tmnxBundleImaGrpEntry 33 }

tmnxBundleImaGrpLeastDelayLink OBJECT-TYPE
    SYNTAX      Unsigned32
    UNITS       "milliseconds"
    MAX-ACCESS  read-only
    STATUS      current
    DESCRIPTION
        "tmnxBundleImaGrpLeastDelayLink indicates a member link
         which has the smallest link propagation delay. If this
         delay has yet to be determined or no member link has
         been configured, a value of zero is returned."
    ::= { tmnxBundleImaGrpEntry 34 }

--
-- IMA Group Member Table
--
--  Sparse Dependent Extension of the tmnxBundleMemberTable.
--
--  The same indexes are used for both the base table tmnxBundleMemberTable,
--  and the sparse dependent table, tmnxBundleMemberImaTable.
--
--  This in effect extends the tmnxBundleMemberTable with additional columns.
--  Rows are created in the tmnxBundleMemberImaTable only for those entries
--  in the tmnxBundleMemberTable that were created and have a value of 'imagrp'
--  for the bundle type.
--
--  Deletion of a row in the tmnxBundleMemberTable results in the
--  same fate for the row in the tmnxBundleMemberImaTable.
--

tmnxBundleMemberImaTable OBJECT-TYPE
    SYNTAX      SEQUENCE OF TmnxBundleMemberImaEntry
    MAX-ACCESS  not-accessible
    STATUS      current
    DESCRIPTION
        "The tmnxBundleMemberImaTable has an entry for an
         IMA link associated with an IMA Group."
    ::= { tmnxPortObjs 22 }

tmnxBundleMemberImaEntry  OBJECT-TYPE
    SYNTAX      TmnxBundleMemberImaEntry
    MAX-ACCESS  not-accessible
    STATUS      current
    DESCRIPTION
        "Each row entry represents an IMA link associated with
         an IMA Group."
    INDEX   { tmnxBundleBundleID, tmnxPortPortID }
    ::= { tmnxBundleMemberImaTable 1 }

TmnxBundleMemberImaEntry ::=
    SEQUENCE {
        tmnxBundleMemberImaNeTxState     TmnxImaLnkState,
        tmnxBundleMemberImaNeRxState     TmnxImaLnkState,
        tmnxBundleMemberImaFeTxState     TmnxImaLnkState,
        tmnxBundleMemberImaFeRxState     TmnxImaLnkState,
        tmnxBundleMemberImaNeRxFailState TmnxImaLnkFailState,
        tmnxBundleMemberImaFeRxFailState TmnxImaLnkFailState,
        tmnxBundleMemberImaTxLid         INTEGER,
        tmnxBundleMemberImaRxLid         INTEGER,
        tmnxBundleMemberImaViolations    Counter32,
        tmnxBundleMemberImaNeSevErrSecs  Counter32,
        tmnxBundleMemberImaFeSevErrSecs  Counter32,
        tmnxBundleMemberImaNeUnavailSecs Counter32,
        tmnxBundleMemberImaFeUnavailSecs Counter32,
        tmnxBundleMemberImaNeTxUnuseSecs Counter32,
        tmnxBundleMemberImaNeRxUnuseSecs Counter32,
        tmnxBundleMemberImaFeTxUnuseSecs Counter32,
        tmnxBundleMemberImaFeRxUnuseSecs Counter32,
        tmnxBundleMemberImaNeTxNumFails  Counter32,
        tmnxBundleMemberImaNeRxNumFails  Counter32,
        tmnxBundleMemberImaFeTxNumFails  Counter32,
        tmnxBundleMemberImaFeRxNumFails  Counter32,
        tmnxBundleMemberImaTxIcpCells    Counter32,
        tmnxBundleMemberImaRxIcpCells    Counter32,
        tmnxBundleMemberImaErrorIcpCells Counter32,
        tmnxBundleMemberImaLstRxIcpCells Counter32,
        tmnxBundleMemberImaOifAnomalies  Counter32,
        tmnxBundleMemberImaRxTestState   TmnxImaTestState,
        tmnxBundleMemberImaRxTestPattern INTEGER,
        tmnxBundleMemberImaRelDelay      Unsigned32

    }

tmnxBundleMemberImaNeTxState    OBJECT-TYPE
    SYNTAX      TmnxImaLnkState
    MAX-ACCESS  read-only
    STATUS      current
    DESCRIPTION
        "tmnxBundleMemberImaNeTxState indicates the state of near-end
         transmit IMA link."
    ::= { tmnxBundleMemberImaEntry 1 }

tmnxBundleMemberImaNeRxState    OBJECT-TYPE
    SYNTAX      TmnxImaLnkState
    MAX-ACCESS  read-only
    STATUS      current
    DESCRIPTION
        "tmnxBundleMemberImaNeRxState indicates the state of near-end
         receive IMA link."
    ::= { tmnxBundleMemberImaEntry 2 }

tmnxBundleMemberImaFeTxState    OBJECT-TYPE
    SYNTAX      TmnxImaLnkState
    MAX-ACCESS  read-only
    STATUS      current
    DESCRIPTION
        "tmnxBundleMemberImaFeTxState indicates the state of far-end
         transmit IMA link."
    ::= { tmnxBundleMemberImaEntry 3 }

tmnxBundleMemberImaFeRxState    OBJECT-TYPE
    SYNTAX      TmnxImaLnkState
    MAX-ACCESS  read-only
    STATUS      current
    DESCRIPTION
        "tmnxBundleMemberImaFeRxState indicates the state of far-end
         receive IMA link."
    ::= { tmnxBundleMemberImaEntry 4 }

tmnxBundleMemberImaNeRxFailState    OBJECT-TYPE
    SYNTAX      TmnxImaLnkFailState
    MAX-ACCESS  read-only
    STATUS      current
    DESCRIPTION
        "tmnxBundleMemberImaNeRxFailState indicates the IMA link failure
         reason for the near-end."
    ::= { tmnxBundleMemberImaEntry 5 }

tmnxBundleMemberImaFeRxFailState    OBJECT-TYPE
    SYNTAX      TmnxImaLnkFailState
    MAX-ACCESS  read-only
    STATUS      current
    DESCRIPTION
        "tmnxBundleMemberImaFeRxFailState indicates the IMA link failure
         reason for the far-end."
    ::= { tmnxBundleMemberImaEntry 6 }

tmnxBundleMemberImaTxLid OBJECT-TYPE
    SYNTAX      INTEGER
    MAX-ACCESS  read-only
    STATUS      current
    DESCRIPTION
        "tmnxBundleMemberImaTxLid indicates the Link Identifier
         assigned to the transmit IMA link."
    ::= { tmnxBundleMemberImaEntry 7 }

tmnxBundleMemberImaRxLid OBJECT-TYPE
    SYNTAX      INTEGER
    MAX-ACCESS  read-only
    STATUS      current
    DESCRIPTION
        "tmnxBundleMemberImaRxLid indicates the Link Identifier
         used on the receive IMA link."
    ::= { tmnxBundleMemberImaEntry 8 }

tmnxBundleMemberImaViolations OBJECT-TYPE
    SYNTAX      Counter32
    MAX-ACCESS  read-only
    STATUS      current
    DESCRIPTION
        "tmnxBundleMemberImaViolations indicates the number of
         ICP violations including errored, invalid or missing ICP
         cells."
    ::= { tmnxBundleMemberImaEntry 9 }

tmnxBundleMemberImaNeSevErrSecs OBJECT-TYPE
    SYNTAX      Counter32
    MAX-ACCESS  read-only
    STATUS      current
    DESCRIPTION
        "tmnxBundleMemberImaNeSevErrSecs indicates the number
         of one second intervals in which thirty percent or
         more of the near-end ICP cells are in violation, or
         link defects have occurred."
    ::= { tmnxBundleMemberImaEntry 10 }

tmnxBundleMemberImaFeSevErrSecs OBJECT-TYPE
    SYNTAX      Counter32
    MAX-ACCESS  read-only
    STATUS      current
    DESCRIPTION
        "tmnxBundleMemberImaFeSevErrSecs indicates the number
         of one second intervals in which the far-end contains
         IMA-RDI defects."
    ::= { tmnxBundleMemberImaEntry 11 }

tmnxBundleMemberImaNeUnavailSecs OBJECT-TYPE
    SYNTAX      Counter32
    MAX-ACCESS  read-only
    STATUS      current
    DESCRIPTION
        "tmnxBundleMemberImaNeUnavailSecs indicates the number
         of unavailable seconds at the near-end."
    ::= { tmnxBundleMemberImaEntry 12 }

tmnxBundleMemberImaFeUnavailSecs OBJECT-TYPE
    SYNTAX      Counter32
    MAX-ACCESS  read-only
    STATUS      current
    DESCRIPTION
        "tmnxBundleMemberImaFeUnavailSecs indicates the number
         of unavailable seconds at the near-end."
    ::= { tmnxBundleMemberImaEntry 13 }

tmnxBundleMemberImaNeTxUnuseSecs OBJECT-TYPE
    SYNTAX      Counter32
    MAX-ACCESS  read-only
    STATUS      current
    DESCRIPTION
        "tmnxBundleMemberImaNeTxUnuseSecs indicates the number
         of unavailable seconds at the near-end transmit link
         state machine."
    ::= { tmnxBundleMemberImaEntry 14 }

tmnxBundleMemberImaNeRxUnuseSecs OBJECT-TYPE
    SYNTAX      Counter32
    MAX-ACCESS  read-only
    STATUS      current
    DESCRIPTION
        "tmnxBundleMemberImaNeRxUnuseSecs indicates the number
         of unavailable seconds at the near-end receive link
         state machine."
    ::= { tmnxBundleMemberImaEntry 15 }

tmnxBundleMemberImaFeTxUnuseSecs OBJECT-TYPE
    SYNTAX      Counter32
    MAX-ACCESS  read-only
    STATUS      current
    DESCRIPTION
        "tmnxBundleMemberImaFeTxUnuseSecs indicates the number
         of unavailable seconds at the far-end transmit link
         state machine."
    ::= { tmnxBundleMemberImaEntry 16 }

tmnxBundleMemberImaFeRxUnuseSecs OBJECT-TYPE
    SYNTAX      Counter32
    MAX-ACCESS  read-only
    STATUS      current
    DESCRIPTION
        "tmnxBundleMemberImaFeRxUnuseSecs indicates the number
         of unavailable seconds at the far-end receive link
         state machine."
    ::= { tmnxBundleMemberImaEntry 17 }

tmnxBundleMemberImaNeTxNumFails OBJECT-TYPE
    SYNTAX      Counter32
    MAX-ACCESS  read-only
    STATUS      current
    DESCRIPTION
        "tmnxBundleMemberImaNeTxNumFails indicates the number
         of times that a near-end transmit alarm is set on the
         IMA link."
    ::= { tmnxBundleMemberImaEntry 18 }

tmnxBundleMemberImaNeRxNumFails OBJECT-TYPE
    SYNTAX      Counter32
    MAX-ACCESS  read-only
    STATUS      current
    DESCRIPTION
        "tmnxBundleMemberImaNeRxNumFails indicates the number
         of times that a near-end receive alarm is set on the
         IMA link."
    ::= { tmnxBundleMemberImaEntry 19 }

tmnxBundleMemberImaFeTxNumFails OBJECT-TYPE
    SYNTAX      Counter32
    MAX-ACCESS  read-only
    STATUS      current
    DESCRIPTION
        "tmnxBundleMemberImaFeTxNumFails indicates the number
         of times that a far-end transmit alarm is set on the
         IMA link."
    ::= { tmnxBundleMemberImaEntry 20 }

tmnxBundleMemberImaFeRxNumFails OBJECT-TYPE
    SYNTAX      Counter32
    MAX-ACCESS  read-only
    STATUS      current
    DESCRIPTION
        "tmnxBundleMemberImaFeRxNumFails indicates the number
         of times that a far-end receive alarm is set on the
         IMA link."
    ::= { tmnxBundleMemberImaEntry 21 }

tmnxBundleMemberImaTxIcpCells OBJECT-TYPE
    SYNTAX      Counter32
    MAX-ACCESS  read-only
    STATUS      current
    DESCRIPTION
        "tmnxBundleMemberImaTxIcpCells indicates the number
         of ICP cells that have been transmitted on the IMA
         link."
    ::= { tmnxBundleMemberImaEntry 22 }

tmnxBundleMemberImaRxIcpCells OBJECT-TYPE
    SYNTAX      Counter32
    MAX-ACCESS  read-only
    STATUS      current
    DESCRIPTION
        "tmnxBundleMemberImaRxIcpCells indicates the number
         of ICP cells that have been received on the IMA
         link."
    ::= { tmnxBundleMemberImaEntry 23 }

tmnxBundleMemberImaErrorIcpCells OBJECT-TYPE
    SYNTAX      Counter32
    MAX-ACCESS  read-only
    STATUS      current
    DESCRIPTION
        "tmnxBundleMemberImaErrorIcpCells indicates the number
         of ICP cells with HEC or CRC-10 errors."
    ::= { tmnxBundleMemberImaEntry 24 }

tmnxBundleMemberImaLstRxIcpCells OBJECT-TYPE
    SYNTAX      Counter32
    MAX-ACCESS  read-only
    STATUS      current
    DESCRIPTION
        "tmnxBundleMemberImaLstRxIcpCells indicates the number
         of lost ICP cells at the expected offset."
    ::= { tmnxBundleMemberImaEntry 25 }

tmnxBundleMemberImaOifAnomalies OBJECT-TYPE
    SYNTAX      Counter32
    MAX-ACCESS  read-only
    STATUS      current
    DESCRIPTION
        "tmnxBundleMemberImaOifAnomalies indicates the number
         of OIF anomalies at the near-end."
    ::= { tmnxBundleMemberImaEntry 26 }

tmnxBundleMemberImaRxTestState OBJECT-TYPE
    SYNTAX      TmnxImaTestState
    MAX-ACCESS  read-only
    STATUS      current
    DESCRIPTION
        "tmnxBundleMemberImaRxTestState indicates the current
         state of the test pattern on this link."
    ::= { tmnxBundleMemberImaEntry 27 }

tmnxBundleMemberImaRxTestPattern OBJECT-TYPE
    SYNTAX      INTEGER (0..255)
    MAX-ACCESS  read-only
    STATUS      current
    DESCRIPTION
        "tmnxBundleMemberImaRxTestPattern indicates the received
        test pattern value on this link."
    ::= { tmnxBundleMemberImaEntry 28 }

tmnxBundleMemberImaRelDelay OBJECT-TYPE
    SYNTAX      Unsigned32
    UNITS       "milliseconds"
    MAX-ACCESS  read-only
    STATUS      current
    DESCRIPTION
        "tmnxBundleMemberImaRelDelay indicates the latest measured
        delay on this member link relative to the member link with
        the least delay within the same IMA group"
    ::= { tmnxBundleMemberImaEntry 29 }

--
--     Configuration Scalars 
--

tmnxPortScalarObjs OBJECT IDENTIFIER ::= { tmnxPortObjs 19 }

tmnxL4LoadBalancing OBJECT-TYPE
    SYNTAX      TruthValue
    MAX-ACCESS  read-write
    STATUS      current
    DESCRIPTION
        "The value of tmnxL4LoadBalancing specifies whether layer 4 information,
         src and dst ports, should be used in the LAG and ECMP hashing
         algorithm. This is the global system setting that all ports will
         inherit. When set to 'true', src and dst ports are used in the hashing
         algorithm. The per port setting of tmnxPortLoadBalanceAlgorithm can
         override tmnxL4LoadBalancing."
    DEFVAL { false }
    ::= { tmnxPortScalarObjs 1 }

tmnxLsrIpLoadBalancing           OBJECT-TYPE
    SYNTAX      INTEGER {
                    label-only (1),
                    label-ip   (2),
                    ip-only    (3),
                   eth-encap-ip (4)
                }
    MAX-ACCESS  read-write
    STATUS      current
    DESCRIPTION
        "The value of tmnxLsrIpLoadBalancing specifies whether the IP Header is
         used in the LAG and ECMP LSR hashing algorithm. This is the global
         system setting that all ports will inherit.
         
         When set to 'label-ip (2)', the IP Header is included in the hashing 
         algorithm.

         When set to 'ip-only (3)' the IP Header is used exclusively in the 
         hashing algorithm.

         When set to 'eth-encap-ip (4)' the IP SA/DA fields is used in the 
         hashing Algorithm.
         "
    DEFVAL { label-only }
    ::= { tmnxPortScalarObjs 2 }

tmnxIpLoadBalancing              OBJECT-TYPE
    SYNTAX      INTEGER {
                    standard (1),
                    systemIp (2)
                }
    MAX-ACCESS  read-write
    STATUS      current
    DESCRIPTION
        "The value of tmnxIpLoadBalancing specifies whether or not this node's
         system IP address is used in the final stage of the load balancing
         (hashing) algorithm used to choose the LAG member or ECMP route for an
         outbound packet.

         If 'systemIp(2)' is selected, this node's system IP address (i.e.
         TIMETRA-VRTR-MIB::vRiaIpAddress.1.1.1) is used in the final stage of
         the LAG and ECMP load balancing algorithm.  This selection makes it
         more likely that different SROS nodes in a network will make different
         load balancing decisions.  'systemIp(2)' is supported on iom3-xp IOMs,
         equivalent IMMs, and newer IOM and IMM types.  When older IOMs/IMMs are
         present in a system which has 'systemIp(2)' configured, the older IOMs
         operate in 'standard(1)' mode.

         If 'standard(1)' is selected, this node's system IP address is not used
         in the final stage of the LAG and ECMP load balancing algorithm.
         'standard(1)' is supported on all IOM and IMM types.

         The earlier stages of the load balancing algorithm are controlled by
         tmnxL4LoadBalancing and tmnxLsrIpLoadBalancing (when applicable)."
    DEFVAL { standard }
    ::= { tmnxPortScalarObjs 3 }

tmnxMulticastEnhLoadBalancing    OBJECT-TYPE
    SYNTAX      TruthValue
    MAX-ACCESS  read-write
    STATUS      current
    DESCRIPTION
        "The value of tmnxMulticastEnhLoadBalancing specifies how the node
         distributes multicast traffic over LAG ports.

         The default value, 'false (1),' preserves the behaviour prior to
         the introduction of this object: multicast traffic hash uses internal
         system multicast identifiers.  This allows per multicast
         (S,G) channel (IP replication) or per LSP (MPLS replication) traffic
         distribution over LAG.

         The value of 'true (2)' introduces an enhanced multicast distribution
         over LAG: multicast traffic hash uses packet header information and
         configuration of other system-level hashing parameters like
         tmnxL4LoadBalancing, tmnxLsrIpLoadBalancing, or tmnxIpLoadBalancing.
         The functionality allows for a greater flexibility in defining how
         multicast is to be distributed over a LAG allowing, for example, per
         (S,G) channel distribution for both IP and MPLS replications."
    DEFVAL { false }
    ::= { tmnxPortScalarObjs 4 }

tmnxServiceIdLagHashing       OBJECT-TYPE
    SYNTAX      TruthValue
    MAX-ACCESS  read-write
    STATUS      current
    DESCRIPTION
        "The value of tmnxServiceIdLagHashing specifies how the node
         distributes LAG link traffic in a VLL service when both ECMP and
         LAG load balancing are performed.

         The default value, 'false (1),' preserves the behaviour prior to the
         introduction of this object: the ingress IOM will select one ECMP
         interface and one LAG link for all packets on the VLL service based on
         a modulo of the service ID.

         The value of 'true (2)' introduces an enhanced distribution which
         hashes the service-id prior to the LAG link modulo operation.

         The default value, 'false (1),' preserves the behaviour prior to the
         introduction of this object: the ingress IOM will select one ECMP
         interface and one LAG link for all packets on the VLL service based on
         a modulo of the service ID.

         The value of 'true (2)' introduces an enhanced distribution for VLL
         services."
    DEFVAL { false }
    ::= { tmnxPortScalarObjs 5 }
--
-- DS1 Port table
--
tmnxDS1PortTable OBJECT-TYPE
    SYNTAX      SEQUENCE OF TmnxDS1PortEntry
    MAX-ACCESS  not-accessible
    STATUS      current
    DESCRIPTION
        "The tmnxDS1PortTable has an entry for a DS1 physical port."
    ::= { tmnxPortObjs 23 }

tmnxDS1PortEntry       OBJECT-TYPE
    SYNTAX      TmnxDS1PortEntry
    MAX-ACCESS  not-accessible
    STATUS      current
    DESCRIPTION
        "Each row entry represents a physical DS1 port on a
         IOM card in a chassis in the system.  Entries cannot be created
         and deleted via SNMP SET operations.  Entries in this table will
         be created automatically when the tmnxMDAAssignedType object is
         set to the DS1 MDA type The tmnxDS1PortEntry contains attributes
         that are unique to the 'ds1e1' TmnxPortType. The tmnxPortPortID
         contains the slot, mda and port numbers encoded into it.

         For each tmnxDS1PortEntry, there will be a corresponding entry
         in the tmnxPortTable and the ifTable."
    INDEX       { tmnxChassisIndex, tmnxPortPortID }
    ::= { tmnxDS1PortTable 1 }

TmnxDS1PortEntry ::=
    SEQUENCE {
        tmnxDS1PortBuildout             INTEGER,
        tmnxDS1PortLastChangeTime       TimeStamp,
        tmnxDS1PortType                 INTEGER,
        tmnxDS1PortLineLength           INTEGER,
        tmnxDS1PortLbo                  INTEGER,
        tmnxDS1PortDbGain               Integer32
    }

tmnxDS1PortBuildout       OBJECT-TYPE
    SYNTAX      INTEGER {
                    short (1),
                    long  (2)
                }
    MAX-ACCESS  read-create
    STATUS      current
    DESCRIPTION
        "tmnxDS1PortBuildout configures the cable buildout length.  A ds1 port
         has two settings for the DS1 cable buildout: a 'short' setting, for
         cable lengths of less than or equal to 655 feet, and a 'long' setting
         for cable lengths of greater than 655 feet.
         This object applies to copper-cable-based DS1 ports only."
    DEFVAL      { short }
    ::= { tmnxDS1PortEntry 1 }

tmnxDS1PortLastChangeTime OBJECT-TYPE
    SYNTAX      TimeStamp
    MAX-ACCESS  read-only
    STATUS      current
    DESCRIPTION
        "The tmnxDS1PortLastChangeTime variable contains the sysUpTime
         value of the most recently modified writable variable in the
         tmnxDS1PortEntry row for this port."
    ::= { tmnxDS1PortEntry 2 }

tmnxDS1PortType           OBJECT-TYPE
    SYNTAX      INTEGER {
                    ds1(1),
                    e1 (2),
                    j1 (3)
                }
    MAX-ACCESS  read-create
    STATUS      current
    DESCRIPTION
        "tmnxDS1PortType configures the type of the physical port to 'ds1',
         'e1' or 'j1'."
    DEFVAL      { ds1 }
    ::= { tmnxDS1PortEntry 3 }

tmnxDS1PortLineLength           OBJECT-TYPE
    SYNTAX      INTEGER {
                    lengthNotApplicable (1),
                    length0To133        (2),
                    length134To266      (3),
                    length267To399      (4),
                    length400To533      (5),
                    length534To655      (6)
                }
    MAX-ACCESS  read-create
    STATUS      current
    DESCRIPTION
        "tmnxDS1PortLineLength configuration only applies to a ds1 port
         configured with a 'short' buildout.  tmnxDS1PortLineLength configures
         the length of the line (in feet).  For line lengths longer than 655
         feet configure the ds1 port buildout as 'long'.
         For 'long' buildout the following values are valid:
             lengthNotApplicable - Not applicable
         For 'short' buildout the following values are valid:
             length0To133        - For line length from 0 to 133 feet
             length134To266      - For line length from 134 to 266 feet
             length267To399      - For line length from 267 to 399 feet
             length400To533      - For line length from 400 to 533 feet
             length534To655      - For line length from 534 to 655 feet
         The default for 'long' buildout is 'lengthNotApplicable' while the
         default for 'short' buildout is 'length0To133'."
    ::= { tmnxDS1PortEntry 4 }

tmnxDS1PortLbo       OBJECT-TYPE
    SYNTAX      INTEGER {
                    lboNotApplicable (1),
                    lbo0dB           (2),
                    lboNeg7p5dB      (3),
                    lboNeg15p0dB     (4),
                    lboNeg22p5dB     (5)
                }
    MAX-ACCESS  read-create
    STATUS      current
    DESCRIPTION
        "tmnxDS1PortLbo configuration only applies to a ds1 port
         configured with a 'long' buildout.  tmnxDS1PortLbo configures the
         number of decibels(dB) the transmission signal decreases over the line.
         For 'short' buildout the following values are valid:
             lboNotApplicable - Not applicable
         For 'long' buildout the following values are valid:
             lbo0dB           - For 0 dB
             lboNeg7p5dB      - For -7.5 dB
             lboNeg15p0dB     - For -15.0 dB
             lboNeg22p5dB     - For -22.5 dB
         The default for 'short' build out is 'lboNotApplicable' while the
         default for 'long' buildout is 'lbo0dB'"
    ::= { tmnxDS1PortEntry 5 }

tmnxDS1PortDbGain       OBJECT-TYPE
    SYNTAX      Integer32
    UNITS       "db"
    MAX-ACCESS  read-only
    STATUS      current
    DESCRIPTION
        "tmnxDS1PortDbGain only applies to a ds1 port configured with a
         'long' buildout.  tmnxDS1PortDbGain shows the number of decibels
         the received signal is increased to compensate for loss."
    ::= { tmnxDS1PortEntry 6 }

--
--      Port scheduler policy overrides
--

tmnxPortSchedOverrideTable OBJECT-TYPE
    SYNTAX      SEQUENCE OF TmnxPortSchedOverrideEntry
    MAX-ACCESS  not-accessible
    STATUS      current
    DESCRIPTION
        "The tmnxPortSchedOverrideTable has an entry for each port
         scheduler override configured on this system."
    ::= { tmnxPortObjs 24 }

tmnxPortSchedOverrideEntry    OBJECT-TYPE
    SYNTAX      TmnxPortSchedOverrideEntry
    MAX-ACCESS  not-accessible
    STATUS      current
    DESCRIPTION
        "Each row represents a particular port-scheduler override. Entries
         are created and deleted by the user."
    INDEX { tmnxChassisIndex, tmnxPortPortID }
    ::= { tmnxPortSchedOverrideTable 1}

TmnxPortSchedOverrideEntry ::= SEQUENCE
    {
        tmnxPortSchedOverrideRowStatus          RowStatus,
        tmnxPortSchedOverrideSchedName          DisplayString,
        tmnxPortSchedOverrideLastChanged        TimeStamp,
        tmnxPortSchedOverrideMaxRate            TPortSchedulerPIRRate,
        tmnxPortSchedOverrideLvl1PIR            TPortSchedulerPIRRate,
        tmnxPortSchedOverrideLvl1CIR            TPortSchedulerCIR,
        tmnxPortSchedOverrideLvl2PIR            TPortSchedulerPIRRate,
        tmnxPortSchedOverrideLvl2CIR            TPortSchedulerCIR,
        tmnxPortSchedOverrideLvl3PIR            TPortSchedulerPIRRate,
        tmnxPortSchedOverrideLvl3CIR            TPortSchedulerCIR,
        tmnxPortSchedOverrideLvl4PIR            TPortSchedulerPIRRate,
        tmnxPortSchedOverrideLvl4CIR            TPortSchedulerCIR,
        tmnxPortSchedOverrideLvl5PIR            TPortSchedulerPIRRate,
        tmnxPortSchedOverrideLvl5CIR            TPortSchedulerCIR,
        tmnxPortSchedOverrideLvl6PIR            TPortSchedulerPIRRate,
        tmnxPortSchedOverrideLvl6CIR            TPortSchedulerCIR,
        tmnxPortSchedOverrideLvl7PIR            TPortSchedulerPIRRate,
        tmnxPortSchedOverrideLvl7CIR            TPortSchedulerCIR,
        tmnxPortSchedOverrideLvl8PIR            TPortSchedulerPIRRate,
        tmnxPortSchedOverrideLvl8CIR            TPortSchedulerCIR,
        tmnxPortSchedOverrideFlags              BITS,
        tmnxPortSchedOvrMaxRatePercent          Unsigned32,
        tmnxPortSchedOvrLvl1PIRPercent          Unsigned32,
        tmnxPortSchedOvrLvl1CIRPercent          Unsigned32,
        tmnxPortSchedOvrLvl2PIRPercent          Unsigned32,
        tmnxPortSchedOvrLvl2CIRPercent          Unsigned32,
        tmnxPortSchedOvrLvl3PIRPercent          Unsigned32,
        tmnxPortSchedOvrLvl3CIRPercent          Unsigned32,
        tmnxPortSchedOvrLvl4PIRPercent          Unsigned32,
        tmnxPortSchedOvrLvl4CIRPercent          Unsigned32,
        tmnxPortSchedOvrLvl5PIRPercent          Unsigned32,
        tmnxPortSchedOvrLvl5CIRPercent          Unsigned32,
        tmnxPortSchedOvrLvl6PIRPercent          Unsigned32,
        tmnxPortSchedOvrLvl6CIRPercent          Unsigned32,
        tmnxPortSchedOvrLvl7PIRPercent          Unsigned32,
        tmnxPortSchedOvrLvl7CIRPercent          Unsigned32,
        tmnxPortSchedOvrLvl8PIRPercent          Unsigned32,
        tmnxPortSchedOvrLvl8CIRPercent          Unsigned32
    }

tmnxPortSchedOverrideRowStatus        OBJECT-TYPE
    SYNTAX      RowStatus
    MAX-ACCESS  read-create
    STATUS      current
    DESCRIPTION
        "The value of tmnxPortSchedOverrideRowStatus is used for the
         creation and deletion of port-scheduler overrides. When
         tmnxPortEgrPortSchedPlcy of the tmnxPortEntry indexed by the
         same indices of this table is an empty string, creation
         will fail."
    ::= { tmnxPortSchedOverrideEntry 1 }

tmnxPortSchedOverrideSchedName        OBJECT-TYPE
    SYNTAX      DisplayString
    MAX-ACCESS  read-only
    STATUS      current
    DESCRIPTION
        "The value of tmnxPortSchedOverrideSchedName indicates the name
         of the port scheduler policy that this row entry overrides."
    ::= { tmnxPortSchedOverrideEntry 2 }

tmnxPortSchedOverrideLastChanged        OBJECT-TYPE
    SYNTAX      TimeStamp
    MAX-ACCESS  read-only
    STATUS      current
    DESCRIPTION
        "The value of tmnxPortSchedOverrideLastChanged indicates the value
         of sysUpTime at the time of the most recent management change to
         this row."
    ::= { tmnxPortSchedOverrideEntry 3 }

tmnxPortSchedOverrideMaxRate        OBJECT-TYPE
    SYNTAX      TPortSchedulerPIRRate
    UNITS       "kbps"
    MAX-ACCESS  read-create
    STATUS      current
    DESCRIPTION
        "The value of tmnxPortSchedOverrideMaxRate specifies the explicit
         maximum frame based bandwidth limit. This object overrides
         TIMETRA-QOS-MIB::tPortSchedulerPlcyMaxRate."
    DEFVAL      { -1 }
    ::= { tmnxPortSchedOverrideEntry 4 }

tmnxPortSchedOverrideLvl1PIR        OBJECT-TYPE
    SYNTAX      TPortSchedulerPIRRate
    UNITS       "kbps"
    MAX-ACCESS  read-create
    STATUS      current
    DESCRIPTION
        "The value of tmnxPortSchedOverrideLvl1PIR specifies the total
         bandwidth limit, PIR, for priority level 1. This object
         overrides TIMETRA-QOS-MIB::tPortSchedulerPlcyLvl1PIR."
    DEFVAL      { -1 }
    ::= { tmnxPortSchedOverrideEntry 5 }

tmnxPortSchedOverrideLvl1CIR        OBJECT-TYPE
    SYNTAX      TPortSchedulerCIR
    UNITS       "kbps"
    MAX-ACCESS  read-create
    STATUS      current
    DESCRIPTION
        "The value of tmnxPortSchedOverrideLvl1CIR specifies the within-cir
         bandwidth limit for priority level 1. This object overrides
         TIMETRA-QOS-MIB::tPortSchedulerPlcyLvl1CIR."
    DEFVAL      { -1 }
    ::= { tmnxPortSchedOverrideEntry 6 }

tmnxPortSchedOverrideLvl2PIR        OBJECT-TYPE
    SYNTAX      TPortSchedulerPIRRate
    UNITS       "kbps"
    MAX-ACCESS  read-create
    STATUS      current
    DESCRIPTION
        "The value of tmnxPortSchedOverrideLvl2PIR specifies the total
         bandwidth limit, PIR, for priority level 2. This object
         overrides TIMETRA-QOS-MIB::tPortSchedulerPlcyLvl2PIR."
    DEFVAL      { -1 }
    ::= { tmnxPortSchedOverrideEntry 7 }

tmnxPortSchedOverrideLvl2CIR        OBJECT-TYPE
    SYNTAX      TPortSchedulerCIR
    UNITS       "kbps"
    MAX-ACCESS  read-create
    STATUS      current
    DESCRIPTION
        "The value of tmnxPortSchedOverrideLvl2CIR specifies the within-cir
         bandwidth limit for priority level 2. This object overrides
         TIMETRA-QOS-MIB::tPortSchedulerPlcyLvl2CIR."
    DEFVAL      { -1 }
    ::= { tmnxPortSchedOverrideEntry 8 }

tmnxPortSchedOverrideLvl3PIR        OBJECT-TYPE
    SYNTAX      TPortSchedulerPIRRate
    UNITS       "kbps"
    MAX-ACCESS  read-create
    STATUS      current
    DESCRIPTION
        "The value of tmnxPortSchedOverrideLvl3PIR specifies the total
         bandwidth limit, PIR, for priority level 3. This object
         overrides TIMETRA-QOS-MIB::tPortSchedulerPlcyLvl3PIR."
    DEFVAL      { -1 }
    ::= { tmnxPortSchedOverrideEntry 9 }

tmnxPortSchedOverrideLvl3CIR        OBJECT-TYPE
    SYNTAX      TPortSchedulerCIR
    UNITS       "kbps"
    MAX-ACCESS  read-create
    STATUS      current
    DESCRIPTION
        "The value of tmnxPortSchedOverrideLvl3CIR specifies the within-cir
         bandwidth limit for priority level 3. This object overrides
         TIMETRA-QOS-MIB::tPortSchedulerPlcyLvl3CIR."
    DEFVAL      { -1 }
    ::= { tmnxPortSchedOverrideEntry 10 }

tmnxPortSchedOverrideLvl4PIR        OBJECT-TYPE
    SYNTAX      TPortSchedulerPIRRate
    UNITS       "kbps"
    MAX-ACCESS  read-create
    STATUS      current
    DESCRIPTION
        "The value of tmnxPortSchedOverrideLvl4PIR specifies the total
         bandwidth limit, PIR, for priority level 4. This object
         overrides TIMETRA-QOS-MIB::tPortSchedulerPlcyLvl4PIR."
    DEFVAL      { -1 }
    ::= { tmnxPortSchedOverrideEntry 11 }

tmnxPortSchedOverrideLvl4CIR        OBJECT-TYPE
    SYNTAX      TPortSchedulerCIR
    UNITS       "kbps"
    MAX-ACCESS  read-create
    STATUS      current
    DESCRIPTION
        "The value of tmnxPortSchedOverrideLvl4CIR specifies the within-cir
         bandwidth limit for priority level 4. This object overrides
         TIMETRA-QOS-MIB::tPortSchedulerPlcyLvl4CIR."
    DEFVAL      { -1 }
    ::= { tmnxPortSchedOverrideEntry 12 }

tmnxPortSchedOverrideLvl5PIR        OBJECT-TYPE
    SYNTAX      TPortSchedulerPIRRate
    UNITS       "kbps"
    MAX-ACCESS  read-create
    STATUS      current
    DESCRIPTION
        "The value of tmnxPortSchedOverrideLvl5PIR specifies the total
         bandwidth limit, PIR, for priority level 5. This object
         overrides TIMETRA-QOS-MIB::tPortSchedulerPlcyLvl5PIR."
    DEFVAL      { -1 }
    ::= { tmnxPortSchedOverrideEntry 13 }

tmnxPortSchedOverrideLvl5CIR        OBJECT-TYPE
    SYNTAX      TPortSchedulerCIR
    UNITS       "kbps"
    MAX-ACCESS  read-create
    STATUS      current
    DESCRIPTION
        "The value of tmnxPortSchedOverrideLvl5CIR specifies the within-cir
         bandwidth limit for priority level 5. This object overrides
         TIMETRA-QOS-MIB::tPortSchedulerPlcyLvl5CIR."
    DEFVAL      { -1 }
    ::= { tmnxPortSchedOverrideEntry 14 }

tmnxPortSchedOverrideLvl6PIR        OBJECT-TYPE
    SYNTAX      TPortSchedulerPIRRate
    UNITS       "kbps"
    MAX-ACCESS  read-create
    STATUS      current
    DESCRIPTION
        "The value of tmnxPortSchedOverrideLvl6PIR specifies the total
         bandwidth limit, PIR, for priority level 6. This object
         overrides TIMETRA-QOS-MIB::tPortSchedulerPlcyLvl6PIR."
    DEFVAL      { -1 }
    ::= { tmnxPortSchedOverrideEntry 15 }

tmnxPortSchedOverrideLvl6CIR        OBJECT-TYPE
    SYNTAX      TPortSchedulerCIR
    UNITS       "kbps"
    MAX-ACCESS  read-create
    STATUS      current
    DESCRIPTION
        "The value of tmnxPortSchedOverrideLvl6CIR specifies the within-cir
         bandwidth limit for priority level 6. This object overrides
         TIMETRA-QOS-MIB::tPortSchedulerPlcyLvl6CIR."
    DEFVAL      { -1 }
    ::= { tmnxPortSchedOverrideEntry 16 }

tmnxPortSchedOverrideLvl7PIR        OBJECT-TYPE
    SYNTAX      TPortSchedulerPIRRate
    UNITS       "kbps"
    MAX-ACCESS  read-create
    STATUS      current
    DESCRIPTION
        "The value of tmnxPortSchedOverrideLvl7PIR specifies the total
         bandwidth limit, PIR, for priority level 7. This object
         overrides TIMETRA-QOS-MIB::tPortSchedulerPlcyLvl7PIR."
    DEFVAL      { -1 }
    ::= { tmnxPortSchedOverrideEntry 17 }

tmnxPortSchedOverrideLvl7CIR        OBJECT-TYPE
    SYNTAX      TPortSchedulerCIR
    UNITS       "kbps"
    MAX-ACCESS  read-create
    STATUS      current
    DESCRIPTION
        "The value of tmnxPortSchedOverrideLvl7CIR specifies the within-cir
         bandwidth limit for priority level 7. This object overrides
         TIMETRA-QOS-MIB::tPortSchedulerPlcyLvl7CIR."
    DEFVAL      { -1 }
    ::= { tmnxPortSchedOverrideEntry 18 }

tmnxPortSchedOverrideLvl8PIR        OBJECT-TYPE
    SYNTAX      TPortSchedulerPIRRate
    UNITS       "kbps"
    MAX-ACCESS  read-create
    STATUS      current
    DESCRIPTION
        "The value of tmnxPortSchedOverrideLvl8PIR specifies the total
         bandwidth limit, PIR, for priority level 8. This object
         overrides TIMETRA-QOS-MIB::tPortSchedulerPlcyLvl8PIR."
    DEFVAL      { -1 }
    ::= { tmnxPortSchedOverrideEntry 19 }

tmnxPortSchedOverrideLvl8CIR        OBJECT-TYPE
    SYNTAX      TPortSchedulerCIR
    UNITS       "kbps"
    MAX-ACCESS  read-create
    STATUS      current
    DESCRIPTION
        "The value of tmnxPortSchedOverrideLvl8CIR specifies the within-cir
         bandwidth limit for priority level 8. This object overrides
         TIMETRA-QOS-MIB::tPortSchedulerPlcyLvl8CIR."
    DEFVAL      { -1 }
    ::= { tmnxPortSchedOverrideEntry 20 }

tmnxPortSchedOverrideFlags        OBJECT-TYPE
    SYNTAX      BITS {
                    maxRate            (0),
                    lvl1PIR            (1),
                    lvl1CIR            (2),
                    lvl2PIR            (3),
                    lvl2CIR            (4),
                    lvl3PIR            (5),
                    lvl3CIR            (6),
                    lvl4PIR            (7),
                    lvl4CIR            (8),
                    lvl5PIR            (9),
                    lvl5CIR            (10),
                    lvl6PIR            (11),
                    lvl6CIR            (12),
                    lvl7PIR            (13),
                    lvl7CIR            (14),
                    lvl8PIR            (15),
                    lvl8CIR            (16),
                    maxRatePercent     (17),
                    lvl1PIRPercent     (18),
                    lvl1CIRPercent     (19),
                    lvl2PIRPercent     (20),
                    lvl2CIRPercent     (21),
                    lvl3PIRPercent     (22),
                    lvl3CIRPercent     (23),
                    lvl4PIRPercent     (24),
                    lvl4CIRPercent     (25),
                    lvl5PIRPercent     (26),
                    lvl5CIRPercent     (27),
                    lvl6PIRPercent     (28),
                    lvl6CIRPercent     (29),
                    lvl7PIRPercent     (30),
                    lvl7CIRPercent     (31),
                    lvl8PIRPercent     (32),
                    lvl8CIRPercent     (33)
                }
    MAX-ACCESS  read-create
    STATUS      current
    DESCRIPTION
        "The value of tmnxPortSchedOverrideFlags specifies the set of
         attributes whose values have been overridden via management
         on this port scheduler. Clearing a given flag will return the
         corresponding overridden attribute to the value defined in
         the port's port-scheduler policy."
    ::= { tmnxPortSchedOverrideEntry 21 }

tmnxPortSchedOvrMaxRatePercent    OBJECT-TYPE
    SYNTAX      Unsigned32 (1..10000)
    UNITS       "hundredths of a percent"
    MAX-ACCESS  read-create
    STATUS      current
    DESCRIPTION
        "The value of tmnxPortSchedOvrMaxRatePercent specifies the explicit
         maximum frame based bandwidth limit in percentage. This object
         overrides TIMETRA-QOS-MIB::tPortSchedPlcyMaxRatePercent."
    DEFVAL { 10000 }
    ::= { tmnxPortSchedOverrideEntry 22 }

tmnxPortSchedOvrLvl1PIRPercent   OBJECT-TYPE
    SYNTAX      Unsigned32 (1..10000)
    UNITS       "hundredths of a percent"
    MAX-ACCESS  read-create
    STATUS      current
    DESCRIPTION
        "The value of tmnxPortSchedOvrLvl1PIRPercent specifies the total
         bandwidth percentage, PIR percentage, for priority level 1. This object
         overrides TIMETRA-QOS-MIB::tPortSchedPlcyLvl1PIRPercent."
    DEFVAL { 10000 }
    ::= { tmnxPortSchedOverrideEntry 23 }

tmnxPortSchedOvrLvl1CIRPercent   OBJECT-TYPE
    SYNTAX      Unsigned32 (0..10000)
    UNITS       "hundredths of a percent"
    MAX-ACCESS  read-create
    STATUS      current
    DESCRIPTION
        "The value of tmnxPortSchedOvrLvl1CIRPercent specifies the within-cir
         bandwidth percentage for priority level 1. This object overrides
         TIMETRA-QOS-MIB::tPortSchedPlcyLvl1CIRPercent."
    DEFVAL { 10000 }
    ::= { tmnxPortSchedOverrideEntry 24 }

tmnxPortSchedOvrLvl2PIRPercent   OBJECT-TYPE
    SYNTAX      Unsigned32 (1..10000)
    UNITS       "hundredths of a percent"
    MAX-ACCESS  read-create
    STATUS      current
    DESCRIPTION
        "The value of tmnxPortSchedOvrLvl2PIRPercent specifies the total
         bandwidth percentage, PIR percentage, for priority level 2. This object
         overrides TIMETRA-QOS-MIB::tPortSchedPlcyLvl2PIRPercent."
    DEFVAL { 10000 }
    ::= { tmnxPortSchedOverrideEntry 25 }

tmnxPortSchedOvrLvl2CIRPercent   OBJECT-TYPE
    SYNTAX      Unsigned32 (0..10000)
    UNITS       "hundredths of a percent"
    MAX-ACCESS  read-create
    STATUS      current
    DESCRIPTION
        "The value of tmnxPortSchedOvrLvl2CIRPercent specifies the within-cir
         bandwidth percentage for priority level 2. This object overrides
         TIMETRA-QOS-MIB::tPortSchedPlcyLvl2CIRPercent."
    DEFVAL { 10000 }
    ::= { tmnxPortSchedOverrideEntry 26 }

tmnxPortSchedOvrLvl3PIRPercent   OBJECT-TYPE
    SYNTAX      Unsigned32 (1..10000)
    UNITS       "hundredths of a percent"
    MAX-ACCESS  read-create
    STATUS      current
    DESCRIPTION
        "The value of tmnxPortSchedOvrLvl3PIRPercent specifies the total
         bandwidth percentage, PIR percentage, for priority level 3. This object
         overrides TIMETRA-QOS-MIB::tPortSchedPlcyLvl3PIRPercent."
    DEFVAL { 10000 }
    ::= { tmnxPortSchedOverrideEntry 27 }

tmnxPortSchedOvrLvl3CIRPercent   OBJECT-TYPE
    SYNTAX      Unsigned32 (0..10000)
    UNITS       "hundredths of a percent"
    MAX-ACCESS  read-create
    STATUS      current
    DESCRIPTION
        "The value of tmnxPortSchedOvrLvl3CIRPercent specifies the within-cir
         bandwidth percentage for priority level 3. This object overrides
         TIMETRA-QOS-MIB::tPortSchedPlcyLvl3CIRPercent."
    DEFVAL { 10000 }
    ::= { tmnxPortSchedOverrideEntry 28 }

tmnxPortSchedOvrLvl4PIRPercent   OBJECT-TYPE
    SYNTAX      Unsigned32 (1..10000)
    UNITS       "hundredths of a percent"
    MAX-ACCESS  read-create
    STATUS      current
    DESCRIPTION
        "The value of tmnxPortSchedOvrLvl4PIRPercent specifies the total
         bandwidth percentage, PIR percentage, for priority level 4. This object
         overrides TIMETRA-QOS-MIB::tPortSchedPlcyLvl4PIRPercent."
    DEFVAL { 10000 }
    ::= { tmnxPortSchedOverrideEntry 29 }

tmnxPortSchedOvrLvl4CIRPercent   OBJECT-TYPE
    SYNTAX      Unsigned32 (0..10000)
    UNITS       "hundredths of a percent"
    MAX-ACCESS  read-create
    STATUS      current
    DESCRIPTION
        "The value of tmnxPortSchedOvrLvl4CIRPercent specifies the within-cir
         bandwidth percentage for priority level 4. This object overrides
         TIMETRA-QOS-MIB::tPortSchedPlcyLvl4CIRPercent."
    DEFVAL { 10000 }
    ::= { tmnxPortSchedOverrideEntry 30 }

tmnxPortSchedOvrLvl5PIRPercent   OBJECT-TYPE
    SYNTAX      Unsigned32 (1..10000)
    UNITS       "hundredths of a percent"
    MAX-ACCESS  read-create
    STATUS      current
    DESCRIPTION
        "The value of tmnxPortSchedOvrLvl5PIRPercent specifies the total
         bandwidth percentage, PIR percentage, for priority level 5. This object
         overrides TIMETRA-QOS-MIB::tPortSchedPlcyLvl5PIRPercent."
    DEFVAL { 10000 }
    ::= { tmnxPortSchedOverrideEntry 31 }

tmnxPortSchedOvrLvl5CIRPercent   OBJECT-TYPE
    SYNTAX      Unsigned32 (0..10000)
    UNITS       "hundredths of a percent"
    MAX-ACCESS  read-create
    STATUS      current
    DESCRIPTION
        "The value of tmnxPortSchedOvrLvl5CIRPercent specifies the within-cir
         bandwidth percentage for priority level 5. This object overrides
         TIMETRA-QOS-MIB::tPortSchedPlcyLvl5CIRPercent."
    DEFVAL { 10000 }
    ::= { tmnxPortSchedOverrideEntry 32 }

tmnxPortSchedOvrLvl6PIRPercent   OBJECT-TYPE
    SYNTAX      Unsigned32 (1..10000)
    UNITS       "hundredths of a percent"
    MAX-ACCESS  read-create
    STATUS      current
    DESCRIPTION
        "The value of tmnxPortSchedOvrLvl6PIRPercent specifies the total
         bandwidth percentage, PIR percentage, for priority level 6. This object
         overrides TIMETRA-QOS-MIB::tPortSchedPlcyLvl6PIRPercent."
    DEFVAL { 10000 }
    ::= { tmnxPortSchedOverrideEntry 33 }

tmnxPortSchedOvrLvl6CIRPercent   OBJECT-TYPE
    SYNTAX      Unsigned32 (0..10000)
    UNITS       "hundredths of a percent"
    MAX-ACCESS  read-create
    STATUS      current
    DESCRIPTION
        "The value of tmnxPortSchedOvrLvl6CIRPercent specifies the within-cir
         bandwidth percentage for priority level 6. This object overrides
         TIMETRA-QOS-MIB::tPortSchedPlcyLvl6CIRPercent."
    DEFVAL { 10000 }
    ::= { tmnxPortSchedOverrideEntry 34 }

tmnxPortSchedOvrLvl7PIRPercent   OBJECT-TYPE
    SYNTAX      Unsigned32 (1..10000)
    UNITS       "hundredths of a percent"
    MAX-ACCESS  read-create
    STATUS      current
    DESCRIPTION
        "The value of tmnxPortSchedOvrLvl7PIRPercent specifies the total
         bandwidth percentage, PIR percentage, for priority level 7. This object
         overrides TIMETRA-QOS-MIB::tPortSchedPlcyLvl7PIRPercent."
    DEFVAL { 10000 }
    ::= { tmnxPortSchedOverrideEntry 35 }

tmnxPortSchedOvrLvl7CIRPercent   OBJECT-TYPE
    SYNTAX      Unsigned32 (0..10000)
    UNITS       "hundredths of a percent"
    MAX-ACCESS  read-create
    STATUS      current
    DESCRIPTION
        "The value of tmnxPortSchedOvrLvl7CIRPercent specifies the within-cir
         bandwidth percentage for priority level 7. This object overrides
         TIMETRA-QOS-MIB::tPortSchedPlcyLvl7CIRPercent."
    DEFVAL { 10000 }
    ::= { tmnxPortSchedOverrideEntry 36 }

tmnxPortSchedOvrLvl8PIRPercent   OBJECT-TYPE
    SYNTAX      Unsigned32 (1..10000)
    UNITS       "hundredths of a percent"
    MAX-ACCESS  read-create
    STATUS      current
    DESCRIPTION
        "The value of tmnxPortSchedOvrLvl8PIRPercent specifies the total
         bandwidth percentage, PIR percentage, for priority level 8. This object
         overrides TIMETRA-QOS-MIB::tPortSchedPlcyLvl8PIRPercent."
    DEFVAL { 10000 }
    ::= { tmnxPortSchedOverrideEntry 37 }

tmnxPortSchedOvrLvl8CIRPercent   OBJECT-TYPE
    SYNTAX      Unsigned32 (0..10000)
    UNITS       "hundredths of a percent"
    MAX-ACCESS  read-create
    STATUS      current
    DESCRIPTION
        "The value of tmnxPortSchedOvrLvl8CIRPercent specifies the within-cir
         bandwidth percentage for priority level 8. This object overrides
         TIMETRA-QOS-MIB::tPortSchedPlcyLvl8CIRPercent."
    DEFVAL { 10000 }
    ::= { tmnxPortSchedOverrideEntry 38 }

--
-- Bundle Protection Group Association Table
--
tmnxBPGrpAssocTable   OBJECT-TYPE
    SYNTAX      SEQUENCE OF TmnxBPGrpAssocEntry
    MAX-ACCESS  not-accessible
    STATUS      current
    DESCRIPTION
        "The tmnxBPGrpAssocTable has an entry for each Bundle Protection Group
         created on the system."
    ::= { tmnxPortObjs 25 }

tmnxBPGrpAssocEntry       OBJECT-TYPE
    SYNTAX      TmnxBPGrpAssocEntry
    MAX-ACCESS  not-accessible
    STATUS      current
    DESCRIPTION
        "Each row displays the relationship between a Bundle Protection
         group and its working and protection bundle."
    INDEX       { tmnxChassisIndex, tmnxBundleBundleID }
    ::= { tmnxBPGrpAssocTable 1 }

TmnxBPGrpAssocEntry ::=
    SEQUENCE {
        tmnxBPGrpAssocWorkingBundleID  TmnxBundleID,
        tmnxBPGrpAssocProtectBundleID  TmnxBundleID,
        tmnxBPGrpAssocActiveBundleID   TmnxBundleID
    }

tmnxBPGrpAssocWorkingBundleID    OBJECT-TYPE
    SYNTAX      TmnxBundleID
    MAX-ACCESS  read-only
    STATUS      current
    DESCRIPTION
        "tmnxBPGrpAssocWorkingBundleID identifies the working bundle. A value
         of zero is given if no working bundle is associated with the given
         tmnxBundleBundleID."
    ::= { tmnxBPGrpAssocEntry 1 }

tmnxBPGrpAssocProtectBundleID    OBJECT-TYPE
    SYNTAX      TmnxBundleID
    MAX-ACCESS  read-only
    STATUS      current
    DESCRIPTION
        "tmnxBPGrpAssocProtectBundleID identifies the protection bundle. A value
         of zero is given if no protection bundle is associated with the given
         tmnxBundleBundleID."
    ::= { tmnxBPGrpAssocEntry 2 }

tmnxBPGrpAssocActiveBundleID    OBJECT-TYPE
    SYNTAX      TmnxBundleID
    MAX-ACCESS  read-only
    STATUS      current
    DESCRIPTION
        "tmnxBPGrpAssocActiveBundleID identifies the bundle that is considered
         the active bundle. This bundle contains the members that are part of
         the active aps port. A value of zero is given if no bundle is
         considered active."
    ::= { tmnxBPGrpAssocEntry 3 }

--
-- MLPPP Bundle Table
--
--  Sparse Dependent Extension of the tmnxBundleTable.
--
--  The same indexes are used for both the base table tmnxBundleTable,
--  and the sparse dependent table, tmnxBundleMlpppTable.
--
--  This in effect extends the tmnxBundleTable with additional columns.
--  Rows are created in the tmnxBundleMlpppTable only for those entries
--  in the tmnxBundleTable for a value of 'mlppp' for the bundle type.
--
--  Deletion of a row in the tmnxBundleTable results in the
--  same fate for the row in the tmnxBundleMlpppTable.
--
tmnxBundleMlpppTable OBJECT-TYPE
    SYNTAX      SEQUENCE OF TmnxBundleMlpppEntry
    MAX-ACCESS  not-accessible
    STATUS      current
    DESCRIPTION
        "The tmnxBundleMlpppTable contains MLPPP specific data."
    ::= { tmnxPortObjs 26 }

tmnxBundleMlpppEntry OBJECT-TYPE
    SYNTAX      TmnxBundleMlpppEntry
    MAX-ACCESS  not-accessible
    STATUS      current
    DESCRIPTION
        "Each row entry contains data on an MLPPP Bundle."
    INDEX       { tmnxChassisIndex, tmnxBundleBundleID }
    ::= { tmnxBundleMlpppTable 1 }

TmnxBundleMlpppEntry ::=
    SEQUENCE {
        tmnxBundleMlpppEndpointID         OCTET STRING,
        tmnxBundleMlpppEndpointIDClass    TmnxMlpppEndpointIdClass,
        tmnxBundleMlpppClassCount         INTEGER,
        tmnxBundleMlpppIngQoSProfId       TMlpppQoSProfileId,
        tmnxBundleMlpppEgrQoSProfId       TMlpppQoSProfileId,
        tmnxBundleMlpppMagicNumber        TmnxEnabledDisabled,
        tmnxBundleMlpppStatelessApsSwo    TmnxEnabledDisabled
    }

tmnxBundleMlpppEndpointID OBJECT-TYPE
    SYNTAX      OCTET STRING (SIZE (0..20))
    MAX-ACCESS  read-create
    STATUS      current
    DESCRIPTION
        "tmnxBundleMlpppEndpointID indentifies the Endpoint Discriminator
         identifier value within the specified tmnxBundleMlpppEndpointIDClass.
         The object tmnxPortAdminStatus must be set to 'outOfService' to
         change this value."
    ::= { tmnxBundleMlpppEntry 1 }

tmnxBundleMlpppEndpointIDClass OBJECT-TYPE
    SYNTAX      TmnxMlpppEndpointIdClass
    MAX-ACCESS  read-create
    STATUS      current
    DESCRIPTION
        "tmnxBundleMlpppEndpointIDClass specifies the Link Control
         Protocol Endpoint Descriminator Class field type of the
         tmnxBundleMlpppEndpointID. The object tmnxPortAdminStatus
         must be set to 'outOfService' to change this value.

                    Bundle                     DEFVAL
            Physical MLPPP Bundle           ieee802dot1GlobalMacAddress (3)
            MLPPP Bundle Protection Group   ipAddress (2)"
    ::= { tmnxBundleMlpppEntry 2 }

tmnxBundleMlpppClassCount OBJECT-TYPE
    SYNTAX      INTEGER (0..16)
    MAX-ACCESS  read-create
    STATUS      current
    DESCRIPTION
        "The value of tmnxBundleMlpppClassCount specifies
         whether Multiclass MLPPP is enabled on
         a bundle with a tmnxBundleType of 'mlppp' and when enabled what is the
         number of classes to be negotiated/supported over the MLPPP bundle.

         The value of 0 disables multiclass MLPPP including negotiation in
         the PPP protocol.
         All other values specify the number of classes to be supported
         on a given multiclass bundle and enable Multiclass MLPPP negotiation
         on that bundle.

         Non-zero values supported are platform/MDA specific.

         The value of tmnxBundleMlpppClassCount must be set to 0 and cannot be
         changed when LFI is enabled on the bundle (see tmnxBundleLFI object
         in tmnxBundleTable).

         The value of tmnxBundleMlpppClassCount may be modified only when
         tmnxBundleNumLinks is zero.

         To set the value of tmnxBundleMlpppClassCount to a value greater
         than 4, the long sequence format must be enabled on the bundle (see
         tmnxBundleShortSequence object in tmnxBundleTable).

         Changing the value of tmnxBundleMlpppClassCount resets the values of
         tmnxBundleMlpppIngQoSProfId and tmnxBundleMlpppEgrQoSProfId to their
         defaults"
    DEFVAL { 0 }
    ::= { tmnxBundleMlpppEntry 3 }

tmnxBundleMlpppIngQoSProfId OBJECT-TYPE
    SYNTAX      TMlpppQoSProfileId
    MAX-ACCESS  read-create
    STATUS      current
    DESCRIPTION
        "tmnxBundleMlpppIngQoSProfId specifies ingress QoS profile
         to be used for the incoming traffic over this MLPPP
         bundle.

         The value of tmnxBundleMlpppIngQoSProfId may be modified only
         when the value of tmnxBundleNumLinks is 0.

         The value of tmnxBundleMlpppIngQoSProfId of 0 indicates
         a default QoS profile is used as applicable to a given hardware
         and the configured value of tmnxBundleMlpppClassCount."
    DEFVAL { 0 }
    ::= { tmnxBundleMlpppEntry 4 }

tmnxBundleMlpppEgrQoSProfId OBJECT-TYPE
    SYNTAX      TMlpppQoSProfileId
    MAX-ACCESS  read-create
    STATUS      current
    DESCRIPTION
        "tmnxBundleMlpppEgrQoSProfId specifies egress QoS profile
         to be used for the outgoing traffic over this MLPPP
         bundle.

         The value of tmnxBundleMlpppEgrQoSProfId may be modified only
         when tmnxBundleNumLinks is zero.

         The value of tmnxBundleMlpppEgrQoSProfId of 0 indicates
         a default profile is used as applicable to a given hardware
         and the configured value of tmnxBundleMlpppClassCount."
    DEFVAL { 0 }
    ::= { tmnxBundleMlpppEntry 5 }

tmnxBundleMlpppMagicNumber OBJECT-TYPE
    SYNTAX      TmnxEnabledDisabled
    MAX-ACCESS  read-create
    STATUS      current
    DESCRIPTION
        "tmnxBundleMlpppMagicNumber specifies whether or not the bundle will
         detect a loopback scenario on member links and take a looped back
         member links out of service.
         A value of 'enabled (1)' will detect loopbacks."
    DEFVAL { disabled }
    ::= { tmnxBundleMlpppEntry 6 }

tmnxBundleMlpppStatelessApsSwo OBJECT-TYPE
    SYNTAX      TmnxEnabledDisabled
    MAX-ACCESS  read-create
    STATUS      current
    DESCRIPTION
        "tmnxBundleMlpppStatelessApsSwo specifies whether the bundle will
         perform a statefull or a stateless APS switchover.

         The value of tmnxBundleMlpppStatelessApsSwo must be set to 'disabled (2)' and
         cannot be changed for normal mlppp bundles.

         The value of tmnxBundleMlpppStatelessApsSwo may be changed
         for APS bundle protection groups.

         A stateless switchover implies that PPP is renegotiated on  each member
         link after the switchover. PPP negotiations may take a few seconds
         to complete.

         A statefull switchover implies that after an APS switchover the PPP
         state of the bundle will be restored based on the bpgrp bundle state
         before the switchover.

         A value of 'enabled (1)' will configure stateless APS switchovers."
    DEFVAL { disabled }
    ::= { tmnxBundleMlpppEntry 7 }

--
--      HSMDA scheduler policy overrides
--

tmnxHsmdaPortSchOvrTblLastChngd OBJECT-TYPE
    SYNTAX      TimeStamp
    MAX-ACCESS  read-only
    STATUS      current
    DESCRIPTION
        "The value of tmnxHsmdaPortSchOvrTblLastChngd indicates the sysUpTime
         at the time of the last modification of tmnxHsmdaPortSchOvrTable.

         If no changes were made to the table since the last
         re-initialization of the local network management subsystem,
         then this object contains a zero value."
    ::= { tmnxPortObjs 27 }

tmnxHsmdaPortSchOvrTable OBJECT-TYPE
    SYNTAX      SEQUENCE OF TmnxHsmdaPortSchedOverEntry
    MAX-ACCESS  not-accessible
    STATUS      current
    DESCRIPTION
        "The tmnxHsmdaPortSchOvrTable has an entry for each port-level HSMDA
         scheduler override configured on this system."
    ::= { tmnxPortObjs 28 }

tmnxHsmdaPortSchOvrEntry    OBJECT-TYPE
    SYNTAX      TmnxHsmdaPortSchedOverEntry
    MAX-ACCESS  not-accessible
    STATUS      current
    DESCRIPTION
        "Each row represents a particular port-level HSMDA scheduler override.
         Entries are created and deleted by the user."
    INDEX { tmnxChassisIndex, tmnxPortPortID }
    ::= { tmnxHsmdaPortSchOvrTable 1}

TmnxHsmdaPortSchedOverEntry ::= SEQUENCE
    {
        tmnxHsmdaPortSchOvrRowStatus          RowStatus,
        tmnxHsmdaPortSchOvrLastChanged        TimeStamp,
        tmnxHsmdaPortSchOvrMaxRate            THsmdaPIRMRateOverride,
        tmnxHsmdaPortSchOvrGrp1Rate           THsmdaPIRMRateOverride,
        tmnxHsmdaPortSchOvrGrp2Rate           THsmdaPIRMRateOverride,
        tmnxHsmdaPortSchOvrClass1Rate         THsmdaPIRMRateOverride,
        tmnxHsmdaPortSchOvrClass1WtInGp     THsmdaWeightOverride,
        tmnxHsmdaPortSchOvrClass2Rate         THsmdaPIRMRateOverride,
        tmnxHsmdaPortSchOvrClass2WtInGp     THsmdaWeightOverride,
        tmnxHsmdaPortSchOvrClass3Rate         THsmdaPIRMRateOverride,
        tmnxHsmdaPortSchOvrClass3WtInGp     THsmdaWeightOverride,
        tmnxHsmdaPortSchOvrClass4Rate         THsmdaPIRMRateOverride,
        tmnxHsmdaPortSchOvrClass4WtInGp     THsmdaWeightOverride,
        tmnxHsmdaPortSchOvrClass5Rate         THsmdaPIRMRateOverride,
        tmnxHsmdaPortSchOvrClass5WtInGp     THsmdaWeightOverride,
        tmnxHsmdaPortSchOvrClass6Rate         THsmdaPIRMRateOverride,
        tmnxHsmdaPortSchOvrClass6WtInGp     THsmdaWeightOverride,
        tmnxHsmdaPortSchOvrClass7Rate         THsmdaPIRMRateOverride,
        tmnxHsmdaPortSchOvrClass7WtInGp     THsmdaWeightOverride,
        tmnxHsmdaPortSchOvrClass8Rate         THsmdaPIRMRateOverride,
        tmnxHsmdaPortSchOvrClass8WtInGp     THsmdaWeightOverride
    }

tmnxHsmdaPortSchOvrRowStatus        OBJECT-TYPE
    SYNTAX      RowStatus
    MAX-ACCESS  read-create
    STATUS      current
    DESCRIPTION
        "The value of tmnxHsmdaPortSchOvrRowStatus is used for the
         creation and deletion of port-level HSMDA scheduler overrides.

         When the tmnxMDAAssignedType of the tmnxPortEntry indexed
         by the same indices of this table is a non-HSMDA MDA Type,
         creation will fail and return a 'noCreation' error."
    ::= { tmnxHsmdaPortSchOvrEntry 1 }

tmnxHsmdaPortSchOvrLastChanged        OBJECT-TYPE
    SYNTAX      TimeStamp
    MAX-ACCESS  read-only
    STATUS      current
    DESCRIPTION
        "The value of tmnxHsmdaPortSchOvrLastChanged indicates the sysUpTime
         at the time of the last modification of this entry.

         If no changes were made to the entry since the last
         re-initialization of the local network management subsystem,
         then this object contains a zero value."
    ::= { tmnxHsmdaPortSchOvrEntry 2 }

tmnxHsmdaPortSchOvrMaxRate        OBJECT-TYPE
    SYNTAX      THsmdaPIRMRateOverride
    UNITS       "Mbps"
    MAX-ACCESS  read-create
    STATUS      current
    DESCRIPTION
        "The value of tmnxHsmdaPortSchOvrMaxRate specifies the explicit
         maximum frame based bandwidth limit for this HSMDA port
         scheduler.

         A value of -2 indicates no override.

         This object overrides TIMETRA-QOS-MIB::tHsmdaSchedulerPlcyMaxRate."
    DEFVAL      { -2 }
    ::= { tmnxHsmdaPortSchOvrEntry 3 }

tmnxHsmdaPortSchOvrGrp1Rate          OBJECT-TYPE
    SYNTAX      THsmdaPIRMRateOverride
    UNITS       "Mbps"
    MAX-ACCESS  read-create
    STATUS      current
    DESCRIPTION
        "The value of tmnxHsmdaPortSchOvrGrp1Rate specifies the explicit
         maximum frame based bandwidth limit, in megabits per second, for
         group 1 for this HSMDA port scheduler.

         A value of -2 indicates no override.

         This object overrides TIMETRA-QOS-MIB::tHsmdaSchedulerPlcyGrp1Rate."
    DEFVAL { -2 }
    ::= { tmnxHsmdaPortSchOvrEntry 4 }

tmnxHsmdaPortSchOvrGrp2Rate           OBJECT-TYPE
    SYNTAX      THsmdaPIRMRateOverride
    UNITS       "Mbps"
    MAX-ACCESS  read-create
    STATUS      current
    DESCRIPTION
        "The value of tmnxHsmdaPortSchOvrGrp2Rate specifies the explicit
         maximum frame based bandwidth limit, in megabits per second, for
         group 2 for this HSMDA port scheduler.

         A value of -2 indicates no override.

         This object overrides TIMETRA-QOS-MIB::tHsmdaSchedulerPlcyGrp2Rate."
    DEFVAL { -2 }
    ::= { tmnxHsmdaPortSchOvrEntry 5 }

tmnxHsmdaPortSchOvrClass1Rate        OBJECT-TYPE
    SYNTAX      THsmdaPIRMRateOverride
    UNITS       "Mbps"
    MAX-ACCESS  read-create
    STATUS      current
    DESCRIPTION
        "The value of tmnxHsmdaPortSchOvrClass1Rate specifies the explicit
         maximum frame based bandwidth limit, in megabits per second, for
         this HSMDA port scheduler policy level.

         A value of -2 indicates no override.

         This object overrides TIMETRA-QOS-MIB::tHsmdaSchedulerPlcyLvl1Rate."
    DEFVAL { -2 }
    ::= { tmnxHsmdaPortSchOvrEntry 6 }

tmnxHsmdaPortSchOvrClass1WtInGp        OBJECT-TYPE
    SYNTAX      THsmdaWeightOverride
    MAX-ACCESS  read-create
    STATUS      current
    DESCRIPTION
        "The value of tmnxHsmdaPortSchOvrClass1WtInGp specifies the weight
         the HSMDA port scheduler policy should apply to this policy level
         within the group it belongs to.

         The value of tmnxHsmdaPortSchOvrClass1WtInGp will only be
         used if this policy level has been assigned to a group
         by setting tHsmdaSchedulerPlcyLvl1GrpId to a non-zero value.

         A value of -2 indicates no override.

         This object overrides
         TIMETRA-QOS-MIB::tHsmdaSchedulerPlcyLvl1WgtInGrp."
    DEFVAL { -2 }
    ::= { tmnxHsmdaPortSchOvrEntry 7 }

tmnxHsmdaPortSchOvrClass2Rate        OBJECT-TYPE
    SYNTAX      THsmdaPIRMRateOverride
    UNITS       "Mbps"
    MAX-ACCESS  read-create
    STATUS      current
    DESCRIPTION
        "The value of tmnxHsmdaPortSchOvrClass2Rate specifies the explicit
         maximum frame based bandwidth limit, in megabits per second, for
         this HSMDA port scheduler policy level.

         A value of -2 indicates no override.

         This object overrides TIMETRA-QOS-MIB::tHsmdaSchedulerPlcyLvl2Rate."
    DEFVAL { -2 }
    ::= { tmnxHsmdaPortSchOvrEntry 8 }

tmnxHsmdaPortSchOvrClass2WtInGp        OBJECT-TYPE
    SYNTAX      THsmdaWeightOverride
    MAX-ACCESS  read-create
    STATUS      current
    DESCRIPTION
        "The value of tmnxHsmdaPortSchOvrClass2WtInGp specifies the weight
         the HSMDA port scheduler policy should apply to this policy level
         within the group it belongs to.

         The value of tmnxHsmdaPortSchOvrClass2WtInGp will only be
         used if this policy level has been assigned to a group
         by setting tHsmdaSchedulerPlcyLvl2GrpId to a non-zero value.

         A value of -2 indicates no override.

         This object overrides
         TIMETRA-QOS-MIB::tHsmdaSchedulerPlcyLvl2WgtInGrp."
    DEFVAL { -2 }
    ::= { tmnxHsmdaPortSchOvrEntry 9 }

tmnxHsmdaPortSchOvrClass3Rate        OBJECT-TYPE
    SYNTAX      THsmdaPIRMRateOverride
    UNITS       "Mbps"
    MAX-ACCESS  read-create
    STATUS      current
    DESCRIPTION
        "The value of tmnxHsmdaPortSchOvrClass3Rate specifies the explicit
         maximum frame based bandwidth limit, in megabits per second, for
         this HSMDA port scheduler policy level.

         A value of -2 indicates no override.

         This object overrides TIMETRA-QOS-MIB::tHsmdaSchedulerPlcyLvl3Rate."
    DEFVAL { -2 }
    ::= { tmnxHsmdaPortSchOvrEntry 10 }

tmnxHsmdaPortSchOvrClass3WtInGp        OBJECT-TYPE
    SYNTAX      THsmdaWeightOverride
    MAX-ACCESS  read-create
    STATUS      current
    DESCRIPTION
        "The value of tmnxHsmdaPortSchOvrClass3WtInGp specifies the weight
         the HSMDA port scheduler policy should apply to this policy level
         within the group it belongs to.

         The value of tmnxHsmdaPortSchOvrClass3WtInGp will only be
         used if this policy level has been assigned to a group
         by setting tHsmdaSchedulerPlcyLvl3GrpId to a non-zero value.

         A value of -2 indicates no override.

         This object overrides
         TIMETRA-QOS-MIB::tHsmdaSchedulerPlcyLvl3WgtInGrp."
    DEFVAL { -2 }
    ::= { tmnxHsmdaPortSchOvrEntry 11 }

tmnxHsmdaPortSchOvrClass4Rate        OBJECT-TYPE
    SYNTAX      THsmdaPIRMRateOverride
    UNITS       "Mbps"
    MAX-ACCESS  read-create
    STATUS      current
    DESCRIPTION
        "The value of tmnxHsmdaPortSchOvrClass4Rate specifies the explicit
         maximum frame based bandwidth limit, in megabits per second, for
         this HSMDA port scheduler policy level.

         A value of -2 indicates no override.

         This object overrides TIMETRA-QOS-MIB::tHsmdaSchedulerPlcyLvl4Rate."
    DEFVAL { -2 }
    ::= { tmnxHsmdaPortSchOvrEntry 12 }

tmnxHsmdaPortSchOvrClass4WtInGp        OBJECT-TYPE
    SYNTAX      THsmdaWeightOverride
    MAX-ACCESS  read-create
    STATUS      current
    DESCRIPTION
        "The value of tmnxHsmdaPortSchOvrClass4WtInGp specifies the weight
         the HSMDA port scheduler policy should apply to this policy level
         within the group it belongs to.

         The value of tmnxHsmdaPortSchOvrClass4WtInGp will only be
         used if this policy level has been assigned to a group
         by setting tHsmdaSchedulerPlcyLvl4GrpId to a non-zero value.

         A value of -2 indicates no override.

         This object overrides
         TIMETRA-QOS-MIB::tHsmdaSchedulerPlcyLvl4WgtInGrp."
    DEFVAL { -2 }
    ::= { tmnxHsmdaPortSchOvrEntry 13 }

tmnxHsmdaPortSchOvrClass5Rate        OBJECT-TYPE
    SYNTAX      THsmdaPIRMRateOverride
    UNITS       "Mbps"
    MAX-ACCESS  read-create
    STATUS      current
    DESCRIPTION
        "The value of tmnxHsmdaPortSchOvrClass5Rate specifies the explicit
         maximum frame based bandwidth limit, in megabits per second, for
         this HSMDA port scheduler policy level.

         A value of -2 indicates no override.

         This object overrides TIMETRA-QOS-MIB::tHsmdaSchedulerPlcyLvl5Rate."
    DEFVAL { -2 }
    ::= { tmnxHsmdaPortSchOvrEntry 14 }

tmnxHsmdaPortSchOvrClass5WtInGp        OBJECT-TYPE
    SYNTAX      THsmdaWeightOverride
    MAX-ACCESS  read-create
    STATUS      current
    DESCRIPTION
        "The value of tmnxHsmdaPortSchOvrClass5WtInGp specifies the weight
         the HSMDA port scheduler policy should apply to this policy level
         within the group it belongs to.

         The value of tmnxHsmdaPortSchOvrClass5WtInGp will only be
         used if this policy level has been assigned to a group
         by setting tHsmdaSchedulerPlcyLvl5GrpId to a non-zero value.

         A value of -2 indicates no override.

         This object overrides
         TIMETRA-QOS-MIB::tHsmdaSchedulerPlcyLvl5WgtInGrp."
    DEFVAL { -2 }
    ::= { tmnxHsmdaPortSchOvrEntry 15 }

tmnxHsmdaPortSchOvrClass6Rate        OBJECT-TYPE
    SYNTAX      THsmdaPIRMRateOverride
    UNITS       "Mbps"
    MAX-ACCESS  read-create
    STATUS      current
    DESCRIPTION
        "The value of tmnxHsmdaPortSchOvrClass6Rate specifies the explicit
         maximum frame based bandwidth limit, in megabits per second, for
         this HSMDA port scheduler policy level.

         A value of -2 indicates no override.

         This object overrides TIMETRA-QOS-MIB::tHsmdaSchedulerPlcyLvl6Rate."
    DEFVAL { -2 }
    ::= { tmnxHsmdaPortSchOvrEntry 16 }

tmnxHsmdaPortSchOvrClass6WtInGp        OBJECT-TYPE
    SYNTAX      THsmdaWeightOverride
    MAX-ACCESS  read-create
    STATUS      current
    DESCRIPTION
        "The value of tmnxHsmdaPortSchOvrClass6WtInGp specifies the weight
         the HSMDA port scheduler policy should apply to this policy level
         within the group it belongs to.

         The value of tmnxHsmdaPortSchOvrClass6WtInGp will only be
         used if this policy level has been assigned to a group
         by setting tHsmdaSchedulerPlcyLvl6GrpId to a non-zero value.

         A value of -2 indicates no override.

         This object overrides
         TIMETRA-QOS-MIB::tHsmdaSchedulerPlcyLvl6WgtInGrp."
    DEFVAL { -2 }
    ::= { tmnxHsmdaPortSchOvrEntry 17 }

tmnxHsmdaPortSchOvrClass7Rate        OBJECT-TYPE
    SYNTAX      THsmdaPIRMRateOverride
    UNITS       "Mbps"
    MAX-ACCESS  read-create
    STATUS      current
    DESCRIPTION
        "The value of tmnxHsmdaPortSchOvrClass7Rate specifies the explicit
         maximum frame based bandwidth limit, in megabits per second, for
         this HSMDA port scheduler policy level.

         A value of -2 indicates no override.

         This object overrides TIMETRA-QOS-MIB::tHsmdaSchedulerPlcyLvl7Rate."
    DEFVAL { -2 }
    ::= { tmnxHsmdaPortSchOvrEntry 18 }

tmnxHsmdaPortSchOvrClass7WtInGp        OBJECT-TYPE
    SYNTAX      THsmdaWeightOverride
    MAX-ACCESS  read-create
    STATUS      current
    DESCRIPTION
        "The value of tmnxHsmdaPortSchOvrClass7WtInGp specifies the weight
         the HSMDA port scheduler policy should apply to this policy level
         within the group it belongs to.

         The value of tmnxHsmdaPortSchOvrClass7WtInGp will only be
         used if this policy level has been assigned to a group
         by setting tHsmdaSchedulerPlcyLvl7GrpId to a non-zero value.

         A value of -2 indicates no override.

         This object overrides
         TIMETRA-QOS-MIB::tHsmdaSchedulerPlcyLvl7WgtInGrp."
    DEFVAL { -2 }
    ::= { tmnxHsmdaPortSchOvrEntry 19 }

tmnxHsmdaPortSchOvrClass8Rate        OBJECT-TYPE
    SYNTAX      THsmdaPIRMRateOverride
    UNITS       "Mbps"
    MAX-ACCESS  read-create
    STATUS      current
    DESCRIPTION
        "The value of tmnxHsmdaPortSchOvrClass8Rate specifies the explicit
         maximum frame based bandwidth limit, in megabits per second, for
         this HSMDA port scheduler policy level.

         A value of -2 indicates no override.

         This object overrides TIMETRA-QOS-MIB::tHsmdaSchedulerPlcyLvl8Rate."
    DEFVAL { -2 }
    ::= { tmnxHsmdaPortSchOvrEntry 20 }

tmnxHsmdaPortSchOvrClass8WtInGp        OBJECT-TYPE
    SYNTAX      THsmdaWeightOverride
    MAX-ACCESS  read-create
    STATUS      current
    DESCRIPTION
        "The value of tmnxHsmdaPortSchOvrClass8WtInGp specifies the weight
         the HSMDA port scheduler policy should apply to this policy level
         within the group it belongs to.

         The value of tmnxHsmdaPortSchOvrClass8WtInGp will only be
         used if this policy level has been assigned to a group
         by setting tHsmdaSchedulerPlcyLvl8GrpId to a non-zero value.

         A value of -2 indicates no override.

         This object overrides
         TIMETRA-QOS-MIB::tHsmdaSchedulerPlcyLvl8WgtInGrp."
    DEFVAL { -2 }
    ::= { tmnxHsmdaPortSchOvrEntry 21 }

--
--  Port Egress Secondary Shaper
--
tmnxPortEgrShaperTblLastChanged OBJECT-TYPE
    SYNTAX      TimeStamp
    MAX-ACCESS  read-only
    STATUS      obsolete
    DESCRIPTION
        "The value of tmnxPortEgrShaperTblLastChanged indicates the sysUpTime
         at the time of the last modification of tmnxPortEgrShaperTable.

         If no changes were made to the table since the last
         re-initialization of the local network management subsystem,
         then this object contains a zero value.

         This object is obsoleted in 10.0 Release."
    ::= { tmnxPortObjs 29 }

tmnxPortEgrShaperTable OBJECT-TYPE
    SYNTAX      SEQUENCE OF TmnxPortEgrShaperEntry
    MAX-ACCESS  not-accessible
    STATUS      obsolete
    DESCRIPTION
        "The tmnxPortEgrShaperTable has an entry for each port-level egress
         secondary shaper configured on this system.

         This table is obsoleted in 10.0 Release."
    ::= { tmnxPortObjs 30 }

tmnxPortEgrShaperEntry    OBJECT-TYPE
    SYNTAX      TmnxPortEgrShaperEntry
    MAX-ACCESS  not-accessible
    STATUS      obsolete
    DESCRIPTION
        "Each row represents a particular port-level egress secondary shaper.
         Entries are created and deleted by the user."
    INDEX { tmnxChassisIndex, tmnxPortPortID, tmnxPortEgrShaperName }
    ::= { tmnxPortEgrShaperTable 1}

TmnxPortEgrShaperEntry ::= SEQUENCE
    {
        tmnxPortEgrShaperName            TNamedItem,
        tmnxPortEgrShaperRowStatus       RowStatus,
        tmnxPortEgrShaperLastChanged     TimeStamp,
        tmnxPortEgrShaperRate            TSecondaryShaper10GPIRRate
    }

tmnxPortEgrShaperName        OBJECT-TYPE
    SYNTAX      TNamedItem
    MAX-ACCESS  not-accessible
    STATUS      obsolete
    DESCRIPTION
        "The port egress shaper named is used an index to the table entry."
    ::= { tmnxPortEgrShaperEntry 1 }

tmnxPortEgrShaperRowStatus        OBJECT-TYPE
    SYNTAX      RowStatus
    MAX-ACCESS  read-create
    STATUS      obsolete
    DESCRIPTION
        "The value of tmnxPortEgrShaperRowStatus is used for the creation
         and deletion of entries in the tmnxPortEgrShaperTable."
    ::= { tmnxPortEgrShaperEntry 2 }

tmnxPortEgrShaperLastChanged        OBJECT-TYPE
    SYNTAX      TimeStamp
    MAX-ACCESS  read-only
    STATUS      obsolete
    DESCRIPTION
        "The value of tmnxPortEgrShaperLastChanged indicates the sysUpTime
         at the time of the last modification of this entry.

         If no changes were made to the entry since the last
         re-initialization of the local network management subsystem,
         then this object contains a zero value."
    ::= { tmnxPortEgrShaperEntry 3 }

tmnxPortEgrShaperRate        OBJECT-TYPE
    SYNTAX      TSecondaryShaper10GPIRRate
    UNITS       "Mbps"
    MAX-ACCESS  read-create
    STATUS      obsolete
    DESCRIPTION
        "The value of tmnxPortEgrShaperRate specifies the explicit maximum
         frame based bandwidth limit, in megabits per second, of this
         egress port secondary shaper policy."
    DEFVAL    { -1 }
    ::= { tmnxPortEgrShaperEntry 4 }

--
--  Digital Diagnostic Monitor Table
--
tmnxDigitalDiagMonitorTable OBJECT-TYPE
    SYNTAX  SEQUENCE OF TmnxDigitalDiagMonitorEntry
    MAX-ACCESS  not-accessible
    STATUS      current
    DESCRIPTION
        "The tmnxDigitalDiagMonitorTable has an entry for each SFF in the
         system that supports Digital Diagnostic Monitoring (DDM). The table is
         indexed by TmnxPortID. Each row in this table is dynamically added
         and removed internally by the system based on the presence or absence
         of DDM capable SFF components."
    ::= { tmnxPortObjs 31 }

tmnxDigitalDiagMonitorEntry OBJECT-TYPE
    SYNTAX      TmnxDigitalDiagMonitorEntry
    MAX-ACCESS  not-accessible
    STATUS      current
    DESCRIPTION
        "Each row represents a particular SFF that supports Digital
         Diagnostic Monitoring.
         Entries are created and deleted internally by the system."
    INDEX { tmnxChassisIndex, tmnxPortPortID }
    ::= { tmnxDigitalDiagMonitorTable 1}

TmnxDigitalDiagMonitorEntry ::= SEQUENCE
    {
        tmnxDDMTemperature                   Integer32,
        tmnxDDMTempLowWarning                Integer32,
        tmnxDDMTempLowAlarm                  Integer32,
        tmnxDDMTempHiWarning                 Integer32,
        tmnxDDMTempHiAlarm                   Integer32,
        tmnxDDMSupplyVoltage                 Integer32,
        tmnxDDMSupplyVoltageLowWarning       Integer32,
        tmnxDDMSupplyVoltageLowAlarm         Integer32,
        tmnxDDMSupplyVoltageHiWarning        Integer32,
        tmnxDDMSupplyVoltageHiAlarm          Integer32,
        tmnxDDMTxBiasCurrent                 Integer32,
        tmnxDDMTxBiasCurrentLowWarning       Integer32,
        tmnxDDMTxBiasCurrentLowAlarm         Integer32,
        tmnxDDMTxBiasCurrentHiWarning        Integer32,
        tmnxDDMTxBiasCurrentHiAlarm          Integer32,
        tmnxDDMTxOutputPower                 Integer32,
        tmnxDDMTxOutputPowerLowWarning       Integer32,
        tmnxDDMTxOutputPowerLowAlarm         Integer32,
        tmnxDDMTxOutputPowerHiWarning        Integer32,
        tmnxDDMTxOutputPowerHiAlarm          Integer32,
        tmnxDDMRxOpticalPower                Integer32,
        tmnxDDMRxOpticalPowerLowWarning      Integer32,
        tmnxDDMRxOpticalPowerLowAlarm        Integer32,
        tmnxDDMRxOpticalPowerHiWarning       Integer32,
        tmnxDDMRxOpticalPowerHiAlarm         Integer32,
        tmnxDDMRxOpticalPowerType            INTEGER,
        tmnxDDMAux1                          Integer32,
        tmnxDDMAux1LowWarning                Integer32,
        tmnxDDMAux1LowAlarm                  Integer32,
        tmnxDDMAux1HiWarning                 Integer32,
        tmnxDDMAux1HiAlarm                   Integer32,
        tmnxDDMAux1Type                      INTEGER,
        tmnxDDMAux2                          Integer32,
        tmnxDDMAux2LowWarning                Integer32,
        tmnxDDMAux2LowAlarm                  Integer32,
        tmnxDDMAux2HiWarning                 Integer32,
        tmnxDDMAux2HiAlarm                   Integer32,
        tmnxDDMAux2Type                      INTEGER,
        tmnxDDMFailedThresholds              TmnxDigitalDiagnosticFailureBits,
        tmnxDDMExternallyCalibrated          TruthValue,
        tmnxDDMExtCalRxPower4                Unsigned32,
        tmnxDDMExtCalRxPower3                Unsigned32,
        tmnxDDMExtCalRxPower2                Unsigned32,
        tmnxDDMExtCalRxPower1                Unsigned32,
        tmnxDDMExtCalRxPower0                Unsigned32,
        tmnxDDMExtCalTxLaserBiasSlope        Unsigned32,
        tmnxDDMExtCalTxLaserBiasOffset       Integer32,
        tmnxDDMExtCalTxPowerSlope            Unsigned32,
        tmnxDDMExtCalTxPowerOffset           Integer32,
        tmnxDDMExtCalTemperatureSlope        Unsigned32,
        tmnxDDMExtCalTemperatureOffset       Integer32,
        tmnxDDMExtCalVoltageSlope            Unsigned32,
        tmnxDDMExtCalVoltageOffset           Integer32
    }

tmnxDDMTemperature                 OBJECT-TYPE
    SYNTAX      Integer32
    MAX-ACCESS  read-only
    STATUS      current
    DESCRIPTION
        "The value of tmnxDDMTemperature indicates the current temperature
         of the SFF in 1/256th degrees Celsius.

         If the SFF is externally calibrated, the objects
         tmnxDDMExtCalTemperatureSlope and tmnxDDMExtCalTemperatureOffset affect
         the temperature calculation.

         The formula for translating between the value of tmnxDDMTemperature and
         degrees Celsius is:
             Internally Calibrated only:
                tmnxDDMTemperature / 256
             Externally Calibrated:
                (tmnxDDMTemperature * (tmnxDDMExtCalTemperatureSlope / 256)
                      + tmnxDDMExtCalTemperatureOffset) / 256

         For example (internally calibrated SFF):
         The SNMP value 5734 is 22.4 degrees Celsius."
    REFERENCE 
        "SFF Committee, SFF-8472 Specification for Diagnostic Monitoring
         Interface for Optical Transceivers, Rev 11.3, June 11, 2013"
    ::= { tmnxDigitalDiagMonitorEntry 1 }

tmnxDDMTempLowWarning              OBJECT-TYPE
    SYNTAX      Integer32
    MAX-ACCESS  read-only
    STATUS      current
    DESCRIPTION
        "The value of tmnxDDMTempLowWarning indicates the temperature
         of the SFF in degrees Celsius that triggers a low-warning."
    ::= { tmnxDigitalDiagMonitorEntry 2 }

tmnxDDMTempLowAlarm                OBJECT-TYPE
    SYNTAX      Integer32
    MAX-ACCESS  read-only
    STATUS      current
    DESCRIPTION
        "The value of tmnxDDMTempLowAlarm indicates the temperature
         of the SFF in degrees Celsius that triggers a low-alarm."
    ::= { tmnxDigitalDiagMonitorEntry 3 }

tmnxDDMTempHiWarning               OBJECT-TYPE
    SYNTAX      Integer32
    MAX-ACCESS  read-only
    STATUS      current
    DESCRIPTION
        "The value of tmnxDDMTempHiWarning indicates the temperature
         of the SFF in degrees Celsius that triggers a hi-warning."
    ::= { tmnxDigitalDiagMonitorEntry 4 }

tmnxDDMTempHiAlarm                 OBJECT-TYPE
    SYNTAX      Integer32
    MAX-ACCESS  read-only
    STATUS      current
    DESCRIPTION
        "The value of tmnxDDMTempHiAlarm indicates the temperature
         of the SFF in degrees Celsius that triggers a hi-alarm."
    ::= { tmnxDigitalDiagMonitorEntry 5 }

tmnxDDMSupplyVoltage               OBJECT-TYPE
    SYNTAX      Integer32
    MAX-ACCESS  read-only
    STATUS      current
    DESCRIPTION
        "The value of tmnxDDMSupplyVoltage indicates the current supply
         voltage of the SFF in 1/10000 of a Volt(V).

         If the SFF is externally calibrated, the objects
         tmnxDDMExtCalVoltageSlope and tmnxDDMExtCalVoltageOffset affect
         the voltage calculation.

         The formula for translating between the value of tmnxDDMSupplyVoltage
         and Voltage is:
             Internally Calibrated only:
                tmnxDDMSupplyVoltage / 10000
             Externally Calibrated:
                (tmnxDDMSupplyVoltage * (tmnxDDMExtCalVoltageSlope / 256)
                      + tmnxDDMExtCalVoltageOffset) / 10000

         For example (internally calibrated SFF):
         The SNMP value 32851 is 3.2851 Volts (V)."
    REFERENCE 
        "SFF Committee, SFF-8472 Specification for Diagnostic Monitoring
         Interface for Optical Transceivers, Rev 11.3, June 11, 2013"
    ::= { tmnxDigitalDiagMonitorEntry 6 }

tmnxDDMSupplyVoltageLowWarning     OBJECT-TYPE
    SYNTAX      Integer32
    MAX-ACCESS  read-only
    STATUS      current
    DESCRIPTION
        "The value of tmnxDDMSupplyVoltageLowWarning indicates the supply
         voltage of the SFF in micro-Volts (uV) that triggers a
         low-warning."
    ::= { tmnxDigitalDiagMonitorEntry 7 }

tmnxDDMSupplyVoltageLowAlarm       OBJECT-TYPE
    SYNTAX      Integer32
    MAX-ACCESS  read-only
    STATUS      current
    DESCRIPTION
        "The value of tmnxDDMSupplyVoltageLowAlarm indicates the supply
         voltage of the SFF in micro-Volts (uV) that triggers a low-alarm."
    ::= { tmnxDigitalDiagMonitorEntry 8 }

tmnxDDMSupplyVoltageHiWarning      OBJECT-TYPE
    SYNTAX      Integer32
    MAX-ACCESS  read-only
    STATUS      current
    DESCRIPTION
        "The value of tmnxDDMSupplyVoltageHiWarning indicates the supply
         voltage of the SFF in micro-Volts (uV) that triggers a hi-warning."
    ::= { tmnxDigitalDiagMonitorEntry 9 }

tmnxDDMSupplyVoltageHiAlarm        OBJECT-TYPE
    SYNTAX      Integer32
    MAX-ACCESS  read-only
    STATUS      current
    DESCRIPTION
        "The value of tmnxDDMSupplyVoltageHiAlarm indicates the supply
         voltage of the SFF in micro-Volts (uV) that triggers a hi-alarm."
    ::= { tmnxDigitalDiagMonitorEntry 10 }

tmnxDDMTxBiasCurrent               OBJECT-TYPE
    SYNTAX      Integer32
    MAX-ACCESS  read-only
    STATUS      current
    DESCRIPTION
        "The value of tmnxDDMTxBiasCurrent indicates the current Transmit
         Bias Current of the SFF in 1/500 milliamperes (mA).

         If the SFF is externally calibrated, the objects
         tmnxDDMExtCalTxLaserBiasSlope and tmnxDDMExtCalTxLaserBiasOffset affect
         the ampere calculation.

         The formula for translating between the value of tmnxDDMTxBiasCurrent
         and amperes is:
             Internally Calibrated only:
                tmnxDDMTxBiasCurrent / 500
             Externally Calibrated:
                (tmnxDDMTxBiasCurrent * (tmnxDDMExtCalTxLaserBiasSlope / 256)
                      + tmnxDDMExtCalTxLaserBiasOffset) / 500

         For example (internally calibrated SFF):
         The SNMP value 2565 is 5.1 milliamperes (mA)."
    REFERENCE 
        "SFF Committee, SFF-8472 Specification for Diagnostic Monitoring
         Interface for Optical Transceivers, Rev 11.3, June 11, 2013"
    ::= { tmnxDigitalDiagMonitorEntry 11 }

tmnxDDMTxBiasCurrentLowWarning     OBJECT-TYPE
    SYNTAX      Integer32
    MAX-ACCESS  read-only
    STATUS      current
    DESCRIPTION
        "The value of tmnxDDMTxBiasCurrentLowWarning indicates the Transmit
         Bias Current of the SFF in micro-Amperes (uA) that triggers a
         low-warning."
    ::= { tmnxDigitalDiagMonitorEntry 12 }

tmnxDDMTxBiasCurrentLowAlarm       OBJECT-TYPE
    SYNTAX      Integer32
    MAX-ACCESS  read-only
    STATUS      current
    DESCRIPTION
        "The value of tmnxDDMTxBiasCurrentLowAlarm indicates the Transmit
         Bias Current of the SFF in micro-Amperes (uA) that triggers a
         low-alarm."
    ::= { tmnxDigitalDiagMonitorEntry 13 }

tmnxDDMTxBiasCurrentHiWarning      OBJECT-TYPE
    SYNTAX      Integer32
    MAX-ACCESS  read-only
    STATUS      current
    DESCRIPTION
        "The value of tmnxDDMTxBiasCurrentHiWarning indicates the Transmit
         Bias Current of the SFF in micro-Amperes (uA) that triggers a
         hi-warning."
    ::= { tmnxDigitalDiagMonitorEntry 14 }

tmnxDDMTxBiasCurrentHiAlarm        OBJECT-TYPE
    SYNTAX      Integer32
    MAX-ACCESS  read-only
    STATUS      current
    DESCRIPTION
        "The value of tmnxDDMTxBiasCurrentHiAlarm indicates the Transmit
         Bias Current of the SFF in micro-Amperes (uA) that triggers a
         hi-alarm."
    ::= { tmnxDigitalDiagMonitorEntry 15 }

tmnxDDMTxOutputPower               OBJECT-TYPE
    SYNTAX      Integer32
    MAX-ACCESS  read-only
    STATUS      current
    DESCRIPTION
        "The value of tmnxDDMTxOutputPower indicates the current Output
         Power of the SFF in one tenths of a microwatt (uW).

         If the SFF is externally calibrated, the objects 
         tmnxDDMExtCalTemperatureSlope and tmnxDDMExtCalTemperatureOffset
         affect the output power calculation.

         For example (internally calibrated SFF):
         Using the SNMP value of 790, and using units of tenths of microwatt,
         790 becomes 79 microwatts or 0.079 milliwatts. Converting to dBm:
               10 x log10(0.079) = -11.0 dBm"
    REFERENCE 
        "SFF Committee, SFF-8472 Specification for Diagnostic Monitoring
         Interface for Optical Transceivers, Rev 11.3, June 11, 2013"
    ::= { tmnxDigitalDiagMonitorEntry 16 }

tmnxDDMTxOutputPowerLowWarning     OBJECT-TYPE
    SYNTAX      Integer32
    MAX-ACCESS  read-only
    STATUS      current
    DESCRIPTION
        "The value of tmnxDDMTxOutputPowerLowWarning indicates the Output Power
         of the SFF in one tenths of a microwatt (uW) that triggers a
         low-warning."
    ::= { tmnxDigitalDiagMonitorEntry 17 }

tmnxDDMTxOutputPowerLowAlarm       OBJECT-TYPE
    SYNTAX      Integer32
    MAX-ACCESS  read-only
    STATUS      current
    DESCRIPTION
        "The value of tmnxDDMTxOutputPowerLowAlarm indicates the Output Power
         of the SFF in one tenths of a microwatt (uW) that triggers a
         low-alarm."
    ::= { tmnxDigitalDiagMonitorEntry 18 }

tmnxDDMTxOutputPowerHiWarning      OBJECT-TYPE
    SYNTAX      Integer32
    MAX-ACCESS  read-only
    STATUS      current
    DESCRIPTION
        "The value of tmnxDDMTxOutputPowerHiWarning indicates the Output Power
         of the SFF in one tenths of a microwatt (uW) that triggers a
         hi-warning."
    ::= { tmnxDigitalDiagMonitorEntry 19 }

tmnxDDMTxOutputPowerHiAlarm        OBJECT-TYPE
    SYNTAX      Integer32
    MAX-ACCESS  read-only
    STATUS      current
    DESCRIPTION
        "The value of tmnxDDMTxOutputPowerHiAlarm indicates the Output Power
         of the SFF in one tenths of a microwatt (uW) that triggers a
         hi-alarm."
    ::= { tmnxDigitalDiagMonitorEntry 20 }

tmnxDDMRxOpticalPower              OBJECT-TYPE
    SYNTAX      Integer32
    MAX-ACCESS  read-only
    STATUS      current
    DESCRIPTION
        "The value of tmnxDDMRxOpticalPower indicates the current Received
         Optical Power of the SFF in one tenths of a microwatt (uW).

         If the SFF is externally calibrated, the objects 
         tmnxDDMExtCalRxPower4, tmnxDDMExtCalRxPower3, tmnxDDMExtCalRxPower2,
         tmnxDDMExtCalRxPower1 and tmnxDDMExtCalRxPower0 affect the output
         power calculation.

         For example (internally calibrated SFF):
         Using the SNMP value of 790, and using units of tenths of microwatt,
         790 becomes 79 microwatts or 0.079 milliwatts. Converting to dBm:
               10 x log10(0.079) = -11.0 dBm"
    REFERENCE 
        "SFF Committee, SFF-8472 Specification for Diagnostic Monitoring
         Interface for Optical Transceivers, Rev 11.3, June 11, 2013"
    ::= { tmnxDigitalDiagMonitorEntry 21 }

tmnxDDMRxOpticalPowerLowWarning    OBJECT-TYPE
    SYNTAX      Integer32
    MAX-ACCESS  read-only
    STATUS      current
    DESCRIPTION
        "The value of tmnxDDMRxOpticalPowerLowWarning indicates the Received
         Optical Power of the SFF in one tenths of a microwatt (uW) that
         triggers a low-warning."
    ::= { tmnxDigitalDiagMonitorEntry 22 }

tmnxDDMRxOpticalPowerLowAlarm      OBJECT-TYPE
    SYNTAX      Integer32
    MAX-ACCESS  read-only
    STATUS      current
    DESCRIPTION
        "The value of tmnxDDMRxOpticalPowerLowAlarm indicates the Received
         Optical Power of the SFF in one tenths of a microwatt (uW) that
         triggers a low-alarm."
    ::= { tmnxDigitalDiagMonitorEntry 23 }

tmnxDDMRxOpticalPowerHiWarning     OBJECT-TYPE
    SYNTAX      Integer32
    MAX-ACCESS  read-only
    STATUS      current
    DESCRIPTION
        "The value of tmnxDDMRxOpticalPowerHiWarning indicates the Received
         Optical Power of the SFF in one tenths of a microwatt (uW) that
         triggers a hi-warning."
    ::= { tmnxDigitalDiagMonitorEntry 24 }

tmnxDDMRxOpticalPowerHiAlarm       OBJECT-TYPE
    SYNTAX      Integer32
    MAX-ACCESS  read-only
    STATUS      current
    DESCRIPTION
        "The value of tmnxDDMRxOpticalPowerHiAlarm indicates the Received
         Optical Power of the SFF in one tenths of a microwatt (uW) that
         triggers a hi-alarm."
    ::= { tmnxDigitalDiagMonitorEntry 25 }

tmnxDDMRxOpticalPowerType          OBJECT-TYPE
    SYNTAX      INTEGER {
                    oma      (0),   -- Optical Modulation Amplitude
                    average  (1)    -- Average rx optical power
                }
    MAX-ACCESS  read-only
    STATUS      current
    DESCRIPTION
        "The value of tmnxDDMRxOpticalPowerType indicates whether the
         tmnxDDMRxOpticalPower was taken as an average, or as an Optical
         Modulation Amplitude (OMA)."
    ::= { tmnxDigitalDiagMonitorEntry 26 }

tmnxDDMAux1                        OBJECT-TYPE
    SYNTAX      Integer32
    MAX-ACCESS  read-only
    STATUS      current
    DESCRIPTION
        "The value of tmnxDDMAux1 indicates the Manufacturer specific
         Auxiliary 1 information of the XFP."
    ::= { tmnxDigitalDiagMonitorEntry 27 }

tmnxDDMAux1LowWarning              OBJECT-TYPE
    SYNTAX      Integer32
    MAX-ACCESS  read-only
    STATUS      current
    DESCRIPTION
        "The value of tmnxDDMAux1LowWarning indicates the Manufacturer specific
         Auxiliary 1 low-warning threshold for the XFP."
    ::= { tmnxDigitalDiagMonitorEntry 28 }

tmnxDDMAux1LowAlarm                OBJECT-TYPE
    SYNTAX      Integer32
    MAX-ACCESS  read-only
    STATUS      current
    DESCRIPTION
        "The value of tmnxDDMAux1LowAlarm indicates the Manufacturer specific
         Auxiliary 1 low-alarm threshold for the XFP."
    ::= { tmnxDigitalDiagMonitorEntry 29 }

tmnxDDMAux1HiWarning               OBJECT-TYPE
    SYNTAX      Integer32
    MAX-ACCESS  read-only
    STATUS      current
    DESCRIPTION
        "The value of tmnxDDMAux1HiWarning indicates the Manufacturer specific
         Auxiliary 1 hi-warning threshold for the XFP."
    ::= { tmnxDigitalDiagMonitorEntry 30 }

tmnxDDMAux1HiAlarm                 OBJECT-TYPE
    SYNTAX      Integer32
    MAX-ACCESS  read-only
    STATUS      current
    DESCRIPTION
        "The value of tmnxDDMAux1HiAlarm indicates the Manufacturer specific
         Auxiliary 1 hi-alarm threshold for the XFP."
    ::= { tmnxDigitalDiagMonitorEntry 31 }

tmnxDDMAux1Type                    OBJECT-TYPE
    SYNTAX      INTEGER {
                    none             (0),
                    adp-bias-voltage (1),
                    reserved-2       (2),
                    tec-current      (3),
                    laser-temp       (4),
                    laser-wavelength (5),
                    voltage-50       (6),
                    voltage-33       (7),
                    voltage-18       (8),
                    voltage-52       (9),
                    current-50       (10),
                    reserved-11      (11),
                    reserved-12      (12),
                    current-33       (13),
                    current-18       (14),
                    current-52       (15)
                }
    MAX-ACCESS  read-only
    STATUS      current
    DESCRIPTION
        "The value of tmnxDDMAux1Type indicates the measurement type of
         the Manufacturer specific Auxiliary 1 information of the XFP:
            none             (0)  - not specified.
            adp-bias-voltage (1)  - LSB is 10mV.
            reserved-2       (2)  - reserved for future use.
            tec-current      (3)  - LSB is 100uA.
            laser-temp       (4)  - degrees Celsius(C).
            laser-wavelength (5)  - LSB is 0.05 nm.
            voltage-50       (6)  - 5.0 supply voltage, LSB=100uV.
            voltage-33       (7)  - 3.3 supply voltage, LSB=100uV.
            voltage-18       (8)  - 1.8 supply voltage, LSB=100uV,
            voltage-52       (9)  - -5.2 supply voltage, LSB=100uV.
            current-50      (10)  - 5.0V supply current, LSB=100uA.
            reserved-11     (11)  - reserved for future use.
            reserved-12     (12)  - reserved for future use.
            current-33      (13)  - 3.3V supply current, LSB=100uA.
            current-18      (14)  - 1.8V supply current, LSB=100uA.
            current-52      (15)  - -5.2V supply current, LSB=100uA."
    ::= { tmnxDigitalDiagMonitorEntry 32 }

tmnxDDMAux2                        OBJECT-TYPE
    SYNTAX      Integer32
    MAX-ACCESS  read-only
    STATUS      current
    DESCRIPTION
        "The value of tmnxDDMAux2 indicates the Manufacturer specific
         Auxiliary 2 information of the SFF."
    ::= { tmnxDigitalDiagMonitorEntry 33 }

tmnxDDMAux2LowWarning              OBJECT-TYPE
    SYNTAX      Integer32
    MAX-ACCESS  read-only
    STATUS      current
    DESCRIPTION
        "The value of tmnxDDMAux2LowWarning indicates the Manufacturer specific
         Auxiliary 2 low-warning threshold for the XFP."
    ::= { tmnxDigitalDiagMonitorEntry 34 }

tmnxDDMAux2LowAlarm                OBJECT-TYPE
    SYNTAX      Integer32
    MAX-ACCESS  read-only
    STATUS      current
    DESCRIPTION
        "The value of tmnxDDMAux2LowAlarm indicates the Manufacturer specific
         Auxiliary 2 low-alarm threshold for the XFP."
    ::= { tmnxDigitalDiagMonitorEntry 35 }

tmnxDDMAux2HiWarning               OBJECT-TYPE
    SYNTAX      Integer32
    MAX-ACCESS  read-only
    STATUS      current
    DESCRIPTION
        "The value of tmnxDDMAux2HiWarning indicates the Manufacturer specific
         Auxiliary 2 hi-warning threshold for the XFP."
    ::= { tmnxDigitalDiagMonitorEntry 36 }

tmnxDDMAux2HiAlarm                 OBJECT-TYPE
    SYNTAX      Integer32
    MAX-ACCESS  read-only
    STATUS      current
    DESCRIPTION
        "The value of tmnxDDMAux2HiAlarm indicates the Manufacturer specific
         Auxiliary 2 hi-alarm threshold for the XFP."
    ::= { tmnxDigitalDiagMonitorEntry 37 }

tmnxDDMAux2Type                    OBJECT-TYPE
    SYNTAX      INTEGER {
                    none             (0),
                    adp-bias-voltage (1),
                    reserved-2       (2),
                    tec-current      (3),
                    laser-temp       (4),
                    laser-wavelength (5),
                    voltage-50       (6),
                    voltage-33       (7),
                    voltage-18       (8),
                    voltage-52       (9),
                    current-50       (10),
                    reserved-11      (11),
                    reserved-12      (12),
                    current-33       (13),
                    current-18       (14),
                    current-52       (15)
                }
    MAX-ACCESS  read-only
    STATUS      current
    DESCRIPTION
        "The value of tmnxDDMAux2Type indicates the measurement type of
         the Manufacturer specific Auxiliary 2 information of the XFP:
            none             (0)  - not specified.
            adp-bias-voltage (1)  - LSB is 10mV.
            reserved-2       (2)  - reserved for future use.
            tec-current      (3)  - LSB is 100uA.
            laser-temp       (4)  - degrees Celsius(C).
            laser-wavelength (5)  - LSB is 0.05 nm.
            voltage-50       (6)  - 5.0 supply voltage, LSB=100uV.
            voltage-33       (7)  - 3.3 supply voltage, LSB=100uV.
            voltage-18       (8)  - 1.8 supply voltage, LSB=100uV,
            voltage-52       (9)  - -5.2 supply voltage, LSB=100uV.
            current-50      (10)  - 5.0V supply current, LSB=100uA.
            reserved-11     (11)  - reserved for future use.
            reserved-12     (12)  - reserved for future use.
            current-33      (13)  - 3.3V supply current, LSB=100uA.
            current-18      (14)  - 1.8V supply current, LSB=100uA.
            current-52      (15)  - -5.2V supply current, LSB=100uA."
    ::= { tmnxDigitalDiagMonitorEntry 38 }

tmnxDDMFailedThresholds            OBJECT-TYPE
    SYNTAX      TmnxDigitalDiagnosticFailureBits
    MAX-ACCESS  read-only
    STATUS      current
    DESCRIPTION
        "The value of tmnxDDMFailedThresholds indicates which objects
        of the monitored SFF is in a failed or cleared threshold state.
        A set bit indicates that the specified threshold has been exceeded."
    ::= { tmnxDigitalDiagMonitorEntry 39 }

tmnxDDMExternallyCalibrated        OBJECT-TYPE
    SYNTAX      TruthValue
    MAX-ACCESS  read-only
    STATUS      current
    DESCRIPTION
        "The value of tmnxDDMExternallyCalibrated indicates whether the
         SFF was externally calibrated (true) or internally calibrated (false)."
    ::= { tmnxDigitalDiagMonitorEntry 40 }

tmnxDDMExtCalRxPower4              OBJECT-TYPE
    SYNTAX      Unsigned32
    MAX-ACCESS  read-only
    STATUS      current
    DESCRIPTION
        "The value of tmnxDDMExtCalRxPower4 indicates the Rx_PWR(4)
         value as specified in Table 3.16 in the SFF Committee Standard's
         document SFF-8472 Rev 10.2."
    REFERENCE "SFF-8472 Rev 10.2"
    ::= { tmnxDigitalDiagMonitorEntry 41 }

tmnxDDMExtCalRxPower3              OBJECT-TYPE
    SYNTAX      Unsigned32
    MAX-ACCESS  read-only
    STATUS      current
    DESCRIPTION
        "The value of tmnxDDMExtCalRxPower3 indicates the Rx_PWR(3)
         value as specified in Table 3.16 in the SFF Committee Standard's
         document SFF-8462 Rev 10.2."
    REFERENCE "SFF-8472 Rev 10.2"
    ::= { tmnxDigitalDiagMonitorEntry 42 }

tmnxDDMExtCalRxPower2              OBJECT-TYPE
    SYNTAX      Unsigned32
    MAX-ACCESS  read-only
    STATUS      current
    DESCRIPTION
        "The value of tmnxDDMExtCalRxPower2 indicates the Rx_PWR(2)
         value as specified in Table 3.16 in the SFF Committee Standard's
         document SFF-8472 Rev 10.2."
    REFERENCE "SFF-8472 Rev 10.2"
    ::= { tmnxDigitalDiagMonitorEntry 43 }

tmnxDDMExtCalRxPower1              OBJECT-TYPE
    SYNTAX      Unsigned32
    MAX-ACCESS  read-only
    STATUS      current
    DESCRIPTION
        "The value of tmnxDDMExtCalRxPower1 indicates the Rx_PWR(1)
         value as specified in Table 3.16 in the SFF Committee Standard's
         document SFF-8472 Rev 10.2."
    REFERENCE "SFF-8472 Rev 10.2"
    ::= { tmnxDigitalDiagMonitorEntry 44 }

tmnxDDMExtCalRxPower0              OBJECT-TYPE
    SYNTAX      Unsigned32
    MAX-ACCESS  read-only
    STATUS      current
    DESCRIPTION
        "The value of tmnxDDMExtCalRxPower0 indicates the Rx_PWR(0)
         value as specified in Table 3.16 in the SFF Committee Standard's
         document SFF-8472 Rev 10.2."
    REFERENCE "SFF-8472 Rev 10.2"
    ::= { tmnxDigitalDiagMonitorEntry 45 }

tmnxDDMExtCalTxLaserBiasSlope      OBJECT-TYPE
    SYNTAX      Unsigned32 (0..65535)
    MAX-ACCESS  read-only
    STATUS      current
    DESCRIPTION
        "The value of tmnxDDMExtCalTxLaserBiasSlope indicates the
         Tx_l(Slope) value as specified in Table 3.16 in the SFF
         Committee Standard's document SFF-8472 Rev 10.2."
    REFERENCE "SFF-8472 Rev 10.2"
    ::= { tmnxDigitalDiagMonitorEntry 46 }

tmnxDDMExtCalTxLaserBiasOffset     OBJECT-TYPE
    SYNTAX      Integer32 (-32767..32768)
    MAX-ACCESS  read-only
    STATUS      current
    DESCRIPTION
        "The value of tmnxDDMExtCalTxLaserBiasOffset indicates the
         Tx_l(Offset) value as specified in Table 3.16 in the SFF
         Committee Standard's document SFF-8472 Rev 10.2."
    REFERENCE "SFF-8472 Rev 10.2"
    ::= { tmnxDigitalDiagMonitorEntry 47 }

tmnxDDMExtCalTxPowerSlope          OBJECT-TYPE
    SYNTAX      Unsigned32 (0..65535)
    MAX-ACCESS  read-only
    STATUS      current
    DESCRIPTION
        "The value of tmnxDDMExtCalTxPowerSlope indicates the
         Tx_PWR(Slope) value as specified in Table 3.16 in the
         SFF Committee Standard's document SFF-8472 Rev 10.2."
    REFERENCE "SFF-8472 Rev 10.2"
    ::= { tmnxDigitalDiagMonitorEntry 48 }

tmnxDDMExtCalTxPowerOffset         OBJECT-TYPE
    SYNTAX      Integer32 (-32767..32768)
    MAX-ACCESS  read-only
    STATUS      current
    DESCRIPTION
        "The value of tmnxDDMExtCalTxPowerOffset indicates the
         Tx_PWR(Offset) value as specified in Table 3.16 in the
         SFF Committee Standard's document SFF-8472 Rev 10.2."
    REFERENCE "SFF-8472 Rev 10.2"
    ::= { tmnxDigitalDiagMonitorEntry 49 }

tmnxDDMExtCalTemperatureSlope      OBJECT-TYPE
    SYNTAX      Unsigned32 (0..65535)
    MAX-ACCESS  read-only
    STATUS      current
    DESCRIPTION
        "The value of tmnxDDMExtCalTemperatureSlope indicates the
         T(Slope) value as specified in Table 3.16 in the SFF
         Committee Standard's document SFF-8472 Rev 10.2."
    REFERENCE "SFF-8472 Rev 10.2"
    ::= { tmnxDigitalDiagMonitorEntry 50 }

tmnxDDMExtCalTemperatureOffset     OBJECT-TYPE
    SYNTAX      Integer32 (-32767..32768)
    MAX-ACCESS  read-only
    STATUS      current
    DESCRIPTION
        "The value of tmnxDDMExtCalTemperatureOffset indicates the
         T(Offset) value as specified in Table 3.16 in the SFF
         Committee Standard's document SFF-8472 Rev 10.2."
    REFERENCE "SFF-8472 Rev 10.2"
    ::= { tmnxDigitalDiagMonitorEntry 51 }

tmnxDDMExtCalVoltageSlope          OBJECT-TYPE
    SYNTAX      Unsigned32 (0..65535)
    MAX-ACCESS  read-only
    STATUS      current
    DESCRIPTION
        "The value of tmnxDDMExtCalVoltageSlope indicates the V(Slope)
        value as specified in Table 3.16 in the SFF Committee Standard's
        document SFF-8472 Rev 10.2."
    REFERENCE "SFF-8472 Rev 10.2"
    ::= { tmnxDigitalDiagMonitorEntry 52 }

tmnxDDMExtCalVoltageOffset         OBJECT-TYPE
    SYNTAX      Integer32 (-32767..32768)
    MAX-ACCESS  read-only
    STATUS      current
    DESCRIPTION
        "The value of tmnxDDMExtCalVoltageOffset indicates the V(Slope)
        value as specified in Table 3.16 in the SFF Committee Standard's
        document SFF-8472 Rev 10.2."
    REFERENCE "SFF-8472 Rev 10.2"
    ::= { tmnxDigitalDiagMonitorEntry 53 }

--
-- access ingress queue group table
--

tPortAccIngQGrpTableLastChgd OBJECT-TYPE
    SYNTAX       TimeStamp
    MAX-ACCESS   read-only
    STATUS       current
    DESCRIPTION
        "The value of tPortAccIngQGrpTableLastChgd indicates the
        timestamp of last change to the tPortAccIngQGrpTable."
    ::= { tmnxPortObjs 32 }

tPortAccIngQGrpTable OBJECT-TYPE
    SYNTAX       SEQUENCE OF TPortAccIngQGrpEntry
    MAX-ACCESS   not-accessible
    STATUS       current
    DESCRIPTION
        "The value of tPortAccIngQGrpTable defines access Ingress Queue Group
        Table for providing, via SNMP, the capability of defining the port
        specific queue groups from the queue-groups existing in the
        TIMETRA-QOS-MIB::tQosIngQGroupTable."
    ::= { tmnxPortObjs 33 }

tPortAccIngQGrpEntry OBJECT-TYPE
    SYNTAX       TPortAccIngQGrpEntry
    MAX-ACCESS   not-accessible
    STATUS       current
    DESCRIPTION
        "The value of tPortAccIngQGrpEntry defines an entry in the
        tPortAccIngQGrpTable.

        Entries are created/deleted in this table by SNMP sets to
        tPortAccIngQGrpRowStatus."
    INDEX { tmnxChassisIndex, tmnxPortPortID, tPortAccIngQGrpName }
    ::= { tPortAccIngQGrpTable 1 }

TPortAccIngQGrpEntry ::= SEQUENCE
    {
        tPortAccIngQGrpName             TNamedItem,
        tPortAccIngQGrpRowStatus        RowStatus,
        tPortAccIngQGrpLastChgd         TimeStamp,
        tPortAccIngQGrpSchedPol         TNamedItemOrEmpty,
        tPortAccIngQGrpAcctgPolId       Unsigned32,
        tPortAccIngQGrpCollectStats     TruthValue,
        tPortAccIngQGrpDescr            TItemDescription
    }

tPortAccIngQGrpName OBJECT-TYPE
    SYNTAX       TNamedItem
    MAX-ACCESS   not-accessible
    STATUS       current
    DESCRIPTION
        "The value of tPortAccIngQGrpName defines the port Ingress
        Queue Group name.  It uniquely identifies a port ingress queue group
        in the managed system."
    ::= { tPortAccIngQGrpEntry 1 }

tPortAccIngQGrpRowStatus OBJECT-TYPE
    SYNTAX       RowStatus
    MAX-ACCESS   read-create
    STATUS       current
    DESCRIPTION
        "The value of tPortAccIngQGrpRowStatus allows entries to be
        created and deleted in the tPortAccIngQGrpTable.

        The creation of an entry in this table will succeed only if the
        queue-group being created exists in
        TIMETRA-QOS-MIB::tQosIngQGroupTable."
    REFERENCE
        "See definition of RowStatus in RFC 2579, 'Textual Conventions for
         SMIv2.'"
    ::= { tPortAccIngQGrpEntry 2 }

tPortAccIngQGrpLastChgd OBJECT-TYPE
    SYNTAX       TimeStamp
    MAX-ACCESS   read-only
    STATUS       current
    DESCRIPTION
        "The value of tPortAccIngQGrpLastChgd indicates the value of
        sysUpTime when the queue entry was last modified."
    ::= { tPortAccIngQGrpEntry 3 }

tPortAccIngQGrpSchedPol OBJECT-TYPE
    SYNTAX       TNamedItemOrEmpty
    MAX-ACCESS   read-create
    STATUS       current
    DESCRIPTION
        "The value of tPortAccIngQGrpSchedPol specifies the name of
        the scheduler-policy to be used with this port ingress queue-group."
    DEFVAL { ''H }
    ::= { tPortAccIngQGrpEntry 4 }

tPortAccIngQGrpAcctgPolId OBJECT-TYPE
    SYNTAX       Unsigned32 (0..99)
    MAX-ACCESS   read-create
    STATUS       current
    DESCRIPTION
        "The value of tPortAccIngQGrpAcctgPolId specifies the accounting-policy
        to be used with this port ingress queue-group.

        A non-zero value indicates the tmnxLogApPolicyId index identifying the
        policy entry in the tmnxLogApTable from the TIMETRA-LOG-MIB which is
        associated with this queue-group.

        The value zero indicates that the agent should use the default
        accounting policy, if one exists."
    DEFVAL { 0 }
    ::= { tPortAccIngQGrpEntry 5 }

tPortAccIngQGrpCollectStats OBJECT-TYPE
    SYNTAX       TruthValue
    MAX-ACCESS   read-create
    STATUS       current
    DESCRIPTION
        "The value of tPortAccIngQGrpCollectStats specifies whether
        statistics should be collected on this port ingress queue-group."
    DEFVAL { false }
    ::= { tPortAccIngQGrpEntry 6 }

tPortAccIngQGrpDescr OBJECT-TYPE
    SYNTAX       TItemDescription
    MAX-ACCESS   read-create
    STATUS       current
    DESCRIPTION
        "The value of tPortAccIngQGrpDescr specifies the description for
        this port queue-group."
    DEFVAL { ''H }
    ::= { tPortAccIngQGrpEntry 7 }


--
--      Port queue policy overrides
--

tPortAccIngQOverTableLastChgd OBJECT-TYPE
    SYNTAX       TimeStamp
    MAX-ACCESS   read-only
    STATUS       current
    DESCRIPTION
        "The value of tPortAccIngQOverTableLastChgd indicates the
        timestamp of last change to the tPortAccIngQOverTable."
    ::= { tmnxPortObjs 34 }

tPortAccIngQOverTable OBJECT-TYPE
    SYNTAX      SEQUENCE OF TPortAccIngQOverEntry
    MAX-ACCESS  not-accessible
    STATUS      current
    DESCRIPTION
        "The tPortAccIngQOverTable has an entry for each access port queue
        override configured on this system."
    ::= { tmnxPortObjs 35 }

tPortAccIngQOverEntry    OBJECT-TYPE
    SYNTAX      TPortAccIngQOverEntry
    MAX-ACCESS  not-accessible
    STATUS      current
    DESCRIPTION
        "Each row represents a particular port-queue override. Entries are
        created and deleted by the user."
    INDEX { tmnxChassisIndex, tmnxPortPortID,
            tPortAccIngQGrpName, tPortAccIngQOverQueue }
    ::= { tPortAccIngQOverTable 1}

TPortAccIngQOverEntry ::= SEQUENCE
    {
        tPortAccIngQOverQueue              TIngressQueueId,
        tPortAccIngQOverRowStatus          RowStatus,
        tPortAccIngQOverLastChanged        TimeStamp,
        tPortAccIngQOverCBS                TBurstSizeOverride,
        tPortAccIngQOverMBS                TBurstSizeOverride,
        tPortAccIngQOverHiPrioOnly         TBurstPercentOrDefaultOverride,
        tPortAccIngQOverAdminPIR           TPIRRateOverride,
        tPortAccIngQOverAdminCIR           TCIRRateOverride,
        tPortAccIngQOverPIRAdaptation      TAdaptationRuleOverride,
        tPortAccIngQOverCIRAdaptation      TAdaptationRuleOverride,
        tPortAccIngQOverMBSBytes           TBurstSizeBytesOverride
    }

tPortAccIngQOverQueue OBJECT-TYPE
    SYNTAX       TIngressQueueId (1..32)
    MAX-ACCESS   not-accessible
    STATUS       current
    DESCRIPTION
        "The value of tPortAccIngQOverQueue specifies the queue ID
        which is used as the fourth index to the table entry."
    ::= { tPortAccIngQOverEntry 1 }

tPortAccIngQOverRowStatus        OBJECT-TYPE
    SYNTAX      RowStatus
    MAX-ACCESS  read-create
    STATUS      current
    DESCRIPTION
        "The value of tPortAccIngQOverRowStatus is used for the creation
        and deletion of port-queue overrides.

        Row creation will fail if there is no entry in the
        TIMETRA-QOS-MIB::tQosIngQueueTable with the same index values as the
        last two indices of this table
        (tPortAccIngQGrpName.tPortAccIngQOverQueue)."
    ::= { tPortAccIngQOverEntry 2 }

tPortAccIngQOverLastChanged        OBJECT-TYPE
    SYNTAX      TimeStamp
    MAX-ACCESS  read-only
    STATUS      current
    DESCRIPTION
        "The value of tPortAccIngQOverLastChanged indicates the value
        of sysUpTime at the time of the most recent management change to
        this row."
    ::= { tPortAccIngQOverEntry 3 }

tPortAccIngQOverCBS OBJECT-TYPE
    SYNTAX       TBurstSizeOverride
    UNITS        "kilo-bytes"
    MAX-ACCESS   read-create
    STATUS       current
    DESCRIPTION
        "The value of tPortAccIngQOverCBS specifies the amount of reserved
        buffer space for the queue."
    DEFVAL { -2 }
    ::= { tPortAccIngQOverEntry 4 }

tPortAccIngQOverMBS OBJECT-TYPE
    SYNTAX       TBurstSizeOverride
    UNITS        "kilo-bytes"
    MAX-ACCESS   read-create
    STATUS       obsolete
    DESCRIPTION
        "The value of tPortAccIngQOverMBS specifies the maximum amount of
        buffer space allowed for the queue.

        This object is replaced with tPortAccIngQOverMBSBytes object."
    DEFVAL { -2 }
    ::= { tPortAccIngQOverEntry 5 }

tPortAccIngQOverHiPrioOnly OBJECT-TYPE
    SYNTAX       TBurstPercentOrDefaultOverride
    MAX-ACCESS   read-create
    STATUS       current
    DESCRIPTION
        "The value of tPortAccIngQOverHiPrioOnly specifies the percentage of
        buffer space for the queue, used exclusively by high priority packets."
    DEFVAL { -2 }
    ::= { tPortAccIngQOverEntry 6 }

tPortAccIngQOverAdminPIR OBJECT-TYPE
    SYNTAX       TPIRRateOverride
    UNITS        "kbps"
    MAX-ACCESS   read-create
    STATUS       current
    DESCRIPTION
        "The value of tPortAccIngQOverAdminPIR specifies the administrative
        PIR specified by the user."
    DEFVAL { -2 }
    ::= { tPortAccIngQOverEntry 7 }

tPortAccIngQOverAdminCIR OBJECT-TYPE
    SYNTAX       TCIRRateOverride
    UNITS        "kbps"
    MAX-ACCESS   read-create
    STATUS       current
    DESCRIPTION
        "The value of tPortAccIngQOverAdminCIR specifies the administrative
        CIR specified by the user."
    DEFVAL { -2 }
    ::= { tPortAccIngQOverEntry 8 }

tPortAccIngQOverPIRAdaptation OBJECT-TYPE
    SYNTAX       TAdaptationRuleOverride
    MAX-ACCESS   read-create
    STATUS       current
    DESCRIPTION
        "The value of tPortAccIngQOverPIRAdaptation specifies the adaptation
         rule to be used while computing the operational PIR
         value. The adaptation rule specifies the rules to compute the
         operational values while maintaining minimum offset."
    DEFVAL { noOverride }
    ::= { tPortAccIngQOverEntry 9 }

tPortAccIngQOverCIRAdaptation OBJECT-TYPE
    SYNTAX       TAdaptationRuleOverride
    MAX-ACCESS   read-create
    STATUS       current
    DESCRIPTION
        "The value of tPortAccIngQOverCIRAdaptation specifies the adaptation
         rule to be used while computing the operational CIR
         value. The adaptation rule specifies the rules to compute the
         operational values while maintaining minimum offset."
    DEFVAL { noOverride }
    ::= { tPortAccIngQOverEntry 10 }

tPortAccIngQOverMBSBytes OBJECT-TYPE
    SYNTAX       TBurstSizeBytesOverride
    UNITS        "bytes"
    MAX-ACCESS   read-create
    STATUS       current
    DESCRIPTION
        "The value of tPortAccIngQOverMBSBytes specifies the maximum amount of
        buffer space allowed for the queue."
    DEFVAL { -2 }
    ::= { tPortAccIngQOverEntry 11 }

--
-- access egress queue group table
--

tPortAccEgrQGrpTableLastChgd OBJECT-TYPE
    SYNTAX       TimeStamp
    MAX-ACCESS   read-only
    STATUS       current
    DESCRIPTION
        "The value of tPortAccEgrQGrpTableLastChgd indicates the
        timestamp of last change to the tPortAccEgrQGrpTable."
    ::= { tmnxPortObjs 36 }

tPortAccEgrQGrpTable OBJECT-TYPE
    SYNTAX       SEQUENCE OF TPortAccEgrQGrpEntry
    MAX-ACCESS   not-accessible
    STATUS       current
    DESCRIPTION
        "The value of tPortAccEgrQGrpTable defines access Egress Queue Group
        Table for providing, via SNMP, the capability of defining the port
        specific queue groups from the queue-groups existing in the
        TIMETRA-QOS-MIB::tQosEgrQGroupTable."
    ::= { tmnxPortObjs 37 }

tPortAccEgrQGrpEntry OBJECT-TYPE
    SYNTAX       TPortAccEgrQGrpEntry
    MAX-ACCESS   not-accessible
    STATUS       current
    DESCRIPTION
        "The value of tPortAccEgrQGrpEntry defines an entry in the
        tPortAccEgrQGrpTable.

        Entries are created/deleted in this table by SNMP sets to
        tPortAccEgrQGrpRowStatus."
    INDEX { tmnxChassisIndex, tmnxPortPortID, tPortAccEgrQGrpName,
            tPortAccEgrQGrpInstanceId }
    ::= { tPortAccEgrQGrpTable 1 }

TPortAccEgrQGrpEntry ::= SEQUENCE
    {
        tPortAccEgrQGrpName                 TNamedItem,
        tPortAccEgrQGrpRowStatus            RowStatus,
        tPortAccEgrQGrpLastChgd             TimeStamp,
        tPortAccEgrQGrpSchedPol             TNamedItemOrEmpty,
        tPortAccEgrQGrpAggRateLimit         TPortSchedulerAggRateLimitPIR,
        tPortAccEgrQGrpAcctgPolId           Unsigned32,
        tPortAccEgrQGrpCollectStats         TruthValue,
        tPortAccEgrQGrpFrameBaseActg        TruthValue,
        tPortAccEgrQGrpDescr                TItemDescription,
        tPortAccEgrQGrpInstanceId           Unsigned32,
        tPortAccEgrQGrpHsmdaShaperOvr       TNamedItemOrEmpty,
        tPortAccEgrQGrpHsmdaPktOffOvr       TEgrHsmdaPerPacketOffsetOvr,
        tPortAccEgrQGrpHsmdaWrrPolicyOvr    TNamedItemOrEmpty,
        tPortAccEgrQGrpAggRateLUB           TruthValue
    }

tPortAccEgrQGrpName OBJECT-TYPE
    SYNTAX       TNamedItem
    MAX-ACCESS   not-accessible
    STATUS       current
    DESCRIPTION
        "The value of tPortAccEgrQGrpName defines the port Egress Queue
        Group name.  It, along with tPortAccEgrQGrpInstanceId, uniquely 
        identifies a port egress queue group in the managed system."
    ::= { tPortAccEgrQGrpEntry 1 }

tPortAccEgrQGrpRowStatus OBJECT-TYPE
    SYNTAX       RowStatus
    MAX-ACCESS   read-create
    STATUS       current
    DESCRIPTION
        "The value of tPortAccEgrQGrpRowStatus allows entries to be
        created and deleted in the tPortAccEgrQGrpTable.

        The creation of an entry in this table will succeed only if the
        queue-group being created exist in TIMETRA-QOS-MIB::tQosEgrQGroupTable."
    REFERENCE
        "See definition of RowStatus in RFC 2579, 'Textual Conventions for
         SMIv2.'"
    ::= { tPortAccEgrQGrpEntry 2 }

tPortAccEgrQGrpLastChgd OBJECT-TYPE
    SYNTAX       TimeStamp
    MAX-ACCESS   read-only
    STATUS       current
    DESCRIPTION
        "The value of tPortAccEgrQGrpLastChgd indicates the value of
        sysUpTime when the queue entry was last modified."
    ::= { tPortAccEgrQGrpEntry 3 }

tPortAccEgrQGrpSchedPol OBJECT-TYPE
    SYNTAX       TNamedItemOrEmpty
    MAX-ACCESS   read-create
    STATUS       current
    DESCRIPTION
        "The value of tPortAccEgrQGrpSchedPol specifies the name of the
        scheduler-policy to be used with this port egress queue-group."
    DEFVAL { ''H }
    ::= { tPortAccEgrQGrpEntry 4 }

tPortAccEgrQGrpAggRateLimit   OBJECT-TYPE
    SYNTAX          TPortSchedulerAggRateLimitPIR
    UNITS           "kbps"
    MAX-ACCESS      read-create
    STATUS          current
    DESCRIPTION
        "The value of tPortAccEgrQGrpAggRateLimit specifies the maximum
        total rate of all egress queues in this queue-group. The
        value '-1' means that there is no limit."
    DEFVAL          { -1 }
    ::= { tPortAccEgrQGrpEntry 5 }

tPortAccEgrQGrpAcctgPolId OBJECT-TYPE
    SYNTAX       Unsigned32 (0..99)
    MAX-ACCESS   read-create
    STATUS       current
    DESCRIPTION
        "The value of tPortAccEgrQGrpAcctgPolId specifies the accounting-policy
        to be used with this port egress queue-group.

        A non-zero value indicates the tmnxLogApPolicyId index identifying the
        policy entry in the tmnxLogApTable from the TIMETRA-LOG-MIB which is
        associated with this queue-group.

        The value zero indicates that the agent should use the default
        accounting policy, if one exists."
    DEFVAL { 0 }
    ::= { tPortAccEgrQGrpEntry 6 }

tPortAccEgrQGrpCollectStats OBJECT-TYPE
    SYNTAX       TruthValue
    MAX-ACCESS   read-create
    STATUS       current
    DESCRIPTION
        "The value of tPortAccEgrQGrpCollectStats specifies whether
        statistics should be collected on this port egress queue-group."
    DEFVAL { false }
    ::= { tPortAccEgrQGrpEntry 7 }

tPortAccEgrQGrpFrameBaseActg OBJECT-TYPE
    SYNTAX       TruthValue
    MAX-ACCESS   read-create
    STATUS       current
    DESCRIPTION
        "The value of tPortAccEgrQGrpFrameBaseActg specifies whether
         to use frame-based accounting for this port egress queue-group.

         If the value is 'false', the default packet-based accounting
         method will be used."
    DEFVAL { false }
    ::= { tPortAccEgrQGrpEntry 8 }

tPortAccEgrQGrpDescr OBJECT-TYPE
    SYNTAX       TItemDescription
    MAX-ACCESS   read-create
    STATUS       current
    DESCRIPTION
        "The value of tPortAccEgrQGrpDescr specifies the description for
        this port queue-group."
    DEFVAL { ''H }
    ::= { tPortAccEgrQGrpEntry 9 }

tPortAccEgrQGrpInstanceId OBJECT-TYPE
    SYNTAX       Unsigned32 (1..65535)  
    MAX-ACCESS   not-accessible
    STATUS       current
    DESCRIPTION
        "The value of tPortAccEgrQGrpInstanceId defines the unique instance of
        the port access egress Queue Group.  It, along with tPortAccEgrQGrpName, 
        uniquely identifies a port access egress queue group in the 
        managed system."
    ::= { tPortAccEgrQGrpEntry 10 }

tPortAccEgrQGrpHsmdaShaperOvr OBJECT-TYPE
    SYNTAX       TNamedItemOrEmpty
    MAX-ACCESS   read-create
    STATUS       current
    DESCRIPTION  
        "The value of tPortAccEgrQGrpHsmdaShaperOvr specifies the name of 
         the secondary shaper for this queue-group instance. This value must 
         correspond to an entry in the tmnxPortEgrShaperTable. If an empty 
         string is specified, default secondary shaper will be used."
    DEFVAL { ''H }
    ::= { tPortAccEgrQGrpEntry 11 }
 
tPortAccEgrQGrpHsmdaPktOffOvr OBJECT-TYPE
    SYNTAX       TEgrHsmdaPerPacketOffsetOvr
    UNITS        "bytes"
    MAX-ACCESS   read-create
    STATUS       current
    DESCRIPTION  
        "The value of tPortAccEgrQGrpHsmdaPktOffOvr specifies the adjustment
         made to the size of each packet for HSMDA queue accounting for this 
         queue-group instance."
    DEFVAL { -128 }
    ::= { tPortAccEgrQGrpEntry 12 }
 
tPortAccEgrQGrpHsmdaWrrPolicyOvr OBJECT-TYPE
    SYNTAX       TNamedItemOrEmpty
    MAX-ACCESS   read-create
    STATUS       current
    DESCRIPTION
        "The value of tPortAccEgrQGrpHsmdaWrrPolicyOvr specifies the egress
         hsmda weighted round-robin policy override for this queue group 
         instance. 
     
         When no policy is given, the hsmda weighted round-robin policy
         specified in the queue-group template is honored. When a valid policy
         is given, it overrides the hsmda weighted round-robin policy given in
         the egress queue group template."
    DEFVAL { ''H }
    ::= { tPortAccEgrQGrpEntry 13 }

tPortAccEgrQGrpAggRateLUB   OBJECT-TYPE
    SYNTAX      TruthValue
    MAX-ACCESS  read-create
    STATUS      current
    DESCRIPTION 
        "The value of tPortAccEgrQGrpAggRateLUB specifies whether to limit
         the unused bandwidth and allow a tighter control in allocation of 
         bandwidth by HQos.

         When the value of tPortAccEgrQGrpAggRateLUB is set to 'true', HQos
         algorithm distributes any unused aggregate bandwidth between queues
         operating below their fair share rates. This allows a simplified 
         aggregate rate protection while allocating bandwidth by HQos scheduling
         algorithm."
    DEFVAL { false }
    ::= { tPortAccEgrQGrpEntry 14 }

--
--      Port queue policy overrides
--

tPortAccEgrQOverTableLastChgd OBJECT-TYPE
    SYNTAX       TimeStamp
    MAX-ACCESS   read-only
    STATUS       current
    DESCRIPTION
        "The value of tPortAccEgrQOverTableLastChgd indicates the timestamp
        of last change to the tPortAccEgrQOverTable."
    ::= { tmnxPortObjs 38 }

tPortAccEgrQOverTable OBJECT-TYPE
    SYNTAX      SEQUENCE OF TPortAccEgrQOverEntry
    MAX-ACCESS  not-accessible
    STATUS      current
    DESCRIPTION
        "The tPortAccEgrQOverTable has an entry for each access port queue
        override configured on this system."
    ::= { tmnxPortObjs 39 }

tPortAccEgrQOverEntry    OBJECT-TYPE
    SYNTAX      TPortAccEgrQOverEntry
    MAX-ACCESS  not-accessible
    STATUS      current
    DESCRIPTION
        "Each row represents a particular port-queue override. Entries
        are created and deleted by the user."
    INDEX { tmnxChassisIndex, tmnxPortPortID,
            tPortAccEgrQGrpName, tPortAccEgrQGrpInstanceId,
            tPortAccEgrQOverQueue }
    ::= { tPortAccEgrQOverTable 1}

TPortAccEgrQOverEntry ::= SEQUENCE
    {
        tPortAccEgrQOverQueue              TEgressQueueId,
        tPortAccEgrQOverRowStatus          RowStatus,
        tPortAccEgrQOverLastChanged        TimeStamp,
        tPortAccEgrQOverCBS                TBurstSizeOverride,
        tPortAccEgrQOverMBS                TBurstSizeOverride,
        tPortAccEgrQOverHiPrioOnly         TBurstPercentOrDefaultOverride,
        tPortAccEgrQOverAdminPIR           TPIRRateOverride,
        tPortAccEgrQOverAdminCIR           TCIRRateOverride,
        tPortAccEgrQOverPIRAdaptation      TAdaptationRuleOverride,
        tPortAccEgrQOverCIRAdaptation      TAdaptationRuleOverride,
        tPortAccEgrQOverMBSBytes           TBurstSizeBytesOverride,
        tPortAccEgrQOverAdminPIRPercent    TPIRPercentOverride,
        tPortAccEgrQOverAdminCIRPercent    TCIRPercentOverride,
        tPortAccEgrQOverRateType           TRateType,
        tPortAccEgrQOverWeight             TWeightOverride,
        tPortAccEgrQOverCIRWeight          TWeightOverride
    }

tPortAccEgrQOverQueue OBJECT-TYPE
    SYNTAX       TEgressQueueId (1..8)
    MAX-ACCESS   not-accessible
    STATUS       current
    DESCRIPTION
        "The value of tPortAccEgrQOverQueue specifies the queue ID which is
        used as the fourth index to the table entry."
    ::= { tPortAccEgrQOverEntry 1 }

tPortAccEgrQOverRowStatus  OBJECT-TYPE
    SYNTAX      RowStatus
    MAX-ACCESS  read-create
    STATUS      current
    DESCRIPTION
        "The value of tPortAccEgrQOverRowStatus is used for the
         creation and deletion of port-queue overrides.

        Row creation will fail if there is no entry in the
        TIMETRA-QOS-MIB::tQosEgrQueueTable with the same index values as the
        last two indices of this table
        (tPortAccEgrQGrpName.tPortAccEgrQOverQueue)."
    ::= { tPortAccEgrQOverEntry 2 }

tPortAccEgrQOverLastChanged  OBJECT-TYPE
    SYNTAX      TimeStamp
    MAX-ACCESS  read-only
    STATUS      current
    DESCRIPTION
        "The value of tPortAccEgrQOverLastChanged indicates the value
        of sysUpTime at the time of the most recent management change to
        this row."
    ::= { tPortAccEgrQOverEntry 3 }

tPortAccEgrQOverCBS OBJECT-TYPE
    SYNTAX       TBurstSizeOverride
    UNITS        "kilo-bytes"
    MAX-ACCESS   read-create
    STATUS       current
    DESCRIPTION
        "The value of tPortAccEgrQOverCBS specifies the amount of reserved
        buffer space for the queue."
    DEFVAL { -2 }
    ::= { tPortAccEgrQOverEntry 4 }

tPortAccEgrQOverMBS OBJECT-TYPE
    SYNTAX       TBurstSizeOverride
    UNITS        "kilo-bytes"
    MAX-ACCESS   read-create
    STATUS       obsolete
    DESCRIPTION
        "The value of tPortAccEgrQOverMBS specifies the maximum amount of
        buffer space allowed for the queue.

        This object is replaced with tPortAccEgrQOverMBSBytes object."
    DEFVAL { -2 }
    ::= { tPortAccEgrQOverEntry 5 }

tPortAccEgrQOverHiPrioOnly OBJECT-TYPE
    SYNTAX       TBurstPercentOrDefaultOverride
    MAX-ACCESS   read-create
    STATUS       current
    DESCRIPTION
        "The value of tPortAccEgrQOverHiPrioOnly specifies the percentage of
        buffer space for the queue, used exclusively by high priority packets."
    DEFVAL { -2 }
    ::= { tPortAccEgrQOverEntry 6 }

tPortAccEgrQOverAdminPIR OBJECT-TYPE
    SYNTAX       TPIRRateOverride
    UNITS        "kbps"
    MAX-ACCESS   read-create
    STATUS       current
    DESCRIPTION
        "The value of tPortAccEgrQOverAdminPIR specifies the administrative
        PIR specified by the user.

        An 'inconsistentValue' error is returned if tPortAccEgrQOverAdminPIR  
        is set to non-default value when the object tPortAccEgrQOverRateType is
        set to 'percent'."
    DEFVAL { -2 }
    ::= { tPortAccEgrQOverEntry 7 }

tPortAccEgrQOverAdminCIR OBJECT-TYPE
    SYNTAX       TCIRRateOverride
    UNITS        "kbps"
    MAX-ACCESS   read-create
    STATUS       current
    DESCRIPTION
        "The value of tPortAccEgrQOverAdminCIR specifies the administrative
        CIR specified by the user.

        An 'inconsistentValue' error is returned if tPortAccEgrQOverAdminCIR  
        is set to non-default value when the object tPortAccEgrQOverRateType is
        set to 'percent'."
    DEFVAL { -2 }
    ::= { tPortAccEgrQOverEntry 8 }

tPortAccEgrQOverPIRAdaptation OBJECT-TYPE
    SYNTAX       TAdaptationRuleOverride
    MAX-ACCESS   read-create
    STATUS       current
    DESCRIPTION
        "The value of tPortAccEgrQOverPIRAdaptation specifies the adaptation
         rule to be used while computing the operational PIR
         value. The adaptation rule specifies the rules to compute the
         operational values while maintaining minimum offset."
    DEFVAL { noOverride }
    ::= { tPortAccEgrQOverEntry 9 }

tPortAccEgrQOverCIRAdaptation OBJECT-TYPE
    SYNTAX       TAdaptationRuleOverride
    MAX-ACCESS   read-create
    STATUS       current
    DESCRIPTION
        "The value of tPortAccEgrQOverCIRAdaptation specifies the adaptation
         rule to be used while computing the operational CIR
         value. The adaptation rule specifies the rules to compute the
         operational values while maintaining minimum offset."
    DEFVAL { noOverride }
    ::= { tPortAccEgrQOverEntry 10 }

tPortAccEgrQOverMBSBytes OBJECT-TYPE
    SYNTAX       TBurstSizeBytesOverride
    UNITS        "bytes"
    MAX-ACCESS   read-create
    STATUS       current
    DESCRIPTION
        "The value of tPortAccEgrQOverMBSBytes specifies the maximum amount of
        buffer space allowed for the queue."
    DEFVAL { -2 }
    ::= { tPortAccEgrQOverEntry 11 }

tPortAccEgrQOverAdminPIRPercent OBJECT-TYPE
    SYNTAX      TPIRPercentOverride
    UNITS       "hundredths of a percent"
    MAX-ACCESS  read-create
    STATUS      current
    DESCRIPTION
        "The value of tPortAccEgrQOverAdminPIRPercent specifies the administrative
         PIR percentage, in hudredths of a percent.

         An 'inconsistentValue' error is returned if tPortAccEgrQOverAdminPIRPercent  
         is set to non-default value when the object tPortAccEgrQOverRateType is set 
         to 'kbps'."

    DEFVAL { -2 }
    ::= { tPortAccEgrQOverEntry 12 }

tPortAccEgrQOverAdminCIRPercent OBJECT-TYPE
    SYNTAX      TCIRPercentOverride
    UNITS       "hundredths of a percent"
    MAX-ACCESS  read-create
    STATUS      current
    DESCRIPTION
        "The value of tPortAccEgrQOverAdminCIRPercent specifies the administrative
         CIR percentage, in hudredths of a percent.

         An 'inconsistentValue' error is returned if tPortAccEgrQOverAdminCIRPercent  
         is set to non-default value when the object tPortAccEgrQOverRateType is set 
         to 'kbps'."
    DEFVAL { -2 }
    ::= { tPortAccEgrQOverEntry 13 }

tPortAccEgrQOverRateType OBJECT-TYPE   
    SYNTAX      TRateType
    MAX-ACCESS  read-create
    STATUS      current
    DESCRIPTION
        "The value of tPortAccEgrQOverRateType specifies the type of Egress queue
         rate.
         
         When the value of the object is set to 'kbps', the egresss queue rates
         are specified in kbps. The objects  tPortAccEgrQOverAdminPIRPercent and
         tPortAccEgrQOverAdminCIRPercent will be set to their default values.

         When the value of the object is set to 'percent', the egress queue rates
         are specified in percentage. The objects tPortAccEgrQOverAdminPIR and 
         tPortAccEgrQOverAdminCIR will be set to their default values."
    DEFVAL { kbps }    
    ::= { tPortAccEgrQOverEntry 14 }

tPortAccEgrQOverWeight OBJECT-TYPE
    SYNTAX       TWeightOverride
    MAX-ACCESS   read-create
    STATUS       current
    DESCRIPTION
        "The value of tPortAccEgrQOverWeight specifies the weight that needs 
         to be used by the scheduler to which this queue would be feeding."
    DEFVAL { -2 }
    ::= { tPortAccEgrQOverEntry 15 }
 
tPortAccEgrQOverCIRWeight OBJECT-TYPE
    SYNTAX       TWeightOverride
    MAX-ACCESS   read-create
    STATUS       current
    DESCRIPTION
        "The value of tPortAccEgrQOverCIRWeight specifies the weight that 
         should be assigned to this queue by the parent scheduler among all the
         entities feeding into the parent, when the traffic is conforming to the 
         committed rate.
        
         A value of '0' specifies that the queue will not receive bandwidth for
         the 'within-cir' pass on its parent scheduler."
    DEFVAL { -2 }
    ::= { tPortAccEgrQOverEntry 16 }

--
-- HSMDA Port queue policy overrides
--

tPortAccEgrHsmdaQOverTable OBJECT-TYPE
    SYNTAX       SEQUENCE OF TPortAccEgrHsmdaQOverEntry
    MAX-ACCESS   not-accessible
    STATUS       current
    DESCRIPTION
        "The tPortAccEgrHsmdaQOverTable has an entry for each access egress port
         queue-group hsmda queue override configured on this system."
    ::= { tmnxPortObjs 76 }
 
tPortAccEgrHsmdaQOverEntry OBJECT-TYPE
    SYNTAX       TPortAccEgrHsmdaQOverEntry
    MAX-ACCESS   not-accessible
    STATUS       current
    DESCRIPTION
        "Each row represents a particular port queue-group hsmda queue override.
         Entries are created and deleted by the user."
    INDEX { tmnxChassisIndex, tmnxPortPortID, tPortAccEgrQGrpName, 
            tPortAccEgrQGrpInstanceId, tPortAccEgrHsmdaQOverQueue }
    ::= { tPortAccEgrHsmdaQOverTable 1}
 
TPortAccEgrHsmdaQOverEntry ::= SEQUENCE
    {
        tPortAccEgrHsmdaQOverQueue           TEgressHsmdaQueueId,
        tPortAccEgrHsmdaQOverRowStatus       RowStatus,
        tPortAccEgrHsmdaQOverLastChanged     TimeStamp,
        tPortAccEgrHsmdaQOverAdminPIR        THsmdaPIRKRateOverride,
        tPortAccEgrHsmdaQOverSlopePolicy     TNamedItemOrEmpty,
        tPortAccEgrHsmdaQOverWrrWeight       THsmdaWrrWeightOverride,
        tPortAccEgrHsmdaQOverMBS             THSMDABurstSizeBytesOverride
    }
 
tPortAccEgrHsmdaQOverQueue OBJECT-TYPE
    SYNTAX       TEgressHsmdaQueueId
    MAX-ACCESS   not-accessible
    STATUS       current
    DESCRIPTION
         "The value of tPortAccEgrHsmdaQOverQueue specifies the hsmda egress
          queue which this override record will affect."
    ::= { tPortAccEgrHsmdaQOverEntry 1 }
 
tPortAccEgrHsmdaQOverRowStatus OBJECT-TYPE
    SYNTAX       RowStatus
    MAX-ACCESS   read-create
    STATUS       current
    DESCRIPTION
        "The value of tPortAccEgrHsmdaQOverRowStatus controls the creation and
         deletion of rows in this table."
    ::= { tPortAccEgrHsmdaQOverEntry 2 }
 
tPortAccEgrHsmdaQOverLastChanged OBJECT-TYPE
    SYNTAX       TimeStamp
    MAX-ACCESS   read-only
    STATUS       current
    DESCRIPTION
        "The value of tPortAccEgrHsmdaQOverLastChanged indicates the sysUpTime
         at the time of the most recent management-initiated change to this
         table row."
    ::= { tPortAccEgrHsmdaQOverEntry 3 }
 
tPortAccEgrHsmdaQOverAdminPIR OBJECT-TYPE
    SYNTAX       THsmdaPIRKRateOverride
    UNITS        "kbps"
    MAX-ACCESS   read-create
    STATUS       current
    DESCRIPTION
        "The value of tPortAccEgrHsmdaQOverAdminPIR specifies the PIR rate
         allowed for this hsmda egress queue-group queue."
    DEFVAL { -2 }
    ::= { tPortAccEgrHsmdaQOverEntry 4 }
 
tPortAccEgrHsmdaQOverSlopePolicy OBJECT-TYPE
    SYNTAX       TNamedItemOrEmpty
    MAX-ACCESS   read-create
    STATUS       current
    DESCRIPTION
        "The value of tPortAccEgrHsmdaQOverSlopePolicy specifies the slope
         policy that defines the RED slopes for this hsmda egress queue-group
         queue."
    DEFVAL { ''H }
    ::= { tPortAccEgrHsmdaQOverEntry 5 }
 
tPortAccEgrHsmdaQOverWrrWeight OBJECT-TYPE
    SYNTAX       THsmdaWrrWeightOverride
    MAX-ACCESS   read-create
    STATUS       current
    DESCRIPTION
        "The value of tPortAccEgrHsmdaQOverWrrWeight specifies the weighted 
         round-robin weight override for the given hsmda queue for this
         queue-group instance.
 
         When set to default value, the weighted round-robin weight is not 
         overridden and the weighted round-robin weight from the queue-group
         template is honored.  When a non-default value is given, that value is
         used instead of the weighted round-robin weight given in the
         queue-group template."
    DEFVAL { -2 }
    ::= { tPortAccEgrHsmdaQOverEntry 6 }
 
tPortAccEgrHsmdaQOverMBS OBJECT-TYPE
    SYNTAX       THSMDABurstSizeBytesOverride
    UNITS        "bytes"
    MAX-ACCESS   read-create
    STATUS       current
    DESCRIPTION
        "The value of tPortAccEgrHsmdaQOverMBS specifies the maximum buffer
         space (MBS) override for the given egress hsmda queue for this
         queue-group instance. 
        
         When set to default value, the MBS is not overridden and the MBS from 
         the queue-group template is honored. When a non-default value is given,
         that is used instead of the MBS given in the queue-group template."
    DEFVAL { -2 }
    ::= { tPortAccEgrHsmdaQOverEntry 7 }

--
-- network egress queue group table
--

tPortNetEgrQGrpTableLastChgd OBJECT-TYPE
    SYNTAX       TimeStamp
    MAX-ACCESS   read-only
    STATUS       current
    DESCRIPTION
        "The value of tPortNetEgrQGrpTableLastChgd indicates the
        timestamp of last change to the tPortNetEgrQGrpTable."
    ::= { tmnxPortObjs 40 }

tPortNetEgrQGrpTable OBJECT-TYPE
    SYNTAX       SEQUENCE OF TPortNetEgrQGrpEntry
    MAX-ACCESS   not-accessible
    STATUS       current
    DESCRIPTION
        "The value of tPortNetEgrQGrpTable defines network Egress Queue Group
        Table for providing, via SNMP, the capability of defining the port
        specific queue groups from the queue-groups existing in the
        TIMETRA-QOS-MIB::tQosEgrQGroupTable."
    ::= { tmnxPortObjs 41 }

tPortNetEgrQGrpEntry OBJECT-TYPE
    SYNTAX       TPortNetEgrQGrpEntry
    MAX-ACCESS   not-accessible
    STATUS       current
    DESCRIPTION
        "The value of tPortNetEgrQGrpEntry defines an entry in the
        tPortNetEgrQGrpTable.

        Entries are created/deleted in this table by SNMP sets to
        tPortNetEgrQGrpRowStatus."
    INDEX { tmnxChassisIndex, tmnxPortPortID, tPortNetEgrQGrpName, 
            tPortNetEgrQGrpInstanceId }
    ::= { tPortNetEgrQGrpTable 1 }

TPortNetEgrQGrpEntry ::= SEQUENCE
    {
        tPortNetEgrQGrpName             TNamedItem,        
        tPortNetEgrQGrpRowStatus        RowStatus,
        tPortNetEgrQGrpLastChgd         TimeStamp,
        tPortNetEgrQGrpSchedPol         TNamedItemOrEmpty,
        tPortNetEgrQGrpAggRateLimit     TPortSchedulerAggRateLimitPIR,
        tPortNetEgrQGrpAcctgPolId       Unsigned32,
        tPortNetEgrQGrpCollectStats     TruthValue,
        tPortNetEgrQGrpFrameBaseActg    TruthValue,
        tPortNetEgrQGrpDescr            TItemDescription,
        tPortNetEgrQGrpPlcrCntrlPolicy  TNamedItemOrEmpty,
        tPortNetEgrQGrpInstanceId       Unsigned32,
        tPortNetEgrQGrpAggRateLUB       TruthValue
    }

tPortNetEgrQGrpName OBJECT-TYPE
    SYNTAX       TNamedItem
    MAX-ACCESS   not-accessible
    STATUS       current
    DESCRIPTION
        "The value of tPortNetEgrQGrpName defines the port Egress Queue
        Group name.  It, along with tPortNetEgrQGrpInstanceId uniquely 
        identifies a port egress queue group in the managed system."
    ::= { tPortNetEgrQGrpEntry 1 }

tPortNetEgrQGrpRowStatus OBJECT-TYPE
    SYNTAX       RowStatus
    MAX-ACCESS   read-create
    STATUS       current
    DESCRIPTION
        "The value of tPortNetEgrQGrpRowStatus allows entries to be
        created and deleted in the tPortNetEgrQGrpTable.

        The creation of an entry in this table will succeed only if the
        queue-group being created exist in TIMETRA-QOS-MIB::tQosEgrQGroupTable."
    REFERENCE
        "See definition of RowStatus in RFC 2579, 'Textual Conventions for
         SMIv2.'"
    ::= { tPortNetEgrQGrpEntry 2 }

tPortNetEgrQGrpLastChgd OBJECT-TYPE
    SYNTAX       TimeStamp
    MAX-ACCESS   read-only
    STATUS       current
    DESCRIPTION
        "The value of tPortNetEgrQGrpLastChgd indicates the value of
        sysUpTime when the queue entry was last modified."
    ::= { tPortNetEgrQGrpEntry 3 }

tPortNetEgrQGrpSchedPol OBJECT-TYPE
    SYNTAX       TNamedItemOrEmpty
    MAX-ACCESS   read-create
    STATUS       current
    DESCRIPTION
        "The value of tPortNetEgrQGrpSchedPol specifies the name of the
        scheduler-policy to be used with this port egress queue-group."
    DEFVAL { ''H }
    ::= { tPortNetEgrQGrpEntry 4 }

tPortNetEgrQGrpAggRateLimit   OBJECT-TYPE
    SYNTAX          TPortSchedulerAggRateLimitPIR
    UNITS           "kbps"
    MAX-ACCESS      read-create
    STATUS          current
    DESCRIPTION
        "The value of tPortNetEgrQGrpAggRateLimit specifies the maximum
        total rate of all egress queues in this queue-group. The
        value '-1' means that there is no limit."
    DEFVAL          { -1 }
    ::= { tPortNetEgrQGrpEntry 5 }

tPortNetEgrQGrpAcctgPolId OBJECT-TYPE
    SYNTAX       Unsigned32 (0..99)
    MAX-ACCESS   read-create
    STATUS       current
    DESCRIPTION
        "The value of tPortNetEgrQGrpAcctgPolId specifies the accounting-policy
        to be used with this port egress queue-group.

        A non-zero value indicates the tmnxLogApPolicyId index identifying the
        policy entry in the tmnxLogApTable from the TIMETRA-LOG-MIB which is
        associated with this queue-group.

        The value zero indicates that the agent should use the default
        accounting policy, if one exists."
    DEFVAL { 0 }
    ::= { tPortNetEgrQGrpEntry 6 }

tPortNetEgrQGrpCollectStats OBJECT-TYPE
    SYNTAX       TruthValue
    MAX-ACCESS   read-create
    STATUS       current
    DESCRIPTION
        "The value of tPortNetEgrQGrpCollectStats specifies whether
        statistics should be collected on this port egress queue-group."
    DEFVAL { false }
    ::= { tPortNetEgrQGrpEntry 7 }

tPortNetEgrQGrpFrameBaseActg    OBJECT-TYPE
    SYNTAX       TruthValue
    MAX-ACCESS   read-create
    STATUS       current
    DESCRIPTION
        "The value of tPortNetEgrQGrpFrameBaseActg specifies whether
         to use frame-based accounting for this port egress queue-group.

         If the value is 'false', the default packet-based accounting
         method will be used."
    DEFVAL { false }
    ::= { tPortNetEgrQGrpEntry 8 }

tPortNetEgrQGrpDescr OBJECT-TYPE
    SYNTAX       TItemDescription
    MAX-ACCESS   read-create
    STATUS       current
    DESCRIPTION
        "The value of tPortNetEgrQGrpDescr specifies the description for
        this port queue-group."
    DEFVAL { ''H }
    ::= { tPortNetEgrQGrpEntry 9 }

tPortNetEgrQGrpPlcrCntrlPolicy OBJECT-TYPE
    SYNTAX       TNamedItemOrEmpty
    MAX-ACCESS   read-create
    STATUS       current
    DESCRIPTION
        "The value of tPortNetEgrQGrpPlcrCntrlPolicy specifies the network
        egress policer control policy applicable to this port egress
        queue-group."
    DEFVAL { ''H }
    ::= { tPortNetEgrQGrpEntry 10 }

tPortNetEgrQGrpInstanceId OBJECT-TYPE
    SYNTAX       Unsigned32 (1..65535)  
    MAX-ACCESS   not-accessible
    STATUS       current
    DESCRIPTION
        "The value of tPortNetEgrQGrpInstanceId defines the unique instance of
        the port Egress Queue Group.  It, along with tPortNetEgrQGrpName, 
        uniquely identifies a port egress queue group in the managed system."
    ::= { tPortNetEgrQGrpEntry 11 }

tPortNetEgrQGrpAggRateLUB   OBJECT-TYPE
    SYNTAX      TruthValue
    MAX-ACCESS  read-create
    STATUS      current
    DESCRIPTION 
        "The value of tPortNetEgrQGrpAggRateLUB specifies whether to limit
         the unused bandwidth and allow a tighter control in allocation of 
         bandwidth by HQos.

         When the value of tPortNetEgrQGrpAggRateLUB is set to 'true', HQos
         algorithm distributes any unused aggregate bandwidth between queues
         operating below their fair share rates. This allows a simplified 
         aggregate rate protection while allocating bandwidth by HQos scheduling
         algorithm."
    DEFVAL { false }
    ::= { tPortNetEgrQGrpEntry 12 }
    
--
--  network port queue policy overrides
--

tPortNetEgrQOverTableLastChgd OBJECT-TYPE
    SYNTAX       TimeStamp
    MAX-ACCESS   read-only
    STATUS       current
    DESCRIPTION
        "The value of tPortNetEgrQOverTableLastChgd indicates the timestamp
        of last change to the tPortNetEgrQOverTable."
    ::= { tmnxPortObjs 42 }

tPortNetEgrQOverTable OBJECT-TYPE
    SYNTAX      SEQUENCE OF TPortNetEgrQOverEntry
    MAX-ACCESS  not-accessible
    STATUS      current
    DESCRIPTION
        "The tPortNetEgrQOverTable has an entry for each port queue override
        configured on this system."
    ::= { tmnxPortObjs 43 }

tPortNetEgrQOverEntry    OBJECT-TYPE
    SYNTAX      TPortNetEgrQOverEntry
    MAX-ACCESS  not-accessible
    STATUS      current
    DESCRIPTION
        "Each row represents a particular port-queue override. Entries
        are created and deleted by the user."
    INDEX { tmnxChassisIndex, tmnxPortPortID,
            tPortNetEgrQGrpName, tPortNetEgrQGrpInstanceId,
            tPortNetEgrQOverQueue }
    ::= { tPortNetEgrQOverTable 1}

TPortNetEgrQOverEntry ::= SEQUENCE
    {
        tPortNetEgrQOverQueue              TEgressQueueId,
        tPortNetEgrQOverRowStatus          RowStatus,
        tPortNetEgrQOverLastChanged        TimeStamp,
        tPortNetEgrQOverCBS                TBurstSizeOverride,
        tPortNetEgrQOverMBS                TBurstSizeOverride,
        tPortNetEgrQOverHiPrioOnly         TBurstPercentOrDefaultOverride,
        tPortNetEgrQOverAdminPIR           TPIRRateOverride,
        tPortNetEgrQOverAdminCIR           TCIRRateOverride,
        tPortNetEgrQOverPIRAdaptation      TAdaptationRuleOverride,
        tPortNetEgrQOverCIRAdaptation      TAdaptationRuleOverride,
        tPortNetEgrQOverMBSBytes           TBurstSizeBytesOverride,
        tPortNetEgrQOverAdminPIRPercent    TPIRPercentOverride,
        tPortNetEgrQOverAdminCIRPercent    TCIRPercentOverride,
        tPortNetEgrQOverRateType           TRateType
    }

tPortNetEgrQOverQueue OBJECT-TYPE
    SYNTAX       TEgressQueueId (1..8)
    MAX-ACCESS   not-accessible
    STATUS       current
    DESCRIPTION
        "The value of tPortNetEgrQOverQueue specifies the queue ID which is
        used as the fourth index to the table entry."
    ::= { tPortNetEgrQOverEntry 1 }

tPortNetEgrQOverRowStatus  OBJECT-TYPE
    SYNTAX      RowStatus
    MAX-ACCESS  read-create
    STATUS      current
    DESCRIPTION
        "The value of tPortNetEgrQOverRowStatus is used for the
         creation and deletion of port-queue overrides.

        Row creation will fail if there is no entry in the
        TIMETRA-QOS-MIB::tQosEgrQueueTable with the same index values as the
        last two indices of this table
        (tPortNetEgrQGrpName.tPortNetEgrQOverQueue)."
    ::= { tPortNetEgrQOverEntry 2 }

tPortNetEgrQOverLastChanged  OBJECT-TYPE
    SYNTAX      TimeStamp
    MAX-ACCESS  read-only
    STATUS      current
    DESCRIPTION
        "The value of tPortNetEgrQOverLastChanged indicates the value
        of sysUpTime at the time of the most recent management change to
        this row."
    ::= { tPortNetEgrQOverEntry 3 }

tPortNetEgrQOverCBS OBJECT-TYPE
    SYNTAX       TBurstSizeOverride
    UNITS        "kilo-bytes"
    MAX-ACCESS   read-create
    STATUS       current
    DESCRIPTION
        "The value of tPortNetEgrQOverCBS specifies the amount of reserved
        buffer space for the queue."
    DEFVAL { -2 }
    ::= { tPortNetEgrQOverEntry 4 }

tPortNetEgrQOverMBS OBJECT-TYPE
    SYNTAX       TBurstSizeOverride
    UNITS        "kilo-bytes"
    MAX-ACCESS   read-create
    STATUS       obsolete
    DESCRIPTION
        "The value of tPortNetEgrQOverMBS specifies the maximum amount of
        buffer space allowed for the queue.
        
        This object is replaced with tPortNetEgrQOverMBSBytes object."
    DEFVAL { -2 }
    ::= { tPortNetEgrQOverEntry 5 }

tPortNetEgrQOverHiPrioOnly OBJECT-TYPE
    SYNTAX       TBurstPercentOrDefaultOverride
    MAX-ACCESS   read-create
    STATUS       current
    DESCRIPTION
        "The value of tPortNetEgrQOverHiPrioOnly specifies the percentage of
        buffer space for the queue, used exclusively by high priority packets."
    DEFVAL { -2 }
    ::= { tPortNetEgrQOverEntry 6 }

tPortNetEgrQOverAdminPIR OBJECT-TYPE
    SYNTAX       TPIRRateOverride
    UNITS        "kbps"
    MAX-ACCESS   read-create
    STATUS       current
    DESCRIPTION
        "The value of tPortNetEgrQOverAdminPIR specifies the administrative
        PIR specified by the user.

        An 'inconsistentValue' error is returned if tPortNetEgrQOverAdminPIR  
        is set to non-default value when the object tPortNetEgrQOverRateType is
        set to 'percent'."
    DEFVAL { -2 }
    ::= { tPortNetEgrQOverEntry 7 }

tPortNetEgrQOverAdminCIR OBJECT-TYPE
    SYNTAX       TCIRRateOverride
    UNITS        "kbps"
    MAX-ACCESS   read-create
    STATUS       current
    DESCRIPTION
        "The value of tPortNetEgrQOverAdminCIR specifies the administrative
        CIR specified by the user.

        An 'inconsistentValue' error is returned if tPortNetEgrQOverAdminCIR  
        is set to non-default value when the object tPortNetEgrQOverRateType is 
        set to 'percent'."
    DEFVAL { -2 }
    ::= { tPortNetEgrQOverEntry 8 }

tPortNetEgrQOverPIRAdaptation OBJECT-TYPE
    SYNTAX       TAdaptationRuleOverride
    MAX-ACCESS   read-create
    STATUS       current
    DESCRIPTION
        "The value of tPortNetEgrQOverPIRAdaptation specifies the adaptation
         rule to be used while computing the operational PIR
         value. The adaptation rule specifies the rules to compute the
         operational values while maintaining minimum offset."
    DEFVAL { noOverride }
    ::= { tPortNetEgrQOverEntry 9 }

tPortNetEgrQOverCIRAdaptation OBJECT-TYPE
    SYNTAX       TAdaptationRuleOverride
    MAX-ACCESS   read-create
    STATUS       current
    DESCRIPTION
        "The value of tPortNetEgrQOverCIRAdaptation specifies the adaptation
         rule to be used while computing the operational CIR
         value. The adaptation rule specifies the rules to compute the
         operational values while maintaining minimum offset."
    DEFVAL { noOverride }
    ::= { tPortNetEgrQOverEntry 10 }

tPortNetEgrQOverMBSBytes OBJECT-TYPE
    SYNTAX       TBurstSizeBytesOverride
    UNITS        "bytes"
    MAX-ACCESS   read-create
    STATUS       current
    DESCRIPTION
        "The value of tPortNetEgrQOverMBSBytes specifies the maximum amount of
        buffer space allowed for the queue."
    DEFVAL { -2 }
    ::= { tPortNetEgrQOverEntry 11 }

tPortNetEgrQOverAdminPIRPercent OBJECT-TYPE
    SYNTAX      TPIRPercentOverride
    UNITS       "hundredths of a percent"
    MAX-ACCESS  read-create
    STATUS      current
    DESCRIPTION
        "The value of tPortNetEgrQOverAdminPIRPercent specifies the administrative
         PIR percentage, in hudredths of a percent.

         An 'inconsistentValue' error is returned if tPortNetEgrQOverAdminPIRPercent  
         is set to non-default value when the object tPortNetEgrQOverRateType is set 
         to 'kbps'."

    DEFVAL { -2 }
    ::= { tPortNetEgrQOverEntry 12 }

tPortNetEgrQOverAdminCIRPercent OBJECT-TYPE
    SYNTAX      TCIRPercentOverride
    UNITS       "hundredths of a percent"
    MAX-ACCESS  read-create
    STATUS      current
    DESCRIPTION
        "The value of tQosEgrQueueAdminCIRPercent specifies the administrative
         CIR percentage, in hudredths of a percent.

         An 'inconsistentValue' error is returned if tQosEgrQueueAdminCIRPercent  
         is set to non-default value when the object tPortNetEgrQOverRateType is set 
         to 'kbps'."
    DEFVAL { -2 }
    ::= { tPortNetEgrQOverEntry 13 }

tPortNetEgrQOverRateType OBJECT-TYPE   
    SYNTAX      TRateType
    MAX-ACCESS  read-create
    STATUS      current
    DESCRIPTION
        "The value of tPortNetEgrQOverRateType specifies the type of Egress queue
         rate.
         
         When the value of the object is set to 'kbps', the egresss queue rates
         are specified in kbps. The objects  tPortNetEgrQOverAdminPIRPercent and
         tPortNetEgrQOverAdminCIRPercent will be set to their default values.

         When the value of the object is set to 'percent', the egress queue rates
         are specified in percentage. The objects tPortNetEgrQOverAdminPIR and 
         tPortNetEgrQOverAdminCIR will be set to their default values."
    DEFVAL { kbps }    
    ::= { tPortNetEgrQOverEntry 14 }

--
--  Multi-Link Frame-Relay (MLFR) Bundle Table
--
--  Sparse Dependent Extension of the tmnxBundleTable.
--
--  The same indexes are used for both the base table tmnxBundleTable,
--  and the sparse dependent table, tmnxBundleMlfrTable.
--
--  This in effect extends the tmnxBundleTable with additional columns.
--  Rows are created in the tmnxBundleMlfrTable only for those entries
--  in the tmnxBundleTable for a value of 'mlfr' for the bundle type.
--
--  Deletion of a row in the tmnxBundleTable results in the
--  same fate for the row in the tmnxBundleMlfrTable.
--
tmnxBundleMlfrTable OBJECT-TYPE
    SYNTAX      SEQUENCE OF TmnxBundleMlfrEntry
    MAX-ACCESS  not-accessible
    STATUS      current
    DESCRIPTION
        "The tmnxBundleMlfrTable contains MLFR specific data."
    ::= { tmnxPortObjs 44 }

tmnxBundleMlfrEntry OBJECT-TYPE
    SYNTAX      TmnxBundleMlfrEntry
    MAX-ACCESS  not-accessible
    STATUS      current
    DESCRIPTION
        "Each row entry contains data on an MLFR Bundle."
    INDEX       { tmnxChassisIndex, tmnxBundleBundleID }
    ::= { tmnxBundleMlfrTable 1 }

TmnxBundleMlfrEntry ::=
    SEQUENCE {
        tmnxBundleMlfrBundleId           SnmpAdminString,
        tmnxBundleMlfrIngQoSProfId       TMcFrQoSProfileId,
        tmnxBundleMlfrEgrQoSProfId       TMcFrQoSProfileId,
        tmnxBundleMlfrHelloTimer         Unsigned32,
        tmnxBundleMlfrHelloRetryCount    Unsigned32,
        tmnxBundleMlfrAckTimer           Unsigned32,
        tmnxBundleMlfrLastChanged        TimeStamp
    }

tmnxBundleMlfrBundleId OBJECT-TYPE
    SYNTAX      SnmpAdminString (SIZE (0..49))
    MAX-ACCESS  read-create
    STATUS      current
    DESCRIPTION
        "The value of tmnxBundleMlfrBundleId is the Bundle Identifier
         sent with each Link Integrity Protocol message for each member
         of a tmnxBundleBundleID.

         The object tmnxPortAdminStatus must be set to 'outOfService' to
         change this value."
    DEFVAL { "" }
    ::= { tmnxBundleMlfrEntry 1 }

tmnxBundleMlfrIngQoSProfId OBJECT-TYPE
    SYNTAX      TMcFrQoSProfileId
    MAX-ACCESS  read-create
    STATUS      current
    DESCRIPTION
        "The value of tmnxBundleMlfrIngQoSProfId specifies the ingress
         QoS profile to be used for the incoming traffic over this MLFR
         bundle.

         The value of tmnxBundleMlfrIngQoSProfId of 0 indicates
         a default QoS profile is used as applicable to given hardware."
    DEFVAL { 0 }
    ::= { tmnxBundleMlfrEntry 4 }

tmnxBundleMlfrEgrQoSProfId OBJECT-TYPE
    SYNTAX      TMcFrQoSProfileId
    MAX-ACCESS  read-create
    STATUS      current
    DESCRIPTION
        "The value of tmnxBundleMlfrEgrQoSProfId specifies the egress
         QoS profile to be used for the outgoing traffic over this MLFR
         bundle.

         The value of tmnxBundleMlfrEgrQoSProfId of 0 indicates
         a default profile is used as applicable to given hardware."
    DEFVAL { 0 }
    ::= { tmnxBundleMlfrEntry 5 }

tmnxBundleMlfrHelloTimer OBJECT-TYPE
    SYNTAX      Unsigned32 (1..180)
    UNITS       "seconds"
    MAX-ACCESS  read-create
    STATUS      current
    DESCRIPTION
        "The value of tmnxBundleMlfrHelloTimer specifies the rate
         at which hello messages are sent across a member link."
    DEFVAL { 10 }
    ::= { tmnxBundleMlfrEntry 6 }

tmnxBundleMlfrHelloRetryCount OBJECT-TYPE
    SYNTAX      Unsigned32 (1..5)
    UNITS       "seconds"
    MAX-ACCESS  read-create
    STATUS      current
    DESCRIPTION
        "The value of tmnxBundleMlfrHelloTimer specifies the number
         of times to attempt to resend hello messages when the
         tmnxBundleMlfrAckTimer has expired before taking action."
    DEFVAL { 2 }
    ::= { tmnxBundleMlfrEntry 7 }

tmnxBundleMlfrAckTimer OBJECT-TYPE
    SYNTAX      Unsigned32 (1..10)
    UNITS       "seconds"
    MAX-ACCESS  read-create
    STATUS      current
    DESCRIPTION
        "The value of tmnxBundleMlfrAckTimer specifies the length
         of time to wait for acknowledgment of a hello message
         before declaring the hello message has not been received."
    DEFVAL { 4 }
    ::= { tmnxBundleMlfrEntry 8 }

tmnxBundleMlfrLastChanged    OBJECT-TYPE
    SYNTAX      TimeStamp
    MAX-ACCESS  read-only
    STATUS      current
    DESCRIPTION
        "The value of tmnxBundleMlfrLastChanged indicates the value
         of sysUpTime at the time of the most recent management change to
         this row."
    ::= { tmnxBundleMlfrEntry 9 }

--
--  FR Interface Table
--

tmnxFrIntfTable OBJECT-TYPE
    SYNTAX  SEQUENCE OF TmnxFrIntfEntry
    MAX-ACCESS  not-accessible
    STATUS      current
    DESCRIPTION
        "The tmnxFrIntfTable has an entry for each port/channel in the
         system that is configured for Frame Relay. It contains Frame Relay
         configuration parameters."
    ::= { tmnxFRObjs 2 }

tmnxFrIntfEntry       OBJECT-TYPE
    SYNTAX      TmnxFrIntfEntry
    MAX-ACCESS  not-accessible
    STATUS      current
    DESCRIPTION
        "The Parameters for a particular FR Interface. Entries cannot be
         created or deleted via SNMP SET operations.

         Entries will exist in this table when tmnxPortEncapType is set
         to frEncap."
    INDEX   { tmnxChassisIndex, tmnxPortPortID }
    ::= { tmnxFrIntfTable 1 }

TmnxFrIntfEntry ::=
    SEQUENCE {
        tmnxFrIntfFrf12Mode     TmnxEnabledDisabled,
        tmnxFrIntfLinkId        SnmpAdminString,
        tmnxFrIntfLastChanged   TimeStamp
    }

tmnxFrIntfFrf12Mode OBJECT-TYPE
    SYNTAX      TmnxEnabledDisabled
    MAX-ACCESS  read-create
    STATUS      current
    DESCRIPTION
        "The value of tmnxFrIntfFrf12Mode enables or disables the
         use of FRF12 headers. This cannot be set to 'enabled'
         for entries with a tmnxPortBundleNumber set or bundles with
         a tmnxBundleType of mlfr."
     DEFVAL { disabled }
    ::= { tmnxFrIntfEntry 1 }

tmnxFrIntfLinkId OBJECT-TYPE
    SYNTAX      SnmpAdminString (SIZE (0..49))
    MAX-ACCESS  read-create
    STATUS      current
    DESCRIPTION
        "The value of tmnxFrIntfLinkId is a Link Identifier
         that is used when this entry is added to a MLFR bundle."
    DEFVAL { "" }
    ::= { tmnxFrIntfEntry 2 }

tmnxFrIntfLastChanged OBJECT-TYPE
    SYNTAX      TimeStamp
    MAX-ACCESS  read-only
    STATUS      current
    DESCRIPTION
        "The value of tmnxFrIntfLastChanged indicates the value
         of sysUpTime at the time of the most recent management change to
         this row."
    ::= { tmnxFrIntfEntry 3 }

--
-- Frame Relay Fragmentation (FRF12) Interface Table
--
tmnxFrf12IntfTable   OBJECT-TYPE
    SYNTAX      SEQUENCE OF TmnxFrf12IntfEntry
    MAX-ACCESS  not-accessible
    STATUS      current
    DESCRIPTION
        "The tmnxFrf12IntfTable contains entries for a port/channel
         that has frf12 mode 'enabled'."
    ::= { tmnxFRObjs 3 }

tmnxFrf12IntfEntry       OBJECT-TYPE
    SYNTAX      TmnxFrf12IntfEntry
    MAX-ACCESS  not-accessible
    STATUS      current
    DESCRIPTION
        "Each row represents a particular frame-relay interface that has
         enabled frf12 on a port/channel.

         Each row in this table is added/removed when frf12 is enabled
         on a port/channel."
    INDEX { tmnxChassisIndex, tmnxPortPortID }
    ::= { tmnxFrf12IntfTable 1 }

TmnxFrf12IntfEntry ::=
    SEQUENCE {
        tmnxFrf12IntfFragmentThreshold     Unsigned32,
        tmnxFrf12IntfEgrQoSProfId          TMcFrQoSProfileId,
        tmnxFrf12IntfLastChanged           TimeStamp
    }

tmnxFrf12IntfFragmentThreshold    OBJECT-TYPE
    SYNTAX      Unsigned32(128..512)
    MAX-ACCESS  read-create
    STATUS      current
    DESCRIPTION
        "The value of tmnxFrf12IntfFragmentThreshold specifies the
         maximum length of a fragment to be transmitted.
         A value of 0 specifies no fragmentation."
    DEFVAL      { 128 }
    ::= { tmnxFrf12IntfEntry 1 }

tmnxFrf12IntfEgrQoSProfId    OBJECT-TYPE
    SYNTAX      TMcFrQoSProfileId
    MAX-ACCESS  read-create
    STATUS      current
    DESCRIPTION
        "The value of tmnxFrf12IntfEgrQoSProfId specifies the egress
         QoS profile to be used for the outgoing traffic over this frf12
         frame-relay interface.

         The value of tmnxFrf12IntfEgrQoSProfId of 0 indicates
         a default QoS profile is used as applicable to given hardware."
    DEFVAL      { 0 }
    ::= { tmnxFrf12IntfEntry 2 }

tmnxFrf12IntfLastChanged    OBJECT-TYPE
    SYNTAX      TimeStamp
    MAX-ACCESS  read-only
    STATUS      current
    DESCRIPTION
        "The value of tmnxFrf12IntfLastChanged indicates the value
         of sysUpTime at the time of the most recent management change to
         this row."
    ::= { tmnxFrf12IntfEntry 3 }

-- ----------------------------------------
-- Ingress QoS Queue port Statistics Table
-- ----------------------------------------
tmnxPortIngQosQStatTable OBJECT-TYPE
    SYNTAX          SEQUENCE OF TmnxPortIngQosQStatEntry
    MAX-ACCESS      not-accessible
    STATUS          current
    DESCRIPTION     "A table that contains ingress QoS queue-group queue
                     port statistics."
    ::= { tmnxPortObjs 45 }

tmnxPortIngQosQStatEntry OBJECT-TYPE
    SYNTAX          TmnxPortIngQosQStatEntry
    MAX-ACCESS      not-accessible
    STATUS          current
    DESCRIPTION     "Ingress statistics about a specific port's
                     QoS queue-group queue."
    INDEX { tmnxChassisIndex, tmnxPortPortID,
            tPortAccIngQGrpName, tmnxPortIngQosQStatQueueId }
    ::= { tmnxPortIngQosQStatTable 1 }

TmnxPortIngQosQStatEntry ::=
    SEQUENCE {
        tmnxPortIngQosQStatQueueId          TIngressQueueId,
        tmnxPortIngQosQStatOffHiPrioPkts    Counter64,
        tmnxPortIngQosQStatDpdHiPrioPkts    Counter64,
        tmnxPortIngQosQStatOffLoPrioPkts    Counter64,
        tmnxPortIngQosQStatDpdLoPrioPkts    Counter64,
        tmnxPortIngQosQStatOffHiPrioOcts    Counter64,
        tmnxPortIngQosQStatDpdHiPrioOcts    Counter64,
        tmnxPortIngQosQStatOffLoPrioOcts    Counter64,
        tmnxPortIngQosQStatDpdLoPrioOcts    Counter64,
        tmnxPortIngQosQStatFwdInProfPkts    Counter64,
        tmnxPortIngQosQStatFwdOutProfPkts   Counter64,
        tmnxPortIngQosQStatFwdInProfOcts    Counter64,
        tmnxPortIngQosQStatFwdOutProfOcts   Counter64,
        tmnxPortIngQosQStatUncolPktsOff     Counter64,
        tmnxPortIngQosQStatUncolOctsOff     Counter64
    }

tmnxPortIngQosQStatQueueId OBJECT-TYPE
    SYNTAX       TIngressQueueId (1..32)
    MAX-ACCESS   not-accessible
    STATUS       current
    DESCRIPTION
        "The value of tmnxPortIngQosQStatQueueId specifies the queue-group
        queue ID which is used as the fourth index to the table entry."
    ::= { tmnxPortIngQosQStatEntry 1 }

tmnxPortIngQosQStatOffHiPrioPkts OBJECT-TYPE
    SYNTAX          Counter64
    MAX-ACCESS      read-only
    STATUS          current
    DESCRIPTION
       "The value of tmnxPortIngQosQStatOffHiPrioPkts indicates the number of
       high priority packets, as determined by the port ingress QoS
       policy, offered by the Pchip to the Qchip."
    ::= { tmnxPortIngQosQStatEntry 2 }

tmnxPortIngQosQStatDpdHiPrioPkts OBJECT-TYPE
    SYNTAX          Counter64
    MAX-ACCESS      read-only
    STATUS          current
    DESCRIPTION
        "The value of tmnxPortIngQosQStatDpdHiPrioPkts indicates the number of
        high priority packets, as determined by the port ingress QoS
        policy, dropped by the Qchip due to: MBS exceeded, buffer pool limit
        exceeded, etc."
    ::= { tmnxPortIngQosQStatEntry 3 }

tmnxPortIngQosQStatOffLoPrioPkts OBJECT-TYPE
    SYNTAX          Counter64
    MAX-ACCESS      read-only
    STATUS          current
    DESCRIPTION
        "The value of tmnxPortIngQosQStatOffLoPrioPkts indicates the number of
        low priority packets, as determined by the port ingress QoS
        policy, offered by the Pchip to the Qchip."
    ::= { tmnxPortIngQosQStatEntry 4 }

tmnxPortIngQosQStatDpdLoPrioPkts OBJECT-TYPE
    SYNTAX          Counter64
    MAX-ACCESS      read-only
    STATUS          current
    DESCRIPTION
        "The value of tmnxPortIngQosQStatDpdLoPrioPkts indicates the number of
        low priority packets, as determined by the port ingress QoS
        policy, dropped by the Qchip due to: MBS exceeded, buffer pool limit
        exceeded, etc."
    ::= { tmnxPortIngQosQStatEntry 5 }

tmnxPortIngQosQStatOffHiPrioOcts OBJECT-TYPE
    SYNTAX          Counter64
    MAX-ACCESS      read-only
    STATUS          current
    DESCRIPTION
        "The value of tmnxPortIngQosQStatOffHiPrioOcts indicates the number of
        high priority octets, as determined by the port ingress QoS
        policy, offered by the Pchip to the Qchip."
    ::= { tmnxPortIngQosQStatEntry 6 }

tmnxPortIngQosQStatDpdHiPrioOcts OBJECT-TYPE
    SYNTAX          Counter64
    MAX-ACCESS      read-only
    STATUS          current
    DESCRIPTION
        "The value of tmnxPortIngQosQStatDpdHiPrioOcts indicates the number of
        high priority octets, as determined by the port ingress QoS
        policy, dropped by the Qchip due to: MBS exceeded, buffer pool limit
        exceeded, etc."
    ::= { tmnxPortIngQosQStatEntry 7 }

tmnxPortIngQosQStatOffLoPrioOcts OBJECT-TYPE
    SYNTAX          Counter64
    MAX-ACCESS      read-only
    STATUS          current
    DESCRIPTION
        "The value of tmnxPortIngQosQStatOffLoPrioOcts indicates the number of
        low priority octets, as determined by the port ingress QoS
        policy, offered by the Pchip to the Qchip."
    ::= { tmnxPortIngQosQStatEntry 8 }

tmnxPortIngQosQStatDpdLoPrioOcts OBJECT-TYPE
    SYNTAX          Counter64
    MAX-ACCESS      read-only
    STATUS          current
    DESCRIPTION
        "The value of tmnxPortIngQosQStatDpdLoPrioOcts indicates the number of
        low priority octets, as determined by the port ingress QoS
        policy, dropped by the Qchip due to: MBS exceeded, buffer pool limit
        exceeded, etc."
    ::= { tmnxPortIngQosQStatEntry 9 }

tmnxPortIngQosQStatFwdInProfPkts OBJECT-TYPE
    SYNTAX          Counter64
    MAX-ACCESS      read-only
    STATUS          current
    DESCRIPTION
        "The value of tmnxPortIngQosQStatFwdInProfPkts indicates the number of
        in-profile packets (rate below CIR) forwarded by the ingress Qchip."
    ::= { tmnxPortIngQosQStatEntry 10 }

tmnxPortIngQosQStatFwdOutProfPkts OBJECT-TYPE
    SYNTAX          Counter64
    MAX-ACCESS      read-only
    STATUS          current
    DESCRIPTION
        "The value of tmnxPortIngQosQStatFwdOutProfPkts indicates the number of
        out-of-profile packets (rate above CIR) forwarded by the ingress Qchip."
    ::= { tmnxPortIngQosQStatEntry 11 }

tmnxPortIngQosQStatFwdInProfOcts OBJECT-TYPE
    SYNTAX          Counter64
    MAX-ACCESS      read-only
    STATUS          current
    DESCRIPTION
        "The value of tmnxPortIngQosQStatFwdInProfOcts indicates the number of
        in-profile octets (rate below CIR) forwarded by the ingress Qchip."
    ::= { tmnxPortIngQosQStatEntry 12 }

tmnxPortIngQosQStatFwdOutProfOcts OBJECT-TYPE
    SYNTAX          Counter64
    MAX-ACCESS      read-only
    STATUS          current
    DESCRIPTION
        "The value of tmnxPortIngQosQStatFwdOutProfOcts indicates the number of
        out-of-profile octets (rate above CIR) forwarded by the ingress Qchip."
    ::= { tmnxPortIngQosQStatEntry 13 }

tmnxPortIngQosQStatUncolPktsOff OBJECT-TYPE
    SYNTAX          Counter64
    MAX-ACCESS      read-only
    STATUS          current
    DESCRIPTION
        "The value of tmnxPortIngQosQStatUncolPktsOff indicates the number of
        uncolored packets offered to the ingress Qchip."
    ::= { tmnxPortIngQosQStatEntry 14 }

tmnxPortIngQosQStatUncolOctsOff OBJECT-TYPE
    SYNTAX          Counter64
    MAX-ACCESS      read-only
    STATUS          current
    DESCRIPTION
        "The value of tmnxPortIngQosQStatUncolOctsOff indicates the number of
        uncolored octets offered to the ingress Qchip."
    ::= { tmnxPortIngQosQStatEntry 15 }

-- ----------------------------------------
-- Egress QoS Queue port Statistics Table
-- ----------------------------------------
tmnxPortEgrQosQStatTable OBJECT-TYPE
    SYNTAX          SEQUENCE OF TmnxPortEgrQosQStatEntry
    MAX-ACCESS      not-accessible
    STATUS          current
    DESCRIPTION     "A table that contains egress QoS queue-group queue
                     port statistics."
    ::= { tmnxPortObjs 46 }

tmnxPortEgrQosQStatEntry OBJECT-TYPE
    SYNTAX          TmnxPortEgrQosQStatEntry
    MAX-ACCESS      not-accessible
    STATUS          current
    DESCRIPTION     "Egress statistics about a specific port's
                     QoS queue-group queue.
                  
                     In release 11.0, tPortAccEgrQGrpInstanceId is added as 
                     another index before tmnxPortEgrQosQStatQueueId for this 
                     tmnxPortEgrQosQStatTable."
    INDEX { tmnxChassisIndex, tmnxPortPortID,
            tPortAccEgrQGrpName, tPortAccEgrQGrpInstanceId,
            tmnxPortEgrQosQStatQueueId }
    ::= { tmnxPortEgrQosQStatTable 1 }

TmnxPortEgrQosQStatEntry ::=
    SEQUENCE {
        tmnxPortEgrQosQStatQueueId          TEgressQueueId,
        tmnxPortEgrQosQStatFwdInProfPkts    Counter64,
        tmnxPortEgrQosQStatDpdInProfPkts    Counter64,
        tmnxPortEgrQosQStatFwdOutProfPkts   Counter64,
        tmnxPortEgrQosQStatDpdOutProfPkts   Counter64,
        tmnxPortEgrQosQStatFwdInProfOcts    Counter64,
        tmnxPortEgrQosQStatDpdInProfOcts    Counter64,
        tmnxPortEgrQosQStatFwdOutProfOcts   Counter64,
        tmnxPortEgrQosQStatDpdOutProfOcts   Counter64
    }

tmnxPortEgrQosQStatQueueId OBJECT-TYPE
    SYNTAX       TEgressQueueId (1..8)
    MAX-ACCESS   not-accessible
    STATUS       current
    DESCRIPTION
        "The value of tmnxPortEgrQosQStatQueueId specifies the queue-group
        queue ID which is used as the fourth index to the table entry."
    ::= { tmnxPortEgrQosQStatEntry 1 }

tmnxPortEgrQosQStatFwdInProfPkts OBJECT-TYPE
    SYNTAX          Counter64
    MAX-ACCESS      read-only
    STATUS          current
    DESCRIPTION
        "The value of tmnxPortEgrQosQStatFwdInProfPkts indicates the number of
        in-profile packets (rate below CIR) forwarded by the egress Qchip."
    ::= { tmnxPortEgrQosQStatEntry 2 }

tmnxPortEgrQosQStatDpdInProfPkts OBJECT-TYPE
    SYNTAX          Counter64
    MAX-ACCESS      read-only
    STATUS          current
    DESCRIPTION
        "The value of tmnxPortEgrQosQStatDpdInProfPkts indicates the number of
        in-profile packets discarded by the egress Qchip due to: MBS exceeded,
        buffer pool limit exceeded, etc."
    ::= { tmnxPortEgrQosQStatEntry 3 }

tmnxPortEgrQosQStatFwdOutProfPkts OBJECT-TYPE
    SYNTAX          Counter64
    MAX-ACCESS      read-only
    STATUS          current
    DESCRIPTION
        "The value of tmnxPortEgrQosQStatFwdOutProfPkts indicates the number of
        out-of-profile packets (rate above CIR) forwarded by the egress Qchip."
    ::= { tmnxPortEgrQosQStatEntry 4 }

tmnxPortEgrQosQStatDpdOutProfPkts OBJECT-TYPE
    SYNTAX          Counter64
    MAX-ACCESS      read-only
    STATUS          current
    DESCRIPTION
        "The value of tmnxPortEgrQosQStatDpdOutProfPkts indicates the number of
        out-of-profile packets discarded by the egress Qchip due to:
        MBS exceeded, buffer pool limit exceeded, etc."
    ::= { tmnxPortEgrQosQStatEntry 5 }

tmnxPortEgrQosQStatFwdInProfOcts OBJECT-TYPE
    SYNTAX          Counter64
    MAX-ACCESS      read-only
    STATUS          current
    DESCRIPTION
        "The value of tmnxPortEgrQosQStatFwdInProfOcts indicates the number of
        in-profile octets (rate below CIR) forwarded by the egress Qchip."
    ::= { tmnxPortEgrQosQStatEntry 6 }

tmnxPortEgrQosQStatDpdInProfOcts OBJECT-TYPE
    SYNTAX          Counter64
    MAX-ACCESS      read-only
    STATUS          current
    DESCRIPTION
        "The value of tmnxPortEgrQosQStatDpdInProfOcts indicates the number of
        in-profile octets discarded by the egress Qchip due to:
        MBS exceeded, buffer pool limit exceeded, etc."
    ::= { tmnxPortEgrQosQStatEntry 7 }

tmnxPortEgrQosQStatFwdOutProfOcts OBJECT-TYPE
    SYNTAX          Counter64
    MAX-ACCESS      read-only
    STATUS          current
    DESCRIPTION
        "The value of tmnxPortEgrQosQStatFwdOutProfOcts indicates the number of
        out-of-profile octets (rate above CIR) forwarded by the egress Qchip."
    ::= { tmnxPortEgrQosQStatEntry 8 }

tmnxPortEgrQosQStatDpdOutProfOcts OBJECT-TYPE
    SYNTAX          Counter64
    MAX-ACCESS      read-only
    STATUS          current
    DESCRIPTION
        "The value of tmnxPortEgrQosQStatDpdOutProfOcts indicates the number of
        out-of-profile octets discarded by the egress Qchip due to:
        MBS exceeded, buffer pool limit exceeded, etc."
    ::= { tmnxPortEgrQosQStatEntry 9 }

--
--  Network Port Egress Stats Per Queue Group Queue Table
--
tmnxPortNetEgrQStatTable OBJECT-TYPE
    SYNTAX      SEQUENCE OF TmnxPortNetEgrQStatEntry
    MAX-ACCESS  not-accessible
    STATUS      current
    DESCRIPTION
        "Defines the Alcatel-Lucent SROS series network port egress
         statistics table for providing, via SNMP, the capability of
         retrieving the traffic statistics for the queue-group queues
         being used for the ports to forward the network egress
         traffic."
    ::= { tmnxPortStatsObjs 5 }

tmnxPortNetEgrQStatEntry    OBJECT-TYPE
    SYNTAX      TmnxPortNetEgrQStatEntry
    MAX-ACCESS  not-accessible
    STATUS      current
    DESCRIPTION
        "Defines an entry in tmnxPortNetEgrQStatTable. Entries are
         created and deleted by the system depending on the queue policy
         being used at the specific port.

         In release 10.0 tPortNetEgrQGrpInstanceId is added as another index
         before tmnxPortEgrQosQStatQueueId for this tmnxPortNetEgrQStatTable."
    INDEX   { tmnxChassisIndex, tmnxPortPortID,
              tPortNetEgrQGrpName, tPortNetEgrQGrpInstanceId,
              tmnxPortEgrQosQStatQueueId }
    ::= { tmnxPortNetEgrQStatTable 1 }

TmnxPortNetEgrQStatEntry ::=
    SEQUENCE {
        tmnxPortNetEgrQFwdInProfPkts   Counter64,
        tmnxPortNetEgrQFwdOutProfPkts  Counter64,
        tmnxPortNetEgrQFwdInProfOcts   Counter64,
        tmnxPortNetEgrQFwdOutProfOcts  Counter64,
        tmnxPortNetEgrQDroInProfPkts   Counter64,
        tmnxPortNetEgrQDroOutProfPkts  Counter64,
        tmnxPortNetEgrQDroInProfOcts   Counter64,
        tmnxPortNetEgrQDroOutProfOcts  Counter64
    }

tmnxPortNetEgrQFwdInProfPkts OBJECT-TYPE
    SYNTAX      Counter64
    MAX-ACCESS  read-only
    STATUS      current
    DESCRIPTION
        "The value of tmnxPortNetEgrQFwdInProfPkts indicates the number of
        conforming network egress packets forwarded on this port using this
        queue-group queue."
    ::= { tmnxPortNetEgrQStatEntry 1 }

tmnxPortNetEgrQFwdOutProfPkts OBJECT-TYPE
    SYNTAX      Counter64
    MAX-ACCESS  read-only
    STATUS      current
    DESCRIPTION
        "The value of tmnxPortNetEgrQFwdOutProfPkts indicates the number of
        exceeding network egress packets forwarded on this port using this
        queue-group queue."
    ::= { tmnxPortNetEgrQStatEntry 2 }

tmnxPortNetEgrQFwdInProfOcts OBJECT-TYPE
    SYNTAX      Counter64
    MAX-ACCESS  read-only
    STATUS      current
    DESCRIPTION
        "The value of tmnxPortNetEgrQFwdInProfOcts indicates the number of
        conforming network egress octets forwarded on this port using this
        queue-group queue."
    ::= { tmnxPortNetEgrQStatEntry 3 }

tmnxPortNetEgrQFwdOutProfOcts OBJECT-TYPE
    SYNTAX      Counter64
    MAX-ACCESS  read-only
    STATUS      current
    DESCRIPTION
        "The value of tmnxPortNetEgrQFwdOutProfOcts indicates the number of
        exceeding network egress octets forwarded on this port using this
        queue-group queue."
    ::= { tmnxPortNetEgrQStatEntry 4 }

tmnxPortNetEgrQDroInProfPkts OBJECT-TYPE
    SYNTAX      Counter64
    MAX-ACCESS  read-only
    STATUS      current
    DESCRIPTION
        "The value of tmnxPortNetEgrQDroInProfPkts indicates the number of
        conforming network egress packets dropped on this port using this
        queue-group queue."
    ::= { tmnxPortNetEgrQStatEntry 5 }

tmnxPortNetEgrQDroOutProfPkts OBJECT-TYPE
    SYNTAX      Counter64
    MAX-ACCESS  read-only
    STATUS      current
    DESCRIPTION
        "The value of tmnxPortNetEgrQDroOutProfPkts indicates the number of
        exceeding network egress packets dropped on this port using this
        queue-group queue."
    ::= { tmnxPortNetEgrQStatEntry 6 }

tmnxPortNetEgrQDroInProfOcts OBJECT-TYPE
    SYNTAX      Counter64
    MAX-ACCESS  read-only
    STATUS      current
    DESCRIPTION
        "The value of tmnxPortNetEgrQDroInProfOcts indicates the number of
        conforming network egress octets dropped on this port using this
        queue-group queue."
    ::= { tmnxPortNetEgrQStatEntry 7 }

tmnxPortNetEgrQDroOutProfOcts OBJECT-TYPE
    SYNTAX      Counter64
    MAX-ACCESS  read-only
    STATUS      current
    DESCRIPTION
        "The value of tmnxPortNetEgrQDroOutProfOcts indicates the number of
        exceeding network egress octets dropped on this port using this
        queue-group queue."
    ::= { tmnxPortNetEgrQStatEntry 8 }

-- ----------------------------------------
--  Network Port Egress Stats Per Queue Group policer Table
-- ----------------------------------------
tPortNetEgrQGrpPStatTable OBJECT-TYPE
    SYNTAX          SEQUENCE OF TPortNetEgrQGrpPStatEntry
    MAX-ACCESS      not-accessible
    STATUS          current
    DESCRIPTION     
        "The value of tPortNetEgrQGrpPStatTable contains port egress 
         queue group policer statistics on network side."
    ::= { tmnxPortStatsObjs 7 }

tPortNetEgrQGrpPStatEntry OBJECT-TYPE
    SYNTAX          TPortNetEgrQGrpPStatEntry
    MAX-ACCESS      not-accessible
    STATUS          current
    DESCRIPTION     
        "The value of tPortNetEgrQGrpPStatEntry defines an entry in the
         tPortNetEgrQGrpPStatTable. It represents statistics about a 
         specific QoS egress queue group policer on the specified port."
    INDEX           { tmnxChassisIndex, tmnxPortPortID, tPortNetEgrQGrpName,
                      tPortNetEgrQGrpInstanceId, 
                      tPortNetEgrQGrpPStatQosPolicerId  }
    ::= { tPortNetEgrQGrpPStatTable 1 }

TPortNetEgrQGrpPStatEntry ::=
    SEQUENCE {
        tPortNetEgrQGrpPStatQosPolicerId   TEgrPolicerId,
        tPortNetEgrQGrpPStatMode           TmnxEgrPolicerStatMode,
        tPortNetEgrQGrpPStOffInProfPkt     Counter64,
        tPortNetEgrQGrpPStOffInProfPktL    Counter32,
        tPortNetEgrQGrpPStOffInProfPktH    Counter32,
        tPortNetEgrQGrpPStFwdInProfPkt     Counter64,
        tPortNetEgrQGrpPStFwdInProfPktL    Counter32,
        tPortNetEgrQGrpPStFwdInProfPktH    Counter32,
        tPortNetEgrQGrpPStDrpInProfPkt     Counter64,
        tPortNetEgrQGrpPStDrpInProfPktL    Counter32,
        tPortNetEgrQGrpPStDrpInProfPktH    Counter32,
        tPortNetEgrQGrpPStOffOutProfPkt    Counter64,
        tPortNetEgrQGrpPStOffOutProfPktL   Counter32,
        tPortNetEgrQGrpPStOffOutProfPktH   Counter32,
        tPortNetEgrQGrpPStFwdOutProfPkt    Counter64,
        tPortNetEgrQGrpPStFwdOutProfPktL   Counter32,
        tPortNetEgrQGrpPStFwdOutProfPktH   Counter32,
        tPortNetEgrQGrpPStDrpOutProfPkt    Counter64,
        tPortNetEgrQGrpPStDrpOutProfPktL   Counter32,
        tPortNetEgrQGrpPStDrpOutProfPktH   Counter32,
        tPortNetEgrQGrpPStOffInProfOct     Counter64,
        tPortNetEgrQGrpPStOffInProfOctL    Counter32,
        tPortNetEgrQGrpPStOffInProfOctH    Counter32,
        tPortNetEgrQGrpPStFwdInProfOct     Counter64,
        tPortNetEgrQGrpPStFwdInProfOctL    Counter32,
        tPortNetEgrQGrpPStFwdInProfOctH    Counter32,
        tPortNetEgrQGrpPStDrpInProfOct     Counter64,
        tPortNetEgrQGrpPStDrpInProfOctL    Counter32,
        tPortNetEgrQGrpPStDrpInProfOctH    Counter32,
        tPortNetEgrQGrpPStOffOutProfOct    Counter64,
        tPortNetEgrQGrpPStOffOutProfOctL   Counter32,
        tPortNetEgrQGrpPStOffOutProfOctH   Counter32,
        tPortNetEgrQGrpPStFwdOutProfOct    Counter64,
        tPortNetEgrQGrpPStFwdOutProfOctL   Counter32,
        tPortNetEgrQGrpPStFwdOutProfOctH   Counter32,
        tPortNetEgrQGrpPStDrpOutProfOct    Counter64,
        tPortNetEgrQGrpPStDrpOutProfOctL   Counter32,
        tPortNetEgrQGrpPStDrpOutProfOctH   Counter32,
        tPortNetEgrQGrpPStUncolPktOff      Counter64,
        tPortNetEgrQGrpPStUncolPktOffL     Counter32,
        tPortNetEgrQGrpPStUncolPktOffH     Counter32,
        tPortNetEgrQGrpPStUncolOctOff      Counter64,
        tPortNetEgrQGrpPStUncolOctOffL     Counter32,
        tPortNetEgrQGrpPStUncolOctOffH     Counter32
    }

tPortNetEgrQGrpPStatQosPolicerId OBJECT-TYPE
    SYNTAX          TEgrPolicerId
    MAX-ACCESS      not-accessible
    STATUS          current
    DESCRIPTION     
        "The value of tPortNetEgrQGrpPStatQosPolicerId specifies the index of the 
         egress QoS policer queue group on network port."
    ::= { tPortNetEgrQGrpPStatEntry 1 }

tPortNetEgrQGrpPStatMode OBJECT-TYPE
    SYNTAX      TmnxEgrPolicerStatMode
    MAX-ACCESS  read-only
    STATUS      current
    DESCRIPTION
        "The value of tPortNetEgrQGrpPStatMode indicates the stat mode used by 
         this policer."
    ::= { tPortNetEgrQGrpPStatEntry 2 }

tPortNetEgrQGrpPStOffInProfPkt OBJECT-TYPE
    SYNTAX          Counter64
    MAX-ACCESS      read-only
    STATUS          current
    DESCRIPTION    
        "The value of tPortNetEgrQGrpPStOffInProfPkt indicates the number of 
         in-profile packets (rate below CIR) offered by the egress Pchip."
    ::= { tPortNetEgrQGrpPStatEntry 3 }

tPortNetEgrQGrpPStOffInProfPktL OBJECT-TYPE
    SYNTAX          Counter32
    MAX-ACCESS      read-only
    STATUS          current
    DESCRIPTION     
        "The value of tPortNetEgrQGrpPStOffInProfPktL indicates the lower 32 
         bits of tPortNetEgrQGrpPStOffInProfPkt."
    ::= { tPortNetEgrQGrpPStatEntry 4 }

tPortNetEgrQGrpPStOffInProfPktH OBJECT-TYPE
    SYNTAX          Counter32
    MAX-ACCESS      read-only
    STATUS          current
    DESCRIPTION    
        "The value of tPortNetEgrQGrpPStOffInProfPktH indicates the upper 32 
         bits of tPortNetEgrQGrpPStOffInProfPkt."
    ::= { tPortNetEgrQGrpPStatEntry 5 }

tPortNetEgrQGrpPStFwdInProfPkt OBJECT-TYPE
    SYNTAX          Counter64
    MAX-ACCESS      read-only
    STATUS          current
    DESCRIPTION    
        "The value of tPortNetEgrQGrpPStFwdInProfPkt indicates the number of 
         in-profile packets (rate below CIR) forwarded by the egress Pchip."
    ::= { tPortNetEgrQGrpPStatEntry 6 }

tPortNetEgrQGrpPStFwdInProfPktL OBJECT-TYPE
    SYNTAX          Counter32
    MAX-ACCESS      read-only
    STATUS          current
    DESCRIPTION    
        "The value of tPortNetEgrQGrpPStFwdInProfPktL indicates the lower 32
         bits of tPortNetEgrQGrpPStFwdInProfPkt."
    ::= { tPortNetEgrQGrpPStatEntry 7 }

tPortNetEgrQGrpPStFwdInProfPktH OBJECT-TYPE
    SYNTAX          Counter32
    MAX-ACCESS      read-only
    STATUS          current
    DESCRIPTION    
        "The value of tPortNetEgrQGrpPStFwdInProfPktH indicates the upper 32 
         bits of tPortNetEgrQGrpPStFwdInProfPkt."
    ::= { tPortNetEgrQGrpPStatEntry 8 }

tPortNetEgrQGrpPStDrpInProfPkt OBJECT-TYPE
    SYNTAX          Counter64
    MAX-ACCESS      read-only
    STATUS          current
    DESCRIPTION    
        "The value of tPortNetEgrQGrpPStDrpInProfPkt indicates the number of 
         in-profile packets discarded by the egress Pchip due to: MBS exceeded,
         buffer pool limit exceeded, etc."
    ::= { tPortNetEgrQGrpPStatEntry 9 }

tPortNetEgrQGrpPStDrpInProfPktL OBJECT-TYPE
    SYNTAX          Counter32
    MAX-ACCESS      read-only
    STATUS          current
    DESCRIPTION    
        "The value of tPortNetEgrQGrpPStDrpInProfPktL indicates the lower 32 
         bits of tPortNetEgrQGrpPStDrpInProfPkt."
    ::= { tPortNetEgrQGrpPStatEntry 10 }

tPortNetEgrQGrpPStDrpInProfPktH OBJECT-TYPE
    SYNTAX          Counter32
    MAX-ACCESS      read-only
    STATUS          current
    DESCRIPTION    
        "The value of tPortNetEgrQGrpPStDrpInProfPktH indicates the upper 32 
         bits of tPortNetEgrQGrpPStDrpInProfPkt."
    ::= { tPortNetEgrQGrpPStatEntry 11 }

tPortNetEgrQGrpPStOffOutProfPkt OBJECT-TYPE
    SYNTAX          Counter64
    MAX-ACCESS      read-only
    STATUS          current
    DESCRIPTION    
        "The value of tPortNetEgrQGrpPStOffOutProfPkt indicates the number of 
         out-of-profile packets (rate above CIR) offered by the  egress Pchip."
    ::= { tPortNetEgrQGrpPStatEntry 12 }

tPortNetEgrQGrpPStOffOutProfPktL OBJECT-TYPE
    SYNTAX          Counter32
    MAX-ACCESS      read-only
    STATUS          current
    DESCRIPTION    
        "The value of tPortNetEgrQGrpPStOffOutProfPktL indicates the lower 32 
         bits of tPortNetEgrQGrpPStOffOutProfPkt."
    ::= { tPortNetEgrQGrpPStatEntry 13 }

tPortNetEgrQGrpPStOffOutProfPktH OBJECT-TYPE
    SYNTAX          Counter32
    MAX-ACCESS      read-only
    STATUS          current
    DESCRIPTION    
        "The value of tPortNetEgrQGrpPStOffOutProfPktH indicates the upper 32 
         bits of tPortNetEgrQGrpPStOffOutProfPkt."
    ::= { tPortNetEgrQGrpPStatEntry 14 }

tPortNetEgrQGrpPStFwdOutProfPkt OBJECT-TYPE
    SYNTAX          Counter64
    MAX-ACCESS      read-only
    STATUS          current
    DESCRIPTION    
        "The value of tPortNetEgrQGrpPStFwdOutProfPkt indicates the number of 
         out-of-profile packets (rate above CIR) forwarded by the egress Pchip."
    ::= { tPortNetEgrQGrpPStatEntry 15 }

tPortNetEgrQGrpPStFwdOutProfPktL OBJECT-TYPE
    SYNTAX          Counter32
    MAX-ACCESS      read-only
    STATUS          current
    DESCRIPTION    
        "The value of tPortNetEgrQGrpPStFwdOutProfPktL indicates the lower 32
         bits of tPortNetEgrQGrpPStFwdOutProfPkt."
    ::= { tPortNetEgrQGrpPStatEntry 16 }

tPortNetEgrQGrpPStFwdOutProfPktH OBJECT-TYPE
    SYNTAX          Counter32
    MAX-ACCESS      read-only
    STATUS          current
    DESCRIPTION    
        "The value of tPortNetEgrQGrpPStFwdOutProfPktH indicates the upper 32 
         bits of tPortNetEgrQGrpPStFwdOutProfPkt."
    ::= { tPortNetEgrQGrpPStatEntry 17 }

tPortNetEgrQGrpPStDrpOutProfPkt OBJECT-TYPE
    SYNTAX          Counter64
    MAX-ACCESS      read-only
    STATUS          current
    DESCRIPTION    
        "The value of tPortNetEgrQGrpPStDrpOutProfPkt indicates the number of 
         out-of-profile packets discarded by the egress Pchip due to: MBS 
         exceeded, buffer pool limit exceeded, etc."
    ::= { tPortNetEgrQGrpPStatEntry 18 }

tPortNetEgrQGrpPStDrpOutProfPktL OBJECT-TYPE
    SYNTAX          Counter32
    MAX-ACCESS      read-only
    STATUS          current
    DESCRIPTION    
        "The value of tPortNetEgrQGrpPStDrpOutProfPktL indicates the lower 32 
         bits of tPortNetEgrQGrpPStDrpOutProfPkt."
    ::= { tPortNetEgrQGrpPStatEntry 19 }

tPortNetEgrQGrpPStDrpOutProfPktH OBJECT-TYPE
    SYNTAX          Counter32
    MAX-ACCESS      read-only
    STATUS          current
    DESCRIPTION    
        "The value of tPortNetEgrQGrpPStDrpOutProfPktH indicates the upper 32 
         bits of tPortNetEgrQGrpPStDrpOutProfPkt."
    ::= { tPortNetEgrQGrpPStatEntry 20 }

tPortNetEgrQGrpPStOffInProfOct OBJECT-TYPE
    SYNTAX          Counter64
    MAX-ACCESS      read-only
    STATUS          current
    DESCRIPTION    
        "The value of tPortNetEgrQGrpPStOffInProfOct indicates the number of 
         in-profile octets (rate below CIR) offered by the egress Pchip."
    ::= { tPortNetEgrQGrpPStatEntry 21 }

tPortNetEgrQGrpPStOffInProfOctL OBJECT-TYPE
    SYNTAX          Counter32
    MAX-ACCESS      read-only
    STATUS          current
    DESCRIPTION    
        "The value of tPortNetEgrQGrpPStOffInProfOctL indicates the lower 32 
         bits of tPortNetEgrQGrpPStOffInProfOct."
    ::= { tPortNetEgrQGrpPStatEntry 22 }

tPortNetEgrQGrpPStOffInProfOctH OBJECT-TYPE
    SYNTAX          Counter32
    MAX-ACCESS      read-only
    STATUS          current
    DESCRIPTION    
        "The value of tPortNetEgrQGrpPStOffInProfOctH indicates the upper 32 
         bits of tPortNetEgrQGrpPStOffInProfOct."
    ::= { tPortNetEgrQGrpPStatEntry 23 }

tPortNetEgrQGrpPStFwdInProfOct OBJECT-TYPE
    SYNTAX          Counter64
    MAX-ACCESS      read-only
    STATUS          current
    DESCRIPTION    
        "The value of tPortNetEgrQGrpPStFwdInProfOct indicates the number of 
         in-profile octets (rate below CIR) forwarded by the egress Pchip."
    ::= { tPortNetEgrQGrpPStatEntry 24 }

tPortNetEgrQGrpPStFwdInProfOctL OBJECT-TYPE
    SYNTAX          Counter32
    MAX-ACCESS      read-only
    STATUS          current
    DESCRIPTION    
        "The value of tPortNetEgrQGrpPStFwdInProfOctL indicates the lower 32 
         bits of tPortNetEgrQGrpPStFwdInProfOct."
    ::= { tPortNetEgrQGrpPStatEntry 25 }

tPortNetEgrQGrpPStFwdInProfOctH OBJECT-TYPE
    SYNTAX          Counter32
    MAX-ACCESS      read-only
    STATUS          current
    DESCRIPTION    
        "The value of tPortNetEgrQGrpPStFwdInProfOctH indicates the upper 32 
         bits of tPortNetEgrQGrpPStFwdInProfOct."
    ::= { tPortNetEgrQGrpPStatEntry 26 }

tPortNetEgrQGrpPStDrpInProfOct OBJECT-TYPE
    SYNTAX          Counter64
    MAX-ACCESS      read-only
    STATUS          current
    DESCRIPTION    
        "The value of tPortNetEgrQGrpPStDrpInProfOct indicates the number of 
         in-profile octets discarded by the egress Pchip due to: MBS exceeded, 
         buffer pool limit exceeded, etc."
    ::= { tPortNetEgrQGrpPStatEntry 27 }

tPortNetEgrQGrpPStDrpInProfOctL OBJECT-TYPE
    SYNTAX          Counter32
    MAX-ACCESS      read-only
    STATUS          current
    DESCRIPTION    
        "The value of tPortNetEgrQGrpPStDrpInProfOctL indicates the lower 32 
         bits of tPortNetEgrQGrpPStDrpInProfOct."
    ::= { tPortNetEgrQGrpPStatEntry 28 }

tPortNetEgrQGrpPStDrpInProfOctH OBJECT-TYPE
    SYNTAX          Counter32
    MAX-ACCESS      read-only
    STATUS          current
    DESCRIPTION    
        "The value of tPortNetEgrQGrpPStDrpInProfOctH indicates the upper 32 
         bits of tPortNetEgrQGrpPStDrpInProfOct."
    ::= { tPortNetEgrQGrpPStatEntry 29 }

tPortNetEgrQGrpPStOffOutProfOct OBJECT-TYPE
    SYNTAX          Counter64
    MAX-ACCESS      read-only
    STATUS          current
    DESCRIPTION    
        "The value of tPortNetEgrQGrpPStOffOutProfOct indicates the number of 
         out-of-profile octets (rate above CIR) forwarded by the egress Pchip."
    ::= { tPortNetEgrQGrpPStatEntry 30 }

tPortNetEgrQGrpPStOffOutProfOctL OBJECT-TYPE
    SYNTAX          Counter32
    MAX-ACCESS      read-only
    STATUS          current
    DESCRIPTION    
        "The value of tPortNetEgrQGrpPStOffOutProfOctL indicates the lower 32 
         bits of tPortNetEgrQGrpPStOffOutProfOct."
    ::= { tPortNetEgrQGrpPStatEntry 31 }

tPortNetEgrQGrpPStOffOutProfOctH OBJECT-TYPE
    SYNTAX          Counter32
    MAX-ACCESS      read-only
    STATUS          current
    DESCRIPTION    
        "The value of tPortNetEgrQGrpPStOffOutProfOctH indicates the upper 32 
         bits of tPortNetEgrQGrpPStOffOutProfOct."
    ::= { tPortNetEgrQGrpPStatEntry 32 }

tPortNetEgrQGrpPStFwdOutProfOct OBJECT-TYPE
    SYNTAX          Counter64
    MAX-ACCESS      read-only
    STATUS          current
    DESCRIPTION    
        "The value of tPortNetEgrQGrpPStFwdOutProfOct indicates the number of 
         out-of-profile octets (rate above CIR) forwarded by the egress Pchip."
    ::= { tPortNetEgrQGrpPStatEntry 33 }

tPortNetEgrQGrpPStFwdOutProfOctL OBJECT-TYPE
    SYNTAX          Counter32
    MAX-ACCESS      read-only
    STATUS          current
    DESCRIPTION    
        "The value of tPortNetEgrQGrpPStFwdOutProfOctL indicates the lower 32 
         bits of tPortNetEgrQGrpPStFwdOutProfOct."
    ::= { tPortNetEgrQGrpPStatEntry 34 }

tPortNetEgrQGrpPStFwdOutProfOctH OBJECT-TYPE
    SYNTAX          Counter32
    MAX-ACCESS      read-only
    STATUS          current
    DESCRIPTION    
        "The value of tPortNetEgrQGrpPStFwdOutProfOctH indicates the upper 32 
         bits of tPortNetEgrQGrpPStFwdOutProfOct."
    ::= { tPortNetEgrQGrpPStatEntry 35 }

tPortNetEgrQGrpPStDrpOutProfOct OBJECT-TYPE
    SYNTAX          Counter64
    MAX-ACCESS      read-only
    STATUS          current
    DESCRIPTION    
        "The value of tPortNetEgrQGrpPStDrpOutProfOct indicates the number of 
         out-of-profile octets discarded by the egress Pchip due to: MBS 
         exceeded, buffer pool limit exceeded, etc."
    ::= { tPortNetEgrQGrpPStatEntry 36 }

tPortNetEgrQGrpPStDrpOutProfOctL OBJECT-TYPE
    SYNTAX          Counter32
    MAX-ACCESS      read-only
    STATUS          current
    DESCRIPTION    
        "The value of tPortNetEgrQGrpPStDrpOutProfOctL indicates the lower 32 
         bits of tPortNetEgrQGrpPStDrpOutProfOct."
    ::= { tPortNetEgrQGrpPStatEntry 37 }

tPortNetEgrQGrpPStDrpOutProfOctH OBJECT-TYPE
    SYNTAX          Counter32
    MAX-ACCESS      read-only
    STATUS          current
    DESCRIPTION    
        "The value of tPortNetEgrQGrpPStDrpOutProfOctH indicates the upper 32 
         bits of tPortNetEgrQGrpPStDrpOutProfOct."
    ::= { tPortNetEgrQGrpPStatEntry 38 }

tPortNetEgrQGrpPStUncolPktOff OBJECT-TYPE
    SYNTAX          Counter64
    MAX-ACCESS      read-only
    STATUS          current
    DESCRIPTION    
        "The value of tPortNetEgrQGrpPStUncolPktOff indicates the number of
         uncolored packets forwarded by the egress Pchip."
    ::= { tPortNetEgrQGrpPStatEntry 39 }

tPortNetEgrQGrpPStUncolPktOffL OBJECT-TYPE
    SYNTAX          Counter32
    MAX-ACCESS      read-only
    STATUS          current
    DESCRIPTION    
        "The value of tPortNetEgrQGrpPStUncolPktOffL indicates the lower 32 
         bits of tPortNetEgrQGrpPStUncolPktOff."
    ::= { tPortNetEgrQGrpPStatEntry 40 }

tPortNetEgrQGrpPStUncolPktOffH OBJECT-TYPE
    SYNTAX          Counter32
    MAX-ACCESS      read-only
    STATUS          current
    DESCRIPTION    
        "The value of tPortNetEgrQGrpPStUncolPktOffH indicates the upper 32 
         bits of tPortNetEgrQGrpPStUncolPktOff."
    ::= { tPortNetEgrQGrpPStatEntry 41 }

tPortNetEgrQGrpPStUncolOctOff OBJECT-TYPE
    SYNTAX          Counter64
    MAX-ACCESS      read-only
    STATUS          current
    DESCRIPTION    
        "The value of tPortNetEgrQGrpPStUncolOctOff indicates the number of 
         uncolored octets forwarded by the egress Pchip."
    ::= { tPortNetEgrQGrpPStatEntry 42 }

tPortNetEgrQGrpPStUncolOctOffL OBJECT-TYPE
    SYNTAX          Counter32
    MAX-ACCESS      read-only
    STATUS          current
    DESCRIPTION    
        "The value of tPortNetEgrQGrpPStUncolOctOffL indicates the lower 32 
         bits of tPortNetEgrQGrpPStUncolOctOff."
    ::= { tPortNetEgrQGrpPStatEntry 43 }

tPortNetEgrQGrpPStUncolOctOffH OBJECT-TYPE
    SYNTAX          Counter32
    MAX-ACCESS      read-only
    STATUS          current
    DESCRIPTION    
        "The value of tPortNetEgrQGrpPStUncolOctOffH indicates the upper 32 
         bits of tPortNetEgrQGrpPStUncolOctOff."
    ::= { tPortNetEgrQGrpPStatEntry 44 }

-- ----------------------------------------
-- Port CEM Stats Table
-- ----------------------------------------
tmnxPortCemStatsTable OBJECT-TYPE
    SYNTAX          SEQUENCE OF TmnxPortCemStatsEntry
    MAX-ACCESS      not-accessible
    STATUS          current
    DESCRIPTION     "A table that contains CEM Port statistics."
    ::= { tmnxPortStatsObjs 6 }

tmnxPortCemStatsEntry OBJECT-TYPE
    SYNTAX          TmnxPortCemStatsEntry
    MAX-ACCESS      not-accessible
    STATUS          current
    DESCRIPTION     "Statistics for a specific CEM Port."
    INDEX           { tmnxChassisIndex, tmnxPortPortID }
    ::= { tmnxPortCemStatsTable 1 }

TmnxPortCemStatsEntry            ::= SEQUENCE {
    tmnxPortCemStatsReportAlarm      BITS,
    tmnxPortCemStatsIgrForwardedPkts Counter32,
    tmnxPortCemStatsIgrDroppedPkts   Counter32,
    tmnxPortCemStatsEgrForwardedPkts Counter32,
    tmnxPortCemStatsEgrDroppedPkts   Counter32,
    tmnxPortCemStatsEgrMissingPkts   Counter32,
    tmnxPortCemStatsEgrPktsReOrder   Counter32,
    tmnxPortCemStatsEgrJtrBfrURun    Counter32,
    tmnxPortCemStatsEgrJtrBfrORun    Counter32,
    tmnxPortCemStatsEgrMisOrderDrop  Counter32,
    tmnxPortCemStatsEgrMalformedPkts Counter32,
    tmnxPortCemStatsEgrLBitDrop      Counter32,
    tmnxPortCemStatsEgrMultipleDrop  Counter32,
    tmnxPortCemStatsEgrESs           Counter32,
    tmnxPortCemStatsEgrSESs          Counter32,
    tmnxPortCemStatsEgrUASs          Counter32,
    tmnxPortCemStatsEgrFailureCounts Counter32,
    tmnxPortCemStatsEgrURunCounts    Counter32,
    tmnxPortCemStatsEgrORunCounts    Counter32,
    tmnxPortCemStatsEgrJtrBfrDepth   Gauge32
}

tmnxPortCemStatsReportAlarm          OBJECT-TYPE
    SYNTAX      BITS {
                        notUsed       (0),
                        strayPkts     (1),
                        malformedPkts (2),
                        pktLoss       (3),
                        bfrOverrun    (4),
                        bfrUnderrun   (5),
                        rmtPktLoss    (6),
                        rmtFault      (7),
                        rmtRdi        (8)
                }
    MAX-ACCESS  read-only
    STATUS      current
    DESCRIPTION
        "The value of tmnxPortCemStatsReportAlarm indicates the type of
         Circuit EMulation (CEM) alarm currently active on the port. The
         syntax of this object mirrors that of the CemSapReportAlarm
         TEXTUAL-CONVENTION. The values may be one of:
             strayPkts     (1)- receiving stray packets.
             malformedPkts (2)- detecting malformed packets.
             pktLoss       (3)- experiencing packet loss.
             bfrOverrun    (4)- experiencing jitter buffer overrun.
             bfrUnderrun   (5)- experiencing jitter buffer underrun.
             rmtPktLoss    (6)- remote packet loss indication.
             rmtFault      (7)- remote TDM fault indication.
             rmtRdi        (8)- remote RDI indication."
     ::= { tmnxPortCemStatsEntry 1 }

tmnxPortCemStatsIgrForwardedPkts OBJECT-TYPE
    SYNTAX      Counter32
    MAX-ACCESS  read-only
    STATUS      current
    DESCRIPTION
        "The value of tmnxPortCemStatsIgrForwardedPkts indicates
         the number of packets that were successfully forwarded."
    ::= { tmnxPortCemStatsEntry 2 }

tmnxPortCemStatsIgrDroppedPkts   OBJECT-TYPE
    SYNTAX      Counter32
    MAX-ACCESS  read-only
    STATUS      current
    DESCRIPTION
        "The value of tmnxPortCemStatsIgrDroppedPkts indicates
         the total number of packets that were dropped due to errors."
    ::= { tmnxPortCemStatsEntry 3 }

tmnxPortCemStatsEgrForwardedPkts OBJECT-TYPE
    SYNTAX      Counter32
    MAX-ACCESS  read-only
    STATUS      current
    DESCRIPTION
        "The value of tmnxPortCemStatsEgrForwardedPkts indicates the
         number of packets that were successfully forwarded."
    ::= { tmnxPortCemStatsEntry 4 }

tmnxPortCemStatsEgrDroppedPkts   OBJECT-TYPE
    SYNTAX      Counter32
    MAX-ACCESS  read-only
    STATUS      current
    DESCRIPTION
        "The value of tmnxPortCemStatsEgrDroppedPkts indicates
         the total number of packets that were dropped due to errors."
    ::= { tmnxPortCemStatsEntry 5 }

tmnxPortCemStatsEgrMissingPkts   OBJECT-TYPE
    SYNTAX      Counter32
    MAX-ACCESS  read-only
    STATUS      current
    DESCRIPTION
        "The value of tmnxPortCemStatsEgrMissingPkts indicates the number of
         missing packets (as detected via control word sequence number gaps)."
    ::= { tmnxPortCemStatsEntry 6 }

tmnxPortCemStatsEgrPktsReOrder   OBJECT-TYPE
    SYNTAX      Counter32
    MAX-ACCESS  read-only
    STATUS      current
    DESCRIPTION
        "The value of tmnxPortCemStatsEgrPktsReOrder indicates the
         number of packets detected out of sequence (via control
         word sequence number), but successfully re-ordered."
    ::= { tmnxPortCemStatsEntry 7 }

tmnxPortCemStatsEgrJtrBfrURun    OBJECT-TYPE
    SYNTAX      Counter32
    MAX-ACCESS  read-only
    STATUS      current
    DESCRIPTION
        "The value of tmnxPortCemStatsEgrJtrBfrURun indicates
         the number of times a packet needed to be played out and
         the jitter buffer was empty."
    ::= { tmnxPortCemStatsEntry 8 }

tmnxPortCemStatsEgrJtrBfrORun    OBJECT-TYPE
    SYNTAX      Counter32
    MAX-ACCESS  read-only
    STATUS      current
    DESCRIPTION
        "The value of tmnxPortCemStatsEgrJtrBfrORun indicates
         the number of times a packet was dropped because it could
         not fit in the jitter buffer."
    ::= { tmnxPortCemStatsEntry 9 }

tmnxPortCemStatsEgrMisOrderDrop  OBJECT-TYPE
    SYNTAX      Counter32
    MAX-ACCESS  read-only
    STATUS      current
    DESCRIPTION
        "The value of tmnxPortCemStatsEgrMisOrderDrop indicates
         the number of packets detected out of order (via control
         word sequence numbers), and could not be re-ordered, or
         could not be placed in the jitter buffer because it was
         out of the current window."
    ::= { tmnxPortCemStatsEntry 10 }

tmnxPortCemStatsEgrMalformedPkts OBJECT-TYPE
    SYNTAX      Counter32
    MAX-ACCESS  read-only
    STATUS      current
    DESCRIPTION
        "The value of tmnxPortCemStatsEgrMalformedPkts indicates the
         number of packets detected with unexpected size, or bad
         headers' stack."
    ::= { tmnxPortCemStatsEntry 11 }

tmnxPortCemStatsEgrLBitDrop      OBJECT-TYPE
    SYNTAX      Counter32
    MAX-ACCESS  read-only
    STATUS      current
    DESCRIPTION
        "The value of tmnxPortCemStatsEgrLBitDrop indicates the
         number of packets dropped due to the L bit set by the far end."
    ::= { tmnxPortCemStatsEntry 12 }

tmnxPortCemStatsEgrMultipleDrop  OBJECT-TYPE
    SYNTAX      Counter32
    MAX-ACCESS  read-only
    STATUS      current
    DESCRIPTION
        "The value of tmnxPortCemStatsEgrMultipleDrop indicates
         the number of packets dropped due to multiple sequence numbers."
    ::= { tmnxPortCemStatsEntry 13 }

tmnxPortCemStatsEgrESs           OBJECT-TYPE
    SYNTAX      Counter32
    MAX-ACCESS  read-only
    STATUS      current
    DESCRIPTION
        "The value of tmnxPortCemStatsEgrESs indicates the number of
         Error Seconds (ESs) encountered. Any malformed packet,
         seq.  error, LOPS and similar are considered as error seconds."
    ::= { tmnxPortCemStatsEntry 14 }

tmnxPortCemStatsEgrSESs          OBJECT-TYPE
    SYNTAX      Counter32
    MAX-ACCESS  read-only
    STATUS      current
    DESCRIPTION
        "The value of tmnxPortCemStatsEgrSESs indicates the number
         of Severely Error Seconds (SESs) encountered.  This is
         when more than 30 percent of the packets within a one
         second window are missing."
    ::= { tmnxPortCemStatsEntry 15 }

tmnxPortCemStatsEgrUASs          OBJECT-TYPE
    SYNTAX      Counter32
    MAX-ACCESS  read-only
    STATUS      current
    DESCRIPTION
        "The value of tmnxPortCemStatsEgrUASs indicates the number of
         Unavailable Seconds (UASs) encountered. Any consecutive
         ten seconds of SESs are counted as one UAS."
    ::= { tmnxPortCemStatsEntry 16 }

tmnxPortCemStatsEgrFailureCounts OBJECT-TYPE
    SYNTAX      Counter32
    MAX-ACCESS  read-only
    STATUS      current
    DESCRIPTION
        "The value of tmnxPortCemStatsEgrFailureCounts indicates
         the number failure events.  A failure event begins when
         the LOPS failure is declared, and ends when the failure
         is cleared."
    ::= { tmnxPortCemStatsEntry 17 }

tmnxPortCemStatsEgrURunCounts    OBJECT-TYPE
    SYNTAX      Counter32
    MAX-ACCESS  read-only
    STATUS      current
    DESCRIPTION
        "The value of tmnxPortCemStatsEgrURunCounts indicates
         the number of times the jitter buffer went into an
         underrun state."
    ::= { tmnxPortCemStatsEntry 18 }

tmnxPortCemStatsEgrORunCounts    OBJECT-TYPE
    SYNTAX      Counter32
    MAX-ACCESS  read-only
    STATUS      current
    DESCRIPTION
        "The value of tmnxPortCemStatsEgrORunCounts indicates
         the number of times the jitter buffer went into an
         overrun state."
    ::= { tmnxPortCemStatsEntry 19 }

tmnxPortCemStatsEgrJtrBfrDepth   OBJECT-TYPE
    SYNTAX      Gauge32
    MAX-ACCESS  read-only
    STATUS      current
    DESCRIPTION
        "The value of tmnxPortCemStatsEgrJtrBfrDepth indicates
         the current packet depth of the jitter buffer."
    ::= { tmnxPortCemStatsEntry 20 }

--
-- MLFR Member Table
--
--  Sparse Dependent Extension of the tmnxBundleMemberTable.
--
--  The same indexes are used for both the base table tmnxBundleMemberTable,
--  and the sparse dependent table, tmnxBundleMemberMlfrTable.
--
--  This in effect extends the tmnxBundleMemberTable with additional columns.
--  Rows are created in the tmnxBundleMemberMlfrTable only for those entries
--  in the tmnxBundleMemberTable that were created and have a value of 'mlfr'
--  for the bundle type.
--
--  Deletion of a row in the tmnxBundleMemberTable results in the
--  same fate for the row in the tmnxBundleMemberMlfrTable.
--

tmnxBundleMemberMlfrTable OBJECT-TYPE
    SYNTAX      SEQUENCE OF TmnxBundleMemberMlfrEntry
    MAX-ACCESS  not-accessible
    STATUS      current
    DESCRIPTION
        "The tmnxBundleMemberMlfrTable has an entry for a
         frame-relay link associated with an MLFR Bundle."
    ::= { tmnxPortObjs 47 }

tmnxBundleMemberMlfrEntry  OBJECT-TYPE
    SYNTAX      TmnxBundleMemberMlfrEntry
    MAX-ACCESS  not-accessible
    STATUS      current
    DESCRIPTION
        "Each row entry represents an frame-relay link associated with
         a MLFR Bundle."
    INDEX   { tmnxBundleBundleID, tmnxPortPortID }
    ::= { tmnxBundleMemberMlfrTable 1 }

TmnxBundleMemberMlfrEntry ::=
    SEQUENCE {
        tmnxBundleMemberMlfrDownReason      TmnxMlfrLinkDownReason
    }

tmnxBundleMemberMlfrDownReason    OBJECT-TYPE
    SYNTAX      TmnxMlfrLinkDownReason
    MAX-ACCESS  read-only
    STATUS      current
    DESCRIPTION
        "The value of tmnxBundleMemberMlfrDownReason indicates the reason code
         for marking the MLFR member link of the bundle to down (i.e.
         tmnxBundleMemberActive will be set to false)."
    ::= { tmnxBundleMemberMlfrEntry 1 }

--
--  Wavelength Tracker Ports Table
--
tmnxWaveTrackerTable OBJECT-TYPE
    SYNTAX  SEQUENCE OF TmnxWaveTrackerEntry
    MAX-ACCESS  not-accessible
    STATUS      current
    DESCRIPTION
        "The tmnxWaveTrackerTable has an entry for each Wavelength Tracker
         port on each IOM card in each chassis in the TMNX system."
    ::= { tmnxPortObjs 48 }

tmnxWaveTrackerEntry OBJECT-TYPE
    SYNTAX      TmnxWaveTrackerEntry
    MAX-ACCESS  not-accessible
    STATUS      current
    DESCRIPTION
        "Each row entry represents a Wave Tracker capable port on a
         IOM card in a chassis in the system. Entries cannot be created
         and deleted via SNMP SET operations. The tmnxWaveTrackerEntry
         contains attributes that are unique to the Wave Tracker capable ports."

    INDEX   { tmnxChassisIndex, tmnxPortPortID }
    ::= { tmnxWaveTrackerTable 1 }

TmnxWaveTrackerEntry             ::= SEQUENCE {
    tmnxWaveTrackerPowerCtrlEnable   TruthValue,
    tmnxWaveTrackerEncodeEnable      TruthValue,
    tmnxWaveTrackerInUse             TruthValue,
    tmnxWaveTrackerTargetPower       Integer32,
    tmnxWaveTrackerWaveKey1          Unsigned32,
    tmnxWaveTrackerWaveKey2          Unsigned32,
    tmnxWaveTrackerTrailName         SnmpAdminString,
    tmnxWaveTrackerCfgAlarms         TmnxWaveTrackerAlarm,
    tmnxWaveTrackerAlarmState        TmnxWaveTrackerAlarm,
    tmnxWaveTrackerMeasuredPower     Integer32,
    tmnxWaveTrackerMaxAttainablePwr  Integer32,
    tmnxWaveTrackerMinAttainablePwr  Integer32,
    tmnxWaveTrackerUpperPowerMargin  Unsigned32,
    tmnxWaveTrackerLowerPowerMargin  Unsigned32,
    tmnxWaveTrackerPortType          INTEGER,
    tmnxWaveTrackerSfpVoaEquipped    TruthValue,
    tmnxWaveTrackerSfpVoaType        INTEGER,
    tmnxWaveTrackerSfpVoaSerialNum   TNamedItemOrEmpty,
    tmnxWaveTrackerSfpVoaModelNum    TNamedItemOrEmpty
}

tmnxWaveTrackerPowerCtrlEnable   OBJECT-TYPE
    SYNTAX      TruthValue
    MAX-ACCESS  read-create
    STATUS      current
    DESCRIPTION
        "The value of tmnxWaveTrackerPowerCtrlEnable specifies whether or not
         the Wavelength Tracker Power Control loop that maintains the
         interface's transmitted optical signal average output power is enabled.

         tmnxWaveTrackerPowerCtrlEnable is equivalent to
         'tnWtEncodePortCapabilityProgrammed' of the 1696-Roadm MIBs."
    DEFVAL { false }
    ::= { tmnxWaveTrackerEntry 1 }

tmnxWaveTrackerEncodeEnable      OBJECT-TYPE
    SYNTAX      TruthValue
    MAX-ACCESS  read-create
    STATUS      current
    DESCRIPTION
        "the value of tmnxWaveTrackerEncodeEnable specifies whether or not
         the Wavelength Tracker Encoding of Wave Keys on the interface's
         transmitted optical signal is enabled.

         tmnxWaveTrackerEncodeEnable is equivalent to
         'tnWaveKeyEncodeTransmitState' of the 1696-Roadm MIBs."
    DEFVAL { false }
    ::= { tmnxWaveTrackerEntry 2 }

tmnxWaveTrackerInUse             OBJECT-TYPE
    SYNTAX      TruthValue
    MAX-ACCESS  read-only
    STATUS      current
    DESCRIPTION
        "The value of tmnxWaveTrackerInUse indicates whether or not the
         Wavelength Tracker feature is in use by the system for services.

         tmnxWaveTrackerInUse is equivalent to
         'tnWtEncodePortCapabilityInUse' of the 1696-Roadm MIBs."
    DEFVAL { false }
    ::= {  tmnxWaveTrackerEntry 3 }

tmnxWaveTrackerTargetPower       OBJECT-TYPE
    SYNTAX      Integer32 (-2200..300)
    UNITS       "mBm"
    MAX-ACCESS  read-create
    STATUS      current
    DESCRIPTION
        "The value of tmnxWaveTrackerTargetPower specifies the desired average
         output power of the interface's transmitted optical signal when
         tmnxWaveTrackerPowerCtrlEnable is set to 'true (1)'.

         The UNITS millibels (mBm) are units of 0.01 decibel relative
         to one milliwatt (0 dBm) or dBm multiplied by 100.
         The mBm is used when integers are required instead of floating point.
         For example: -5.21 dBm is equivalent to -521 mBm."
    DEFVAL { -2000 }
    ::= { tmnxWaveTrackerEntry 4 }

tmnxWaveTrackerWaveKey1          OBJECT-TYPE
    SYNTAX      Unsigned32 (0..4095)
    MAX-ACCESS  read-create
    STATUS      current
    DESCRIPTION
        "The value of tmnxWaveTrackerWaveKey1 specifies the first Wavelength
         Tracker Key (or Identifier) to be transmitted on the interface's
         optical signal when tmnxWaveTrackerEncodeEnable is set to 'true (1)'.

         The following table describes the possible tmnxWaveTrackerWaveKey1
         and tmnxWaveTrackerWaveKey2 values based on ITU channel. Key1 and
         Key2 must also match in modulo 2 with each other.

         Index   ITU          Key 1        Key 2
                channel   First Last      First Last
         -------------------------------------------
            0      61     1548  1548      2032  2032  // 1696 Test Channel

            // Original Tropic Channels (index 1 to 32)
            1      59        1    15       545   559
            2      58       18    32       562   576
            3      57       35    49       579   593
            4      56       52    66       596   610
            5      54       69    83       613   627
            6      53       86   100       630   644
            7      52      103   117       647   661
            8      51      120   134       664   678
            9      49      137   151       681   698
           10      48      154   168       698   712
           11      47      171   185       715   729
           12      46      188   202       732   746
           13      44      205   219       749   763
           14      43      222   236       766   780
           15      42      239   253       783   797
           16      41      256   270       800   814
           17      39      273   287       817   831
           18      38      290   304       834   848
           19      37      307   321       851   865
           20      36      324   338       868   882
           21      34      341   355       885   899
           22      33      358   372       902   916
           23      32      375   389       919   933
           24      31      392   406       936   950
           25      29      409   423       953   967
           26      28      426   440       970   984
           27      27      443   457       987  1001
           28      26      460   474      1004  1018
           29      24      477   491      1021  1035
           30      23      494   508      1038  1052
           31      22      511   525      1055  1069
           32      21      528   542      1072  1086

           // 1696 Extension 42 channels (index 33 to 42)
           33      60     1089  1103      1573  1587
           34      55     1106  1120      1590  1604
           35      50     1123  1137      1607  1621
           36      45     1140  1154      1624  1638
           37      40     1157  1171      1641  1655
           38      35     1174  1188      1658  1672
           39      30     1191  1205      1675  1689
           40      25     1208  1222      1692  1706
           41      20     1225  1239      1709  1723
           42      19     1242  1256      1726  1740

           // 1830 Extension to 44 channels (index 43 and 44)
           43      18     1259  1273      1743  1757
           44      17     1276  1290      1760  1774
           
           // 1830 Extension to 88 channels (index 45 to 88)
           45     595     1293  1307      1777  1791
           46     585     1310  1324      1794  1808
           47     575     1327  1341      1811  1825
           48     565     1344  1358      1828  1842
           49     545     1361  1375      1845  1859
           50     535     1378  1392      1862  1876
           51     525     1395  1409      1879  1893
           52     515     1412  1426      1896  1910
           53     495     1429  1443      1913  1927
           54     485     1446  1460      1930  1944
           55     475     1463  1477      1947  1961
           56     465     1480  1494      1964  1978
           57     445     1497  1511      1981  1995
           58     435     1514  1528      1998  2012
           59     425     1531  1545      2015  2029
           60     415     1548  1562      2032  2046
           61     395     3585  3599      2049  2063
           62     385     3602  3616      2066  2080
           63     375     3619  3633      2083  2097
           64     365     3636  3650      2100  2114
           65     345     3653  3667      2117  2131
           66     335     3670  3684      2134  2148
           67     325     3687  3701      2151  2165
           68     315     3704  3718      2168  2182
           69     295     3721  3735      2185  2199
           70     285     3738  3752      2202  2216
           71     275     3755  3769      2219  2233
           72     265     3772  3786      2236  2250
           73     245     3789  3803      2253  2267
           74     235     3806  3820      2270  2284
           75     225     3823  3837      2287  2301
           76     215     3840  3854      2304  2318
           77     605     3857  3871      2321  2335
           78     555     3874  3888      2338  2352
           79     505     3891  3905      2355  2369
           80     455     3908  3922      2372  2386
           81     405     3434  3448      3946  3960
           82     355     3451  3465      3963  3977
           83     305     3468  3482      3980  3994
           84     255     3485  3499      3997  4011
           85     205     3502  3516      4014  4028
           86     195     3519  3533      4031  4045
           87     185     3536  3550      4048  4062
           88     175     3553  3567      4065  4079
         -------------------------------------------"
    DEFVAL { 0 }
    ::= { tmnxWaveTrackerEntry 5 }

tmnxWaveTrackerWaveKey2          OBJECT-TYPE
    SYNTAX      Unsigned32 (0..4095)
    MAX-ACCESS  read-create
    STATUS      current
    DESCRIPTION
        "the value of tmnxWaveTrackerWaveKey2 specifies the second Wavelength
         Tracker Key (or Identifier) to be transmitted on the interface's
         optical signal when tmnxWaveTrackerEncodeEnable is set to 'true (1)'.

         Refer to the description of tmnxWaveTrackerWaveKey1 for the valid
         values based on the ITU channel."
    DEFVAL { 0 }
    ::= { tmnxWaveTrackerEntry 6 }

tmnxWaveTrackerTrailName         OBJECT-TYPE
    SYNTAX         SnmpAdminString (SIZE(0..80))
    MAX-ACCESS     read-only
    STATUS         current
    DESCRIPTION
        "The value of tmnxWaveTrackerTrailName indicates the trail name of the
         encode point. This trail is usually transmitted in the OTU pm-tti.

         tmnxWaveTrackerTrailName is equivalent to
         'tnWaveKeyEncodeTrailName' of the 1696-Roadm MIBs."
    ::= { tmnxWaveTrackerEntry 7 }

tmnxWaveTrackerCfgAlarms         OBJECT-TYPE
    SYNTAX      TmnxWaveTrackerAlarm
    MAX-ACCESS  read-create
    STATUS      current
    DESCRIPTION
        "The value of tmnxWaveTrackerCfgAlarms specifies the alarms that are to
         be monitored by the Wavelength Tracker interface. If an alarm bit is
         set, then the corresponding alarm will generate a raise or clear
         notification when its state changes. An unset bit specifies that the
         alarm corresponding with the bit will not report on its state
         transitions."
    DEFVAL { {encFail, encDegr, pwrFail, pwrDegr, pwrHigh, pwrLow, missing} }
    ::= { tmnxWaveTrackerEntry 8 }

tmnxWaveTrackerAlarmState        OBJECT-TYPE
    SYNTAX      TmnxWaveTrackerAlarm
    MAX-ACCESS  read-only
    STATUS      current
    DESCRIPTION
        "The value of tmnxWaveTrackerAlarmState indicates which monitored alarms
         are raised against the Wavelength Tracker interface."
    ::= { tmnxWaveTrackerEntry 9 }

tmnxWaveTrackerMeasuredPower     OBJECT-TYPE
    SYNTAX      Integer32
    UNITS       "mBm"
    MAX-ACCESS  read-only
    STATUS      current
    DESCRIPTION
        "tmnxWaveTrackerMeasuredPower indicates the current average output
         power of the interface's transmitted optical signal.

         The UNITS mBm are units of 0.01 dBm or dBm multiplied by 100.
         The mBm is used when integers are required instead of floating point.
         For example: -5.21 dBm is equivalent to -521 mBm."
    ::= { tmnxWaveTrackerEntry 10 }

tmnxWaveTrackerMaxAttainablePwr  OBJECT-TYPE
    SYNTAX      Integer32
    UNITS       "mBm"
    MAX-ACCESS  read-only
    STATUS      current
    DESCRIPTION
        "tmnxWaveTrackerMaxAttainablePwr indicates the maximum average output
         power of the interface's transmitted optical signal at end of life.

         The UNITS mBm are units of 0.01 dBm or dBm multiplied by 100.
         The mBm is used when integers are required instead of floating point.
         For example: -5.21 dBm is equivalent to -521 mBm."
    ::= { tmnxWaveTrackerEntry 11 }

tmnxWaveTrackerMinAttainablePwr  OBJECT-TYPE
    SYNTAX      Integer32
    UNITS       "mBm"
    MAX-ACCESS  read-only
    STATUS      current
    DESCRIPTION
        "tmnxWaveTrackerMinAttainablePwr indicates the minimum average output
         power of the interface's transmitted optical signal at end of life.

         The UNITS mBm are units of 0.01 dBm or dBm multiplied by 100.
         The mBm is used when integers are required instead of floating point.
         For example: -5.21 dBm is equivalent to -521 mBm."
    ::= { tmnxWaveTrackerEntry 12 }

tmnxWaveTrackerUpperPowerMargin  OBJECT-TYPE
    SYNTAX      Unsigned32
    UNITS       "mB"
    MAX-ACCESS  read-only
    STATUS      current
    DESCRIPTION
        "tmnxWaveTrackerUpperPowerMargin indicates how much the average output
         power of the interface's transmitted optical signal can be increased.

         The UNITS millibels (mB) are units of 0.01 dB or dB multiplied by 100.
         The mB is used when integers are required instead of floating point.
         For example: 5.21 dB is equivalent to 521 mB."
    ::= { tmnxWaveTrackerEntry 13 }

tmnxWaveTrackerLowerPowerMargin  OBJECT-TYPE
    SYNTAX      Unsigned32
    UNITS       "mB"
    MAX-ACCESS  read-only
    STATUS      current
    DESCRIPTION
        "tmnxWaveTrackerLowerPowerMargin indicates how much the average output
         power of the interface's transmitted optical signal can be decreased.

         The UNITS mBm are units of 0.01 dB or dB multiplied by 100.
         The mB is used when integers are required instead of floating point.
         For example: 5.21 dB is equivalent to 521 mB."
    ::= { tmnxWaveTrackerEntry 14 }

tmnxWaveTrackerPortType          OBJECT-TYPE
    SYNTAX      INTEGER {
                    unknown(0),
                    fixed(1),
                    pluggable(2)
                }
    MAX-ACCESS  read-only
    STATUS      current
    DESCRIPTION
        "The value of tmnxWaveTrackerPortType indicates if the port is fixed or
         if it supports pluggable equipment."
    ::= { tmnxWaveTrackerEntry 15 }

tmnxWaveTrackerSfpVoaEquipped    OBJECT-TYPE
    SYNTAX      TruthValue
    MAX-ACCESS  read-only
    STATUS      current
    DESCRIPTION
        "The value of tmnxWaveTrackerSfpVoaEquipped indicates whether or not an
         SFP VOA is present."
    ::= { tmnxWaveTrackerEntry 16 }

tmnxWaveTrackerSfpVoaType        OBJECT-TYPE
    SYNTAX      INTEGER {
                    none(0),
                    fast(1),
                    slow(2)
                }
    MAX-ACCESS  read-only
    STATUS      current
    DESCRIPTION
        "The value of tmnxWaveTrackerSfpVoaType indicates if the SFP VOA is
         fast or slow."
    ::= { tmnxWaveTrackerEntry 17 }

tmnxWaveTrackerSfpVoaSerialNum   OBJECT-TYPE
    SYNTAX       TNamedItemOrEmpty
    MAX-ACCESS   read-only
    STATUS       current
    DESCRIPTION
        "The value of tmnxWaveTrackerSfpVoaSerialNum indicates the serial
         number information for the SFP VOA.

         The string is expected to contain printable ASCII characters, but
         unprintable ASCII characters read from the EEPROM are not
         filtered out."
    ::= { tmnxWaveTrackerEntry 18 }

tmnxWaveTrackerSfpVoaModelNum    OBJECT-TYPE
    SYNTAX       TNamedItemOrEmpty
    MAX-ACCESS   read-only
    STATUS       current
    DESCRIPTION
        "The value of tmnxWaveTrackerSfpVoaModelNum indicates the model
         information for the SFP VOA.

         The string is expected to contain printable ASCII characters, but
         unprintable ASCII characters read from the EEPROM are not
         filtered out."
    ::= { tmnxWaveTrackerEntry 19 }

--
-- access egress queue group host match table
--

tPortAccEgrQGrpHMTableLastChgd OBJECT-TYPE
    SYNTAX       TimeStamp
    MAX-ACCESS   read-only
    STATUS       current
    DESCRIPTION
        "The value of tPortAccEgrQGrpHMTableLastChgd indicates the
        timestamp of last change to the tPortAccEgrQGrpHostMatchTable."
    ::= { tmnxPortObjs 49 }

tPortAccEgrQGrpHostMatchTable OBJECT-TYPE
    SYNTAX       SEQUENCE OF TPortAccEgrQGrpHostMatchEntry
    MAX-ACCESS   not-accessible
    STATUS       current
    DESCRIPTION
        "The value of tPortAccEgrQGrpHostMatchTable defines a 
         set of string values optionally used by subscriber 
         management to map subscriber's and subscriber host's
         policed traffic to a specific egress port queue group."
    ::= { tmnxPortObjs 50 }

tPortAccEgrQGrpHostMatchEntry OBJECT-TYPE
    SYNTAX       TPortAccEgrQGrpHostMatchEntry
    MAX-ACCESS   not-accessible
    STATUS       current
    DESCRIPTION
        "The value of tPortAccEgrQGrpHostMatchEntry defines an entry in the
         tPortAccEgrQGrpHostMatchTable.

        Entries are created/deleted in this table by SNMP sets to
        tPortAccEgrQGrpHMRowStatus."
    INDEX { tmnxChassisIndex, tmnxPortPortID, tPortAccEgrQGrpName,
            tPortAccEgrQGrpInstanceId, tPortAccEgrQGrpHMIntDestId,
            tPortAccEgrQGrpHMOrgString }
    ::= { tPortAccEgrQGrpHostMatchTable 1 }

TPortAccEgrQGrpHostMatchEntry ::= SEQUENCE
    {
        tPortAccEgrQGrpHMIntDestId      TmnxSubMgtIntDestId,
        tPortAccEgrQGrpHMOrgString      TmnxSubMgtOrgStrOrZero,
        tPortAccEgrQGrpHMRowStatus      RowStatus,
        tPortAccEgrQGrpHMLastChgd       TimeStamp
    }

tPortAccEgrQGrpHMIntDestId OBJECT-TYPE
    SYNTAX       TmnxSubMgtIntDestId
    MAX-ACCESS   not-accessible
    STATUS       current
    DESCRIPTION
        "The value of tPortAccEgrQGrpHMIntDestId defines the 
         intermediate destination id to match on."
    ::= { tPortAccEgrQGrpHostMatchEntry 1 }

tPortAccEgrQGrpHMOrgString OBJECT-TYPE
    SYNTAX       TmnxSubMgtOrgStrOrZero
    MAX-ACCESS   not-accessible
    STATUS       current
    DESCRIPTION
        "The value of tPortAccEgrQGrpHMOrgString defines the 
         organization string to match on.
         
         If tPortAccEgrQGrpHMOrgString is the empty string (''), 
         every subscriber with an organization string will not 
         match this entry.

         If tPortAccEgrQGrpHMOrgString is the wildcard symbol ('*'),
         every subscriber with an organization string will match
         this entry, if the tPortAccEgrQGrpHMIntDestId matches.
         
         Currently only the empty string ('') is accepted."
    ::= { tPortAccEgrQGrpHostMatchEntry 2 }

tPortAccEgrQGrpHMRowStatus OBJECT-TYPE
    SYNTAX       RowStatus
    MAX-ACCESS   read-create
    STATUS       current
    DESCRIPTION
        "The value of tPortAccEgrQGrpHMRowStatus allows entries to be
        created and deleted in the tPortAccEgrQGrpHostMatchTable.

        The creation of an entry in this table will succeed only if the
        queue-group being created exist in TIMETRA-QOS-MIB::tQosEgrQGroupTable."
    REFERENCE
        "See definition of RowStatus in RFC 2579, 'Textual Conventions for
         SMIv2.'"
    ::= { tPortAccEgrQGrpHostMatchEntry 3 }

tPortAccEgrQGrpHMLastChgd OBJECT-TYPE
    SYNTAX       TimeStamp
    MAX-ACCESS   read-only
    STATUS       current
    DESCRIPTION
        "The value of tPortAccEgrQGrpHMLastChgd indicates the value of
        sysUpTime when the host match entry was last modified."
    ::= { tPortAccEgrQGrpHostMatchEntry 4 }

--
-- Queue Group Scheduler Statistics (Ingress)
--
tPortAccIngSchedStatTable OBJECT-TYPE
    SYNTAX       SEQUENCE OF TPortAccIngSchedStatEntry
    MAX-ACCESS   not-accessible
    STATUS       current
    DESCRIPTION
        "The value of tPortAccIngSchedStatTable defines access Ingress Queue
         Group related statistics per scheduler."
    ::= { tmnxPortObjs 51 }

tPortAccIngSchedStatEntry OBJECT-TYPE
    SYNTAX       TPortAccIngSchedStatEntry
    MAX-ACCESS   not-accessible
    STATUS       current
    DESCRIPTION
        "The value of tPortAccIngSchedStatEntry defines an entry in the
         tPortAccIngSchedStatTable. It represents statistics about a 
         specific QoS ingress queue group scheduler on the port specified by
         tPortAccIngSchedStatName on the access side."
    INDEX { tmnxChassisIndex, tmnxPortPortID,
            tPortAccIngQGrpName, tPortAccIngSchedStatName}
    ::= { tPortAccIngSchedStatTable 1 }

TPortAccIngSchedStatEntry ::= SEQUENCE
    {
        tPortAccIngSchedStatName             TNamedItem,
        tPortAccIngSchedStatFwdPkts          Counter64,
        tPortAccIngSchedStatFwdPktsHi        Counter32,
        tPortAccIngSchedStatFwdPktsLo        Counter32,
        tPortAccIngSchedStatFwdOcts          Counter64,
        tPortAccIngSchedStatFwdOctsHi        Counter32,
        tPortAccIngSchedStatFwdOctsLo        Counter32
    }

tPortAccIngSchedStatName OBJECT-TYPE
    SYNTAX       TNamedItem
    MAX-ACCESS   not-accessible
    STATUS       current
    DESCRIPTION
        "The value of tPortAccEgrSchedStatName indicates the scheduler
         associated with this queue group on this port."
    ::= { tPortAccIngSchedStatEntry 1 }

tPortAccIngSchedStatFwdPkts OBJECT-TYPE
    SYNTAX      Counter64
    MAX-ACCESS  read-only
    STATUS      current
    DESCRIPTION
        "The value of tPortAccIngSchedStatFwdPkts indicates the number of 
         forwarded packets by this port on this queue-group using this
         scheduler."
    ::= { tPortAccIngSchedStatEntry 2 }

tPortAccIngSchedStatFwdPktsHi OBJECT-TYPE
    SYNTAX      Counter32
    MAX-ACCESS  read-only
    STATUS      current
    DESCRIPTION
        "The value of tPortAccIngSchedStatFwdPktsHi indicates upper 32 bits of
         tPortAccIngSchedStatFwdPkts object."
    ::= { tPortAccIngSchedStatEntry 3 }

tPortAccIngSchedStatFwdPktsLo OBJECT-TYPE
    SYNTAX      Counter32
    MAX-ACCESS  read-only
    STATUS      current
    DESCRIPTION
        "The value of tPortAccIngSchedStatFwdPktsLo indicates lower 32 bits of
         tPortAccIngSchedStatFwdPkts object."
    ::= { tPortAccIngSchedStatEntry 4 }

tPortAccIngSchedStatFwdOcts OBJECT-TYPE
    SYNTAX      Counter64
    MAX-ACCESS  read-only
    STATUS      current
    DESCRIPTION
        "The value of tPortAccIngSchedStatFwdOcts indicates the number of 
         forwarded octets by this port on this queue-group using this
         scheduler."
    ::= { tPortAccIngSchedStatEntry 5 }

tPortAccIngSchedStatFwdOctsHi OBJECT-TYPE
    SYNTAX      Counter32
    MAX-ACCESS  read-only
    STATUS      current
    DESCRIPTION
        "The value of tPortAccIngSchedStatFwdOctsHi indicates upper 32 bits of
         tPortAccIngSchedStatFwdOcts object."
    ::= { tPortAccIngSchedStatEntry 6 }

tPortAccIngSchedStatFwdOctsLo OBJECT-TYPE
    SYNTAX      Counter32
    MAX-ACCESS  read-only
    STATUS      current
    DESCRIPTION
        "The value of tPortAccIngSchedStatFwdOctsLo indicates lower 32 bits of
         tPortAccIngSchedStatFwdOcts object."
    ::= { tPortAccIngSchedStatEntry 7 }

--
-- Queue Group Scheduler Statistics (Egress)
--
tPortAccEgrSchedStatTable OBJECT-TYPE
    SYNTAX       SEQUENCE OF TPortAccEgrSchedStatEntry
    MAX-ACCESS   not-accessible
    STATUS       current
    DESCRIPTION
        "The value of tPortAccEgrSchedStatTable defines access Egress Queue
         Group related statistics per scheduler."
    ::= { tmnxPortObjs 52 }

tPortAccEgrSchedStatEntry OBJECT-TYPE
    SYNTAX       TPortAccEgrSchedStatEntry
    MAX-ACCESS   not-accessible
    STATUS       current
    DESCRIPTION
        "The value of tPortAccEgrSchedStatEntry defines an entry in the
         tPortAccEgrSchedStatTable. It represents statistics about a 
         specific QoS egress queue group scheduler on the port specified by
         tPortAccEgrSchedStatName on the access side.

         In release 11.0, tPortAccEgrQGrpInstanceId is added as another index 
         before tPortAccEgrSchedStatName for this tPortAccEgrSchedStatTable."
    INDEX { tmnxChassisIndex, tmnxPortPortID,
            tPortAccEgrQGrpName, tPortAccEgrQGrpInstanceId,
            tPortAccEgrSchedStatName}
    ::= { tPortAccEgrSchedStatTable 1 }

TPortAccEgrSchedStatEntry ::= SEQUENCE
    {
        tPortAccEgrSchedStatName             TNamedItem,
        tPortAccEgrSchedStatFwdPkts          Counter64,
        tPortAccEgrSchedStatFwdPktsHi        Counter32,
        tPortAccEgrSchedStatFwdPktsLo        Counter32,
        tPortAccEgrSchedStatFwdOcts          Counter64,
        tPortAccEgrSchedStatFwdOctsHi        Counter32,
        tPortAccEgrSchedStatFwdOctsLo        Counter32
    }

tPortAccEgrSchedStatName OBJECT-TYPE
    SYNTAX       TNamedItem
    MAX-ACCESS   not-accessible
    STATUS       current
    DESCRIPTION
        "The value of tPortAccEgrSchedStatName indicates the scheduler
         associated with this queue group on this port."
    ::= { tPortAccEgrSchedStatEntry 1 }

tPortAccEgrSchedStatFwdPkts OBJECT-TYPE
    SYNTAX      Counter64
    MAX-ACCESS  read-only
    STATUS      current
    DESCRIPTION
        "The value of tPortAccEgrSchedStatFwdPkts indicates the number of 
         forwarded packets by this port on this queue-group using this
         scheduler."
    ::= { tPortAccEgrSchedStatEntry 2 }

tPortAccEgrSchedStatFwdPktsHi OBJECT-TYPE
    SYNTAX      Counter32
    MAX-ACCESS  read-only
    STATUS      current
    DESCRIPTION
        "The value of tPortAccEgrSchedStatFwdPktsHi indicates upper 32 bits of
         tPortAccEgrSchedStatFwdPkts object."
    ::= { tPortAccEgrSchedStatEntry 3 }

tPortAccEgrSchedStatFwdPktsLo OBJECT-TYPE
    SYNTAX      Counter32
    MAX-ACCESS  read-only
    STATUS      current
    DESCRIPTION
        "The value of tPortAccEgrSchedStatFwdPktsLo indicates lower 32 bits of
         tPortAccEgrSchedStatFwdPkts object."
    ::= { tPortAccEgrSchedStatEntry 4 }

tPortAccEgrSchedStatFwdOcts OBJECT-TYPE
    SYNTAX      Counter64
    MAX-ACCESS  read-only
    STATUS      current
    DESCRIPTION
        "tPortAccEgrSchedStatFwdOcts indicates the number of forwarded octets
        by this port on this queue-group using this scheduler."
    ::= { tPortAccEgrSchedStatEntry 5 }

tPortAccEgrSchedStatFwdOctsHi OBJECT-TYPE
    SYNTAX      Counter32
    MAX-ACCESS  read-only
    STATUS      current
    DESCRIPTION
        "The value of tPortAccEgrSchedStatFwdOctsHi indicates upper 32 bits of
         tPortAccEgrSchedStatFwdOcts object."
    ::= { tPortAccEgrSchedStatEntry 6 }

tPortAccEgrSchedStatFwdOctsLo OBJECT-TYPE
    SYNTAX      Counter32
    MAX-ACCESS  read-only
    STATUS      current
    DESCRIPTION
        "The value of tPortAccEgrSchedStatFwdOctsLo indicates lower 32 bits of
         tPortAccEgrSchedStatFwdOcts object."
    ::= { tPortAccEgrSchedStatEntry 7 }

--
-- Queue Group Scheduler Statistics (Network-Egress)
--
tPortNetEgrSchedStatTable OBJECT-TYPE
    SYNTAX       SEQUENCE OF TPortNetEgrSchedStatEntry
    MAX-ACCESS   not-accessible
    STATUS       current
    DESCRIPTION
        "The value of tPortNetEgrSchedStatTable defines network Egress Queue
         Group related statistics per scheduler."
    ::= { tmnxPortObjs 53 }

tPortNetEgrSchedStatEntry OBJECT-TYPE
    SYNTAX       TPortNetEgrSchedStatEntry
    MAX-ACCESS   not-accessible
    STATUS       current
    DESCRIPTION
        "The value of tPortNetEgrSchedStatEntry defines an entry in the
         tPortNetEgrSchedStatTable. It represents statistics about a 
         specific QoS egress queue group scheduler on the port specified by
         tPortNetEgrSchedStatName on the network side."
    INDEX { tmnxChassisIndex, tmnxPortPortID,
            tPortNetEgrQGrpName, tPortNetEgrQGrpInstanceId,
            tPortNetEgrSchedStatName
          }
    ::= { tPortNetEgrSchedStatTable 1 }

TPortNetEgrSchedStatEntry ::= SEQUENCE
    {
        tPortNetEgrSchedStatName             TNamedItem,
        tPortNetEgrSchedStatFwdPkts          Counter64,
        tPortNetEgrSchedStatFwdPktsHi        Counter32,
        tPortNetEgrSchedStatFwdPktsLo        Counter32,
        tPortNetEgrSchedStatFwdOcts          Counter64,
        tPortNetEgrSchedStatFwdOctsHi        Counter32,
        tPortNetEgrSchedStatFwdOctsLo        Counter32
    }

tPortNetEgrSchedStatName OBJECT-TYPE
    SYNTAX       TNamedItem
    MAX-ACCESS   not-accessible
    STATUS       current
    DESCRIPTION
        "The value of tPortAccEgrSchedStatName indicates the scheduler
         associated with this queue group on this port."
    ::= { tPortNetEgrSchedStatEntry 1 }

tPortNetEgrSchedStatFwdPkts OBJECT-TYPE
    SYNTAX      Counter64
    MAX-ACCESS  read-only
    STATUS      current
    DESCRIPTION
        "The value of tPortNetEgrSchedStatFwdPkts indicates the number of 
         forwarded packets by this port on this queue-group using this
         scheduler."
    ::= { tPortNetEgrSchedStatEntry 2 }

tPortNetEgrSchedStatFwdPktsHi OBJECT-TYPE
    SYNTAX      Counter32
    MAX-ACCESS  read-only
    STATUS      current
    DESCRIPTION
        "The value of tPortNetEgrSchedStatFwdPktsHi indicates upper 32 bits of
         tPortNetEgrSchedStatFwdPkts object."
    ::= { tPortNetEgrSchedStatEntry 3 }

tPortNetEgrSchedStatFwdPktsLo OBJECT-TYPE
    SYNTAX      Counter32
    MAX-ACCESS  read-only
    STATUS      current
    DESCRIPTION
        "tPortNetEgrSchedStatFwdPktsLo indicates lower 32 bits of
        tPortNetEgrSchedStatFwdPkts object."
    ::= { tPortNetEgrSchedStatEntry 4 }

tPortNetEgrSchedStatFwdOcts OBJECT-TYPE
    SYNTAX      Counter64
    MAX-ACCESS  read-only
    STATUS      current
    DESCRIPTION
        "The value of tPortNetEgrSchedStatFwdOcts indicates the number of 
         forwarded octets by this port on this queue-group using this
         scheduler."
    ::= { tPortNetEgrSchedStatEntry 5 }

tPortNetEgrSchedStatFwdOctsHi OBJECT-TYPE
    SYNTAX      Counter32
    MAX-ACCESS  read-only
    STATUS      current
    DESCRIPTION
        "tPortNetEgrSchedStatFwdOctsHi indicates upper 32 bits of
        tPortNetEgrSchedStatFwdOcts object."
    ::= { tPortNetEgrSchedStatEntry 6 }

tPortNetEgrSchedStatFwdOctsLo OBJECT-TYPE
    SYNTAX      Counter32
    MAX-ACCESS  read-only
    STATUS      current
    DESCRIPTION
        "The value of tPortNetEgrSchedStatFwdOctsLo indicates lower 32 bits of
         tPortNetEgrSchedStatFwdOcts object."
    ::= { tPortNetEgrSchedStatEntry 7 }
---
--- port egress vport table
---

tPortEgrVPortTableLastChgd OBJECT-TYPE
    SYNTAX       TimeStamp
    MAX-ACCESS   read-only
    STATUS       current
    DESCRIPTION
        "The value of tPortEgrVPortTableLastChgd indicates the
        timestamp of last change to the tPortEgrVPortTable."
    ::= { tmnxPortObjs 54 }

tPortEgrVPortTable OBJECT-TYPE
    SYNTAX  SEQUENCE OF TPortEgrVPortEntry
    MAX-ACCESS  not-accessible
    STATUS      current
    DESCRIPTION
        "The tPortEgrVPortTable has an entry for each virtual port
        defined on this port."
    ::= { tmnxPortObjs 55 }

tPortEgrVPortEntry       OBJECT-TYPE
    SYNTAX  TPortEgrVPortEntry
    MAX-ACCESS      not-accessible
    STATUS  current
    DESCRIPTION
        "Each row entry represents a virtual port defined on the port for the
         chassis in the system."
    INDEX   { tmnxChassisIndex, tmnxPortPortID, tPortEgrVPortName }
    ::= { tPortEgrVPortTable 1 }

TPortEgrVPortEntry ::=
    SEQUENCE {
        tPortEgrVPortName                TNamedItem,
        tPortEgrVPortRowStatus           RowStatus,
        tPortEgrVPortLastChanged         TimeStamp,
        tPortEgrVPortDescr               TItemDescription,
        tPortEgrVPortSchedPol            TNamedItemOrEmpty,
        tPortEgrVPortAggRateLimit        TPortSchedulerAggRateLimitPIR,
        tPortEgrVPortEgrRateModify       TmnxEnabledDisabled,
        tPortEgrVPortEgrRateModifyDelta  Integer32,
        tPortEgrVPortQosSchedPolicy      TNamedItemOrEmpty,
        tPortEgrVPortAggRateLUB          TruthValue
    }

tPortEgrVPortName     OBJECT-TYPE
    SYNTAX      TNamedItem
    MAX-ACCESS  not-accessible
    STATUS      current
    DESCRIPTION
        "The value of tPortEgrVPortName is the name of the virtual port
        on this port."
    ::= { tPortEgrVPortEntry 1 }

tPortEgrVPortRowStatus     OBJECT-TYPE
    SYNTAX      RowStatus
    MAX-ACCESS  read-create
    STATUS      current
    DESCRIPTION
        "The value of tPortEgrVPortRowStatus specifies the row-status of
        this entry in this table."
    ::= { tPortEgrVPortEntry 2 }

tPortEgrVPortLastChanged     OBJECT-TYPE
    SYNTAX      TimeStamp
    MAX-ACCESS  read-only
    STATUS      current
    DESCRIPTION
        "The value of tPortEgrVPortLastChanged indicates the time-stamp
        of the last change in this entry."
    ::= { tPortEgrVPortEntry 3 }

tPortEgrVPortDescr     OBJECT-TYPE
    SYNTAX      TItemDescription
    MAX-ACCESS  read-create
    STATUS      current
    DESCRIPTION
        "The value of tPortEgrVPortDescr specifies the description of the
        virtual port."
    DEFVAL { ''H }
    ::= { tPortEgrVPortEntry 4 }

tPortEgrVPortSchedPol     OBJECT-TYPE
    SYNTAX      TNamedItemOrEmpty
    MAX-ACCESS  read-create
    STATUS      current
    DESCRIPTION
        "The value of tPortEgrVPortSchedPol specifies the name of the
        port scheduler policy assigned to this virtual port."
    DEFVAL { ''H }
    ::= { tPortEgrVPortEntry 5 }

tPortEgrVPortAggRateLimit     OBJECT-TYPE
    SYNTAX      TPortSchedulerAggRateLimitPIR
    UNITS       "kbps"
    MAX-ACCESS  read-create
    STATUS      current
    DESCRIPTION
        "The value of tPortEgrVPortAggRateLimit specifies the maximum
         total rate of all subscribers for this virtual port. 
         
         The value -1 means that there is no limit."
    DEFVAL { -1 }
    ::= { tPortEgrVPortEntry 6 }

tPortEgrVPortEgrRateModify OBJECT-TYPE
    SYNTAX      TmnxEnabledDisabled
    MAX-ACCESS  read-create
    STATUS      current
    DESCRIPTION
        "The value of tPortEgrVPortEgrRateModify specifies 
         if egress-rate modification is enabled.
         
         Egress-rate-modification takes the egress bandwidth already in use
         for multicast traffic into account while performing rate limiting
         according to the values of tPortEgrVPortAggRateLimit or tPortEgrVPortSchedPol,
         in order to avoid that the sum of unicast and multicast bandwidths would
         exceed the egress aggregate rate limit."
    DEFVAL { disabled }
    ::= { tPortEgrVPortEntry 12 }

tPortEgrVPortEgrRateModifyDelta     OBJECT-TYPE
    SYNTAX      Integer32
    UNITS       "kbps"
    MAX-ACCESS  read-only
    STATUS      current
    DESCRIPTION
        "The value of tPortEgrVPortEgrRateModifyDelta indicates
         the actual bandwidth correction applied while the value
         of the object tPortEgrVPortEgrRateModify is 'enabled'."
    ::= { tPortEgrVPortEntry 13 }


tPortEgrVPortQosSchedPolicy      OBJECT-TYPE
    SYNTAX      TNamedItemOrEmpty
    MAX-ACCESS  read-create
    STATUS      current
    DESCRIPTION
        "The value of tPortEgrVPortQosSchedPolicy specifies the QoS egress
         scheduler policy (from TIMETRA-QOS-MIB::tSchedulerPolicyTable)
         applicable to this virtual port."
    DEFVAL { ''H }
    ::= { tPortEgrVPortEntry 14 }

tPortEgrVPortAggRateLUB   OBJECT-TYPE
    SYNTAX      TruthValue
    MAX-ACCESS  read-create
    STATUS      current
    DESCRIPTION 
        "The value of tPortEgrVPortAggRateLUB specifies whether to limit
         the unused bandwidth and allow a tighter control in allocation of 
         bandwidth by HQos.

         When the value of tPortEgrVPortAggRateLUB is set to 'true', HQos
         algorithm distributes any unused aggregate bandwidth between queues
         operating below their fair share rates. This allows a simplified 
         aggregate rate protection while allocating bandwidth by HQos scheduling
         algorithm."
    DEFVAL { false }
    ::= { tPortEgrVPortEntry 15 }
    
--
-- port egress vport host match table
--

tPortEgrVPortHMTableLastChgd OBJECT-TYPE
    SYNTAX       TimeStamp
    MAX-ACCESS   read-only
    STATUS       current
    DESCRIPTION
        "The value of tPortEgrVPortHMTableLastChgd indicates the timestamp
         of last change to the tPortEgrVPortHostMatchTable."
        ::= { tmnxPortObjs 56 }

tPortEgrVPortHostMatchTable OBJECT-TYPE
    SYNTAX       SEQUENCE OF TPortEgrVPortHostMatchEntry
    MAX-ACCESS   not-accessible
    STATUS       current
    DESCRIPTION
        "The value of tPortEgrVPortHostMatchTable defines a set of string
         values optionally used by subscriber management to map subscriber's
         and subscriber host's queued traffic to a specific egress port
         virtual port."
        ::= { tmnxPortObjs 57 }

tPortEgrVPortHostMatchEntry OBJECT-TYPE
    SYNTAX       TPortEgrVPortHostMatchEntry
    MAX-ACCESS   not-accessible
    STATUS       current
    DESCRIPTION
        "The value of tPortEgrVPortHostMatchEntry defines an entry in the
         tPortEgrVPortHostMatchTable.

         Entries are created/deleted in this table by SNMP sets to
         tPortEgrVPortHMRowStatus."
    INDEX { tmnxChassisIndex, tmnxPortPortID, tPortEgrVPortName, 
            tPortEgrVPortHMIntDestId, tPortEgrVPortHMOrgString }
    ::= { tPortEgrVPortHostMatchTable 1 }

TPortEgrVPortHostMatchEntry ::= SEQUENCE
    {
        tPortEgrVPortHMIntDestId      TmnxSubMgtIntDestId,
        tPortEgrVPortHMOrgString      TmnxSubMgtOrgStrOrZero,
        tPortEgrVPortHMRowStatus      RowStatus,
        tPortEgrVPortHMLastChgd       TimeStamp
    }

tPortEgrVPortHMIntDestId OBJECT-TYPE
    SYNTAX       TmnxSubMgtIntDestId
    MAX-ACCESS   not-accessible
    STATUS       current
    DESCRIPTION
        "The value of tPortEgrVPortHMIntDestId defines the intermediate
         destination id to match on."
    ::= { tPortEgrVPortHostMatchEntry 1 }

tPortEgrVPortHMOrgString OBJECT-TYPE
    SYNTAX       TmnxSubMgtOrgStrOrZero
    MAX-ACCESS   not-accessible
    STATUS       current
    DESCRIPTION
        "The value of tPortEgrVPortHMOrgString defines the organization
         string to match on.
             
         If tPortEgrVPortHMOrgString is the empty string (''), every
         subscriber with an organization string will not match this entry.

         If tPortEgrVPortHMOrgString is the wildcard symbol ('*'), every
         subscriber with an organization string will match this entry, if
         the tPortEgrVPortHMIntDestId matches.
             
         Currently only the empty string ('') is accepted."
    ::= { tPortEgrVPortHostMatchEntry 2 }

tPortEgrVPortHMRowStatus OBJECT-TYPE
    SYNTAX       RowStatus
    MAX-ACCESS   read-create
    STATUS       current
    DESCRIPTION
        "The value of tPortEgrVPortHMRowStatus allows entries to be created
         and deleted in the tPortEgrVPortHostMatchTable."

    REFERENCE
        "See definition of RowStatus in RFC 2579, 'Textual Conventions for
         SMIv2.'"
    ::= { tPortEgrVPortHostMatchEntry 3 }

tPortEgrVPortHMLastChgd OBJECT-TYPE
    SYNTAX       TimeStamp
    MAX-ACCESS   read-only
    STATUS       current
    DESCRIPTION
        "The value of tPortEgrVPortHMLastChgd indicates the value of
         sysUpTime when the host match entry was last modified."
    ::= { tPortEgrVPortHostMatchEntry 4 }

--
--  Optical Ports Configuration Table
--
tmnxOpticalPortCfgTable OBJECT-TYPE
    SYNTAX      SEQUENCE OF TmnxOpticalPortCfgEntry
    MAX-ACCESS  not-accessible
    STATUS      current
    DESCRIPTION
        "The tmnxOpticalPortCfgTable has an entry for each DWDM Optical
         port on each IOM card in each chassis in the Alcatel SROS system."
    ::= { tmnxPortObjs 58 }

tmnxOpticalPortCfgEntry OBJECT-TYPE
    SYNTAX      TmnxOpticalPortCfgEntry
    MAX-ACCESS  not-accessible
    STATUS      current
    DESCRIPTION
        "Each row entry represents an Optical port on a IOM card in a
         chassis in the system. Entries cannot be created and deleted via
         SNMP SET operations. The tmnxOpticalPortCfgEntry contains attributes
         that are unique to the Optical ports."

    INDEX   { tmnxChassisIndex, tmnxPortPortID }
    ::= { tmnxOpticalPortCfgTable 1 }

TmnxOpticalPortCfgEntry          ::= SEQUENCE {
      tmnxOpticalPortAmpCfgAlarms      TmnxOpticalAmpAlarm,
      tmnxOpticalPortTdcmCtrlMode      TmnxOpticalDispCtrlMode,
      tmnxOpticalPortTdcmManCfgDisp    Integer32,
      tmnxOpticalPortTdcmCfgRxChan     TmnxOpticalDwdmChannel,
      tmnxOpticalPortTdcmCfgAlarms     TmnxOpticalTdcmAlarm,
      tmnxOpticalPortTdcmDispSwpStart  Integer32,
      tmnxOpticalPortTdcmDispSwpEnd    Integer32
}

tmnxOpticalPortAmpCfgAlarms      OBJECT-TYPE
    SYNTAX      TmnxOpticalAmpAlarm
    MAX-ACCESS  read-write
    STATUS      current
    DESCRIPTION
        "The value of tmnxOpticalPortAmpCfgAlarms specifies the alarms that are
         monitored by the optical amplifier interface. If an alarm bit is
         set, then the corresponding alarm will generate a raise or clear
         notification when its state changes. An unset bit specifies that the
         alarm corresponding with the bit will not report on its state
         transitions."
    DEFVAL { {ampIld, ampTmp, ampMth, ampMtl, ampLos, ampLop, ampCom} }
    ::= { tmnxOpticalPortCfgEntry 1 }

tmnxOpticalPortTdcmCtrlMode   OBJECT-TYPE 
    SYNTAX      TmnxOpticalDispCtrlMode
    MAX-ACCESS  read-write
    STATUS      current
    DESCRIPTION
        "The value of tmnxOpticalPortTdcmCtrlMode specifies the current
         operational mode of the tunable dispersion compensation module.

         When tmnxOpticalPortTdcmCtrlMode is set to automatic, the dispersion
         setpoint can be retrieved from tmnxOpticalPortTdcmAutoDisp.

         When tmnxOpticalPortTdcmCtrlMode is set to manual, the dispersion
         setpoint can be configured with tmnxOpticalPortTdcmManCfgDisp."
    DEFVAL { automatic }
    ::= { tmnxOpticalPortCfgEntry 2 }

tmnxOpticalPortTdcmManCfgDisp OBJECT-TYPE
    SYNTAX      Integer32 (-1200..1200)
    UNITS       "picoseconds per nanometer"
    MAX-ACCESS  read-write
    STATUS      current
    DESCRIPTION
        "The value of tmnxOpticalPortTdcmManCfgDisp specifies the
         manually configured dispersion of the tunable dispersion
         compensation module. This parameter is valid when the
         tmnxOpticalPortTdcmCtrlMode is manual.
         Dispersion is expressed in pico-seconds per nano-meter (ps/nm)."
    DEFVAL { 0 }
    ::= { tmnxOpticalPortCfgEntry 3 }

tmnxOpticalPortTdcmCfgRxChan  OBJECT-TYPE
    SYNTAX      TmnxOpticalDwdmChannel
    MAX-ACCESS  read-write
    STATUS      current
    DESCRIPTION
        "tmnxOpticalPortTdcmCfgRxChan specifies the DWDM ITU channel at which
         the tunable dispersion compensation module should operate.

         If a value of zero(0) has been specified,
         tmnxOpticalPortTdcmPresRxChan will be changed by the system to be
         equivalent to tmnxPortDwdmLaserChannel.

         tmnxOpticalPortTdcmCfgRxChan should be set to the same value as
         tmnxPortDwdmLaserChannel in most cases, but may be set to a different
         value when the received wavelength is different from the transmitted
         wavelength."
    DEFVAL { 0 }
    ::= { tmnxOpticalPortCfgEntry 4 }

tmnxOpticalPortTdcmCfgAlarms     OBJECT-TYPE
    SYNTAX      TmnxOpticalTdcmAlarm
    MAX-ACCESS  read-write
    STATUS      current
    DESCRIPTION
        "The value of tmnxOpticalPortTdcmCfgAlarms specifies the alarms that
         are monitored by the tunable dispersion compensation module's
         interface. If an alarm bit is set, then the corresponding alarm will
         generate a raise or clear notification when its state changes.
         An unset bit specifies that the alarm corresponding with the bit
         will not report on its state transitions."
    DEFVAL { {tdcmNotRdy, tdcmMth, tdcmMtl, tdcmUnLck, 
              tdcmTmpLim, tdcmEprInv, tdcmCom} }
    ::= { tmnxOpticalPortCfgEntry 5 }

tmnxOpticalPortTdcmDispSwpStart OBJECT-TYPE
    SYNTAX      Integer32 (-1200..1200)
    UNITS       "picoseconds per nanometer"
    MAX-ACCESS  read-write
    STATUS      current
    DESCRIPTION
        "The value of tmnxOpticalPortTdcmDispSwpStart specifies the
         the start value for dispersion sweeping on a tunable dispersion
         compensation module. Dispersion is expressed in pico-seconds per
         nano-meter (ps/nm)."
    DEFVAL { -1200 }
    ::= { tmnxOpticalPortCfgEntry 6 }

tmnxOpticalPortTdcmDispSwpEnd OBJECT-TYPE
    SYNTAX      Integer32 (-1200..1200)
    UNITS       "picoseconds per nanometer"
    MAX-ACCESS  read-write
    STATUS      current
    DESCRIPTION
        "The value of tmnxOpticalPortTdcmDispSwpEnd specifies the
         the end value for dispersion sweeping on a tunable dispersion
         compensation module. Dispersion is expressed in pico-seconds per
         nano-meter (ps/nm)."
    DEFVAL { 1200 }
    ::= { tmnxOpticalPortCfgEntry 7 }

--
--  Optical Ports Operational Table
--
tmnxOpticalPortOperTable OBJECT-TYPE
    SYNTAX      SEQUENCE OF TmnxOpticalPortOperEntry
    MAX-ACCESS  not-accessible
    STATUS      current
    DESCRIPTION
        "The tmnxOpticalPortOperTable has an entry for each DWDM Optical
         port on each IOM card in each chassis in the Alcatel SROS system."
    ::= { tmnxPortObjs 59 }

tmnxOpticalPortOperEntry OBJECT-TYPE
    SYNTAX      TmnxOpticalPortOperEntry
    MAX-ACCESS  not-accessible
    STATUS      current
    DESCRIPTION
        "Each row entry represents an Optical port on a IOM card in a
         chassis in the system. The tmnxOpticalPortOperEntry contains
         attributes that are unique to the Optical ports."

    INDEX   { tmnxChassisIndex, tmnxPortPortID }
    ::= { tmnxOpticalPortOperTable 1 }

TmnxOpticalPortOperEntry         ::= SEQUENCE {
      tmnxOpticalPortHasRxAmplifier    TruthValue,
      tmnxOpticalPortHasRxTdcm         TruthValue,
      tmnxOpticalPortAmpPowerIn        Integer32,
      tmnxOpticalPortAmpGain           Unsigned32,
      tmnxOpticalPortAmpPowerOut       Integer32,
      tmnxOpticalPortAmpPumpTemp       Integer32,
      tmnxOpticalPortAmpModuleTemp     Integer32,
      tmnxOpticalPortAmpPumpCurrent    Unsigned32,
      tmnxOpticalPortAmpAlarmState     TmnxOpticalAmpAlarm,
      tmnxOpticalPortAmpSerialNum      SnmpAdminString,
      tmnxOpticalPortAmpCtrlState      TmnxOpticalAmpCtrlState,
      tmnxOpticalPortTdcmPowerIn       Integer32,
      tmnxOpticalPortTdcmLoss          Unsigned32,
      tmnxOpticalPortTdcmPowerOut      Integer32,
      tmnxOpticalPortTdcmRtd1Temp      Integer32,
      tmnxOpticalPortTdcmRtd2Temp      Integer32,
      tmnxOpticalPortTdcmRtd3Temp      Integer32,
      tmnxOpticalPortTdcmRtd4Temp      Integer32,
      tmnxOpticalPortTdcmModuleTemp    Integer32,
      tmnxOpticalPortTdcmMinDisp       Integer32,
      tmnxOpticalPortTdcmMaxDisp       Integer32,
      tmnxOpticalPortTdcmAutoDisp      Integer32,
      tmnxOpticalPortTdcmMeasDisp      Integer32,
      tmnxOpticalPortTdcmPresRxChan    TmnxOpticalDwdmChannel,
      tmnxOpticalPortTdcmAlarmState    TmnxOpticalTdcmAlarm,
      tmnxOpticalPortTdcmSerialNum     SnmpAdminString,
      tmnxOpticalPortTdcmCtrlState     TmnxOpticalTdcmCtrlState,
      tmnxOpticalPortDwdmChannelMin    TmnxOpticalDwdmChannel,
      tmnxOpticalPortDwdmChannelMax    TmnxOpticalDwdmChannel,
      tmnxOpticalPortLaserTunability   INTEGER
}

tmnxOpticalPortHasRxAmplifier    OBJECT-TYPE
    SYNTAX      TruthValue
    MAX-ACCESS  read-only
    STATUS      current
    DESCRIPTION
        "The value of tmnxOpticalPortHasRxAmplifier indicates whether or not
         the port has an optical amplifier on the receive path."
    ::= { tmnxOpticalPortOperEntry 1 }

tmnxOpticalPortHasRxTdcm         OBJECT-TYPE
    SYNTAX      TruthValue
    MAX-ACCESS  read-only
    STATUS      current
    DESCRIPTION
        "The value of tmnxOpticalPortHasRxTdcm indicates whether or not
         the port has an optical tunable dispersion compensation module
         on the receive path."
    ::= { tmnxOpticalPortOperEntry 2 }
  
tmnxOpticalPortAmpPowerIn        OBJECT-TYPE
    SYNTAX      Integer32
    UNITS       "mBm"
    MAX-ACCESS  read-only
    STATUS      current
    DESCRIPTION
        "The value of tmnxOpticalPortAmpPowerIn indicates the received average
         optical power at the input of the optical amplifier.
  
         The UNITS millibels (mBm) are units of 0.01 decibel relative to one
         milliwatt (0 dBm) or dBm multiplied by 100.
         The mBm is used when integers are required instead of floating point.
         For example: -5.21 dBm is equivalent to -521 mBm."
    ::= { tmnxOpticalPortOperEntry 3 }
  
tmnxOpticalPortAmpGain           OBJECT-TYPE
    SYNTAX      Unsigned32
    UNITS       "mB"
    MAX-ACCESS  read-only
    STATUS      current
    DESCRIPTION
        "The value of tmnxOpticalPortAmpGain indicates the gain of the optical
         amplifier. The gain indicates how much the input signal is amplified.
  
         The UNITS millibels (mB) are units of 0.01 dB or dB multiplied by 100.
         The mB is used when integers are required instead of floating point.
         For example: 5.21 dB is equivalent to 521 mB."
    ::= { tmnxOpticalPortOperEntry 4 }

tmnxOpticalPortAmpPowerOut       OBJECT-TYPE
    SYNTAX      Integer32
    UNITS       "mBm"
    MAX-ACCESS  read-only
    STATUS      current
    DESCRIPTION
        "The value of tmnxOpticalPortAmpPowerOut indicates the optical power
         at the output of the optical amplifier.

         The UNITS millibels (mBm) are units of 0.01 decibel relative
         to one milliwatt (0 dBm) or dBm multiplied by 100.
         The mBm is used when integers are required instead of floating point.
         For example: -5.21 dBm is equivalent to -521 mBm."
    ::= { tmnxOpticalPortOperEntry 5 }

tmnxOpticalPortAmpPumpTemp       OBJECT-TYPE
    SYNTAX      Integer32
    UNITS       "millidegrees Celsius"
    MAX-ACCESS  read-only
    STATUS      current
    DESCRIPTION
        "The value of tmnxOpticalPortAmpPumpTemp indicates the current
           temperature of the optical amplifier's pump in millidegrees Celsius."
    ::= { tmnxOpticalPortOperEntry 6 }

tmnxOpticalPortAmpModuleTemp     OBJECT-TYPE
    SYNTAX      Integer32
    UNITS       "millidegrees Celsius"
    MAX-ACCESS  read-only
    STATUS      current
    DESCRIPTION
        "The value of tmnxOpticalPortAmpModuleTemp indicates the current
         temperature of the optical amplifier module's case in
         millidegrees Celsius."
    ::= { tmnxOpticalPortOperEntry 7 }
  
tmnxOpticalPortAmpPumpCurrent    OBJECT-TYPE
    SYNTAX      Unsigned32
    UNITS       "microAmperes"
    MAX-ACCESS  read-only
    STATUS      current
    DESCRIPTION
        "The value of tmnxOpticalPortAmpPumpCurrent indicates the amount of
         electical current used by the optical amplifier's pump in
         microAmperes (uA)."
    ::= { tmnxOpticalPortOperEntry 8 }

  
tmnxOpticalPortAmpAlarmState     OBJECT-TYPE
    SYNTAX      TmnxOpticalAmpAlarm
    MAX-ACCESS  read-only
    STATUS      current
    DESCRIPTION
        "The value of tmnxOpticalPortAmpAlarmState indicates which monitored
         alarms are raised against the optical amplifier's interface."
    ::= { tmnxOpticalPortOperEntry 9 }

tmnxOpticalPortAmpSerialNum   OBJECT-TYPE
    SYNTAX         SnmpAdminString (SIZE(0..31))
    MAX-ACCESS     read-only
    STATUS         current
    DESCRIPTION
        "The value of tmnxOpticalPortAmpSerialNum indicates the manufacturing
         serial number in ASCII characters as read from the optical amplifier
         module.
           
         An empty string indicates the serial number is unspecified.

         The string is expected to contain printable ASCII characters.
         Any unprintable ASCII characters read from the module will be 
         filtered out. The string will be NULL terminated."
    ::= { tmnxOpticalPortOperEntry 10 }

tmnxOpticalPortAmpCtrlState      OBJECT-TYPE
    SYNTAX         TmnxOpticalAmpCtrlState
    MAX-ACCESS     read-only
    STATUS         current
    DESCRIPTION
        "The value of tmnxOpticalPortAmpCtrlState indicates the state of the
         control loop that optimizes the receive optical power of to the
         MSA optics."
    ::= { tmnxOpticalPortOperEntry 11 }

tmnxOpticalPortTdcmPowerIn       OBJECT-TYPE
    SYNTAX      Integer32
    UNITS       "mBm"
    MAX-ACCESS  read-only
    STATUS      current
    DESCRIPTION
        "The value of tmnxOpticalPortTdcmPowerIn indicates the received average
         optical power at the input the tunable dispersion compensation module.

         The UNITS millibels (mBm) are units of 0.01 decibel relative
         to one milliwatt (0 dBm) or dBm multiplied by 100.
         The mBm is used when integers are required instead of floating point.
         For example: -5.21 dBm is equivalent to -521 mBm."
    ::= { tmnxOpticalPortOperEntry 12 }

tmnxOpticalPortTdcmLoss          OBJECT-TYPE
    SYNTAX      Unsigned32
    UNITS       "mB"
    MAX-ACCESS  read-only
    STATUS      current
    DESCRIPTION
        "The value of tmnxOpticalPortTdcmLoss indicates the optical loss 
         occuring in the tunable dispersion compensation module.

         The UNITS millibels (mB) are units of 0.01 dB or dB multiplied by 100.
         The mB is used when integers are required instead of floating point.
         For example: 5.21 dB is equivalent to 521 mB."
    ::= { tmnxOpticalPortOperEntry 13 }
  
tmnxOpticalPortTdcmPowerOut      OBJECT-TYPE
    SYNTAX      Integer32
    UNITS       "mBm"
    MAX-ACCESS  read-only
    STATUS      current
    DESCRIPTION
        "The value of tmnxOpticalPortTdcmPowerOut indicates the optical power
         at the output of tunable dispersion compensation module.
  
         The UNITS millibels (mBm) are units of 0.01 decibel relative
         to one milliwatt (0 dBm) or dBm multiplied by 100.
         The mBm is used when integers are required instead of floating point.
         For example: -5.21 dBm is equivalent to -521 mBm."
    ::= { tmnxOpticalPortOperEntry 14 }
  
tmnxOpticalPortTdcmRtd1Temp      OBJECT-TYPE
    SYNTAX      Integer32
    UNITS       "millidegrees Celsius"
    MAX-ACCESS  read-only
    STATUS      current
    DESCRIPTION
        "The value of tmnxOpticalPortTdcmRtd1Temp indicates the current
         temperature of the tunable dispersion compensation module's first
         Resistance Temperature Detector (also known as a thermistor).
         The temperature is in units of millidegrees Celsius."
    ::= { tmnxOpticalPortOperEntry 15 }

tmnxOpticalPortTdcmRtd2Temp      OBJECT-TYPE
    SYNTAX      Integer32
    UNITS       "millidegrees Celsius"
    MAX-ACCESS  read-only
    STATUS      current
    DESCRIPTION
        "The value of tmnxOpticalPortTdcmRtd2Temp indicates the current
         temperature of the tunable dispersion compensation module's second
         Resistance Temperature Detector (also known as a thermistor).
         The temperature is in units of millidegrees Celsius."
    ::= { tmnxOpticalPortOperEntry 16 }

tmnxOpticalPortTdcmRtd3Temp      OBJECT-TYPE
    SYNTAX      Integer32
    UNITS       "millidegrees Celsius"
    MAX-ACCESS  read-only
    STATUS      current
    DESCRIPTION
        "The value of tmnxOpticalPortTdcmRtd3Temp indicates the current
         temperature of the tunable dispersion compensation module's third
         Resistance Temperature Detector (also known as a thermistor).
         The temperature is in units of millidegrees Celsius."
    ::= { tmnxOpticalPortOperEntry 17 }
  
tmnxOpticalPortTdcmRtd4Temp      OBJECT-TYPE
    SYNTAX      Integer32
    UNITS       "millidegrees Celsius"
    MAX-ACCESS  read-only
    STATUS      current
    DESCRIPTION
        "The value of tmnxOpticalPortTdcmRtd4Temp indicates the current
         temperature of the tunable dispersion compensation module's fourth
         Resistance Temperature Detector (also known as a thermistor).
         The temperature is in units of millidegrees Celsius."
    ::= { tmnxOpticalPortOperEntry 18 }

tmnxOpticalPortTdcmModuleTemp  OBJECT-TYPE
    SYNTAX      Integer32
    UNITS       "millidegrees Celsius"
    MAX-ACCESS  read-only
    STATUS      current
    DESCRIPTION
        "The value of tmnxOpticalPortTdcmModuleTemp indicates the current
         temperature of the tunable dispersion compensation module's case in
         millidegrees Celsius."
    ::= { tmnxOpticalPortOperEntry 19 }
  
tmnxOpticalPortTdcmMinDisp       OBJECT-TYPE
    SYNTAX      Integer32
    UNITS       "picoseconds per nanometer"
    MAX-ACCESS  read-only
    STATUS      current
    DESCRIPTION
        "The value of tmnxOpticalPortTdcmMinDisp indicates the minimum
         configurable dispersion of the tunable dispersion compensation
         module. Dispersion is expressed in pico-seconds per nano-meter
         (ps/nm)."
    ::= { tmnxOpticalPortOperEntry 20 }
                                 
tmnxOpticalPortTdcmMaxDisp       OBJECT-TYPE
    SYNTAX      Integer32
    UNITS       "picoseconds per nanometer"
    MAX-ACCESS  read-only
    STATUS      current
    DESCRIPTION
        "The value of tmnxOpticalPortTdcmMaxDisp indicates the maximum
         configurable dispersion of the tunable dispersion compensation
         module. Dispersion is expressed in pico-seconds per nano-meter
         (ps/nm)."
    ::= { tmnxOpticalPortOperEntry 21 }

tmnxOpticalPortTdcmAutoDisp      OBJECT-TYPE
    SYNTAX      Integer32
    UNITS       "picoseconds per nanometer"
    MAX-ACCESS  read-only
    STATUS      current
    DESCRIPTION
        "The value of tmnxOpticalPortTdcmAutoDisp indicates the currently
         auto-configured dispersion of the tunable dispersion compensation
         module. Dispersion is expressed in pico-seconds per nano-meter
         (ps/nm)."
    ::= { tmnxOpticalPortOperEntry 22 }
  
tmnxOpticalPortTdcmMeasDisp      OBJECT-TYPE
    SYNTAX      Integer32
    UNITS       "picoseconds per nanometer"
    MAX-ACCESS  read-only
    STATUS      current
    DESCRIPTION
        "The value of tmnxOpticalPortTdcmMeasDisp indicates the dynamically
         measured dispersion of the tunable dispersion compensation
         module. Dispersion is expressed in pico-seconds per nano-meter
         (ps/nm)."
    ::= { tmnxOpticalPortOperEntry 23 }

tmnxOpticalPortTdcmPresRxChan OBJECT-TYPE
    SYNTAX      TmnxOpticalDwdmChannel
    MAX-ACCESS  read-only
    STATUS      current
    DESCRIPTION
        "tmnxOpticalPortTdcmPresRxChan indicates the DWDM ITU channel at which
         the tunable dispersion compensation module is operating."
    ::= { tmnxOpticalPortOperEntry 24 }

tmnxOpticalPortTdcmAlarmState    OBJECT-TYPE
    SYNTAX      TmnxOpticalTdcmAlarm
    MAX-ACCESS  read-only
    STATUS      current
    DESCRIPTION
        "The value of tmnxOpticalPortTdcmAlarmState indicates which monitored
         alarms are raised against the dispersion compensation module's
         interface."
    ::= { tmnxOpticalPortOperEntry 25 }

tmnxOpticalPortTdcmSerialNum  OBJECT-TYPE
    SYNTAX         SnmpAdminString (SIZE(0..31))
    MAX-ACCESS     read-only
    STATUS         current
    DESCRIPTION
        "The value of tmnxOpticalPortTdcmSerialNum indicates the
         manufacturing serial number in ASCII characters as read from the
         tunable dispersion compensation module.
         
         An empty string indicates the serial number is unspecified.

         The string is expected to contain printable ASCII characters.
         Any unprintable ASCII characters read from the module will be 
         filtered out. The string will be NULL terminated."
    ::= { tmnxOpticalPortOperEntry 26 }

tmnxOpticalPortTdcmCtrlState     OBJECT-TYPE
    SYNTAX         TmnxOpticalTdcmCtrlState
    MAX-ACCESS     read-only
    STATUS         current
    DESCRIPTION
        "The TmnxOpticalTdcmCtrlState indicates the state of the control loop
         that optimizes the dispersion by tuning the dispersion compensation
         module to the set point at which the FEC corrected error rate is the
         lowest."
    ::= { tmnxOpticalPortOperEntry 27 }

tmnxOpticalPortDwdmChannelMin    OBJECT-TYPE
    SYNTAX      TmnxOpticalDwdmChannel
    MAX-ACCESS  read-only
    STATUS      current
    DESCRIPTION
        "tmnxOpticalPortDwdmChannelMin indicates the minimum DWDM ITU channel
         supported by a tunable optical interface."
    ::= { tmnxOpticalPortOperEntry 28 }

tmnxOpticalPortDwdmChannelMax    OBJECT-TYPE
    SYNTAX      TmnxOpticalDwdmChannel
    MAX-ACCESS  read-only
    STATUS      current
    DESCRIPTION
        "tmnxOpticalPortDwdmChannelMax indicates the maximum DWDM ITU channel
         supported by a tunable optical interface."
    ::= { tmnxOpticalPortOperEntry 29 }
      
tmnxOpticalPortLaserTunability   OBJECT-TYPE
    SYNTAX      INTEGER {
                    unequipped(0),
                    notTunable(1),
                    fullyTunable(2)
                }
    MAX-ACCESS  read-only
    STATUS      current
    DESCRIPTION
        "tmnxOpticalPortLaserTunability indicates if the optical interface
         laser is tunable or fixed. Value 'unequipped(0)' indicates that the
         optical interface is not equipped with a laser."
    ::= { tmnxOpticalPortOperEntry 30 }

--
--    Port Egress Expanded-Secondary Shaper
--
tmnxPortEgrExpShaperTblLastChngd OBJECT-TYPE
    SYNTAX      TimeStamp
    MAX-ACCESS  read-only
    STATUS      current
    DESCRIPTION
        "The value of tmnxPortEgrExpShaperTblLastChngd indicates the sysUpTime
         at the time of the last modification of tmnxPortEgrExpShaperTable."
    ::= { tmnxPortObjs 60 }

tmnxPortEgrExpShaperTable OBJECT-TYPE
    SYNTAX      SEQUENCE OF TmnxPortEgrExpShaperEntry
    MAX-ACCESS  not-accessible
    STATUS      current
    DESCRIPTION
        "The tmnxPortEgrExpShaperTable contains the information of each 
         egress expanded shaper at the port level configured on this system."
    ::= { tmnxPortObjs 61 }

tmnxPortEgrExpShaperEntry    OBJECT-TYPE
    SYNTAX      TmnxPortEgrExpShaperEntry
    MAX-ACCESS  not-accessible
    STATUS      current
    DESCRIPTION
        "Each row in tmnxPortEgrExpShaperEntry represents a particular 
         egress expanded secondary shaper at the port level specified by 
         tmnxPortEgrExpShaperName."
    INDEX { tmnxChassisIndex, tmnxPortPortID, tmnxPortEgrExpShaperName }
    ::= { tmnxPortEgrExpShaperTable 1}

TmnxPortEgrExpShaperEntry ::= SEQUENCE
    {
        tmnxPortEgrExpShaperName               TNamedItem,
        tmnxPortEgrExpShaperRowStatus          RowStatus,
        tmnxPortEgrExpShaperRate               TExpSecondaryShaperPIRRate,
        tmnxPortEgrExpShaperClass1Rate         TExpSecondaryShaperClassRate,
        tmnxPortEgrExpShaperClass2Rate         TExpSecondaryShaperClassRate,
        tmnxPortEgrExpShaperClass3Rate         TExpSecondaryShaperClassRate,
        tmnxPortEgrExpShaperClass4Rate         TExpSecondaryShaperClassRate,
        tmnxPortEgrExpShaperClass5Rate         TExpSecondaryShaperClassRate,
        tmnxPortEgrExpShaperClass6Rate         TExpSecondaryShaperClassRate,
        tmnxPortEgrExpShaperClass7Rate         TExpSecondaryShaperClassRate,
        tmnxPortEgrExpShaperClass8Rate         TExpSecondaryShaperClassRate,
        tmnxPortEgrExpShaperLastChanged        TimeStamp,
        tmnxPortEgrExpShaperLoBrstMaxCls       Unsigned32,
        tmnxPortEgrExpShaperClass1Thresh       Integer32,
        tmnxPortEgrExpShaperClass2Thresh       Integer32,
        tmnxPortEgrExpShaperClass3Thresh       Integer32,
        tmnxPortEgrExpShaperClass4Thresh       Integer32,
        tmnxPortEgrExpShaperClass5Thresh       Integer32,
        tmnxPortEgrExpShaperClass6Thresh       Integer32,
        tmnxPortEgrExpShaperClass7Thresh       Integer32,
        tmnxPortEgrExpShaperClass8Thresh       Integer32,
        tmnxPortEgrExpShaperThresh             Integer32,
        tmnxPortEgrExpShaperLoBurstLimit       TClassBurstLimit,
        tmnxPortEgrExpShaperHiBurstInc         Integer32,
        tmnxPortEgrExpShaperCl1BrstLimit       TClassBurstLimit,
        tmnxPortEgrExpShaperCl2BrstLimit       TClassBurstLimit,
        tmnxPortEgrExpShaperCl3BrstLimit       TClassBurstLimit,
        tmnxPortEgrExpShaperCl4BrstLimit       TClassBurstLimit,
        tmnxPortEgrExpShaperCl5BrstLimit       TClassBurstLimit,
        tmnxPortEgrExpShaperCl6BrstLimit       TClassBurstLimit,
        tmnxPortEgrExpShaperCl7BrstLimit       TClassBurstLimit,
        tmnxPortEgrExpShaperCl8BrstLimit       TClassBurstLimit
    }

tmnxPortEgrExpShaperName          OBJECT-TYPE
    SYNTAX      TNamedItem
    MAX-ACCESS  not-accessible
    STATUS      current
    DESCRIPTION
        "The value of tmnxPortEgrExpShaperName specifies the expanded shaper 
        name on the egress side of this port."
    ::= { tmnxPortEgrExpShaperEntry 1 }

tmnxPortEgrExpShaperRowStatus        OBJECT-TYPE
    SYNTAX      RowStatus
    MAX-ACCESS  read-create
    STATUS      current
    DESCRIPTION
        "The value of tmnxPortEgrExpShaperRowStatus specifies the row-status of
         this entry in this table."
    ::= { tmnxPortEgrExpShaperEntry 2 }

tmnxPortEgrExpShaperRate        OBJECT-TYPE
    SYNTAX      TExpSecondaryShaperPIRRate
    UNITS       "Kbps"
    MAX-ACCESS  read-create
    STATUS      current
    DESCRIPTION
        "The value of tmnxPortEgrExpShaperRate specifies the explicit
         maximum frame based bandwidth limit, in kilobits per second, of this
         egress port expanded secondary shaper as a whole."
    DEFVAL      { -1 }
    ::= { tmnxPortEgrExpShaperEntry 3 }

tmnxPortEgrExpShaperClass1Rate        OBJECT-TYPE
    SYNTAX      TExpSecondaryShaperClassRate
    UNITS       "Kbps"
    MAX-ACCESS  read-create
    STATUS      current
    DESCRIPTION
        "The value of tmnxPortEgrExpShaperClass1Rate specifies the explicit
         maximum frame based bandwidth limit, in kilobits per second, of the
         Class 1 traffic using this egress port expanded secondary shaper."
    DEFVAL { -1 }
    ::= { tmnxPortEgrExpShaperEntry 4 }

tmnxPortEgrExpShaperClass2Rate        OBJECT-TYPE
    SYNTAX      TExpSecondaryShaperClassRate
    UNITS       "Kbps"
    MAX-ACCESS  read-create
    STATUS      current
    DESCRIPTION
        "The value of tmnxPortEgrExpShaperClass2Rate specifies the explicit
         maximum frame based bandwidth limit, in kilobits per second, of the
         Class 2 traffic using this egress port expanded secondary shaper."
    DEFVAL { -1 }
    ::= { tmnxPortEgrExpShaperEntry 5 }

tmnxPortEgrExpShaperClass3Rate        OBJECT-TYPE
    SYNTAX      TExpSecondaryShaperClassRate
    UNITS       "Kbps"
    MAX-ACCESS  read-create
    STATUS      current
    DESCRIPTION
        "The value of tmnxPortEgrExpShaperClass3Rate specifies the explicit
         maximum frame based bandwidth limit, in kilobits per second, of the
         Class 3 traffic using this egress port expanded secondary shaper."
    DEFVAL { -1 }
    ::= { tmnxPortEgrExpShaperEntry 6 }

tmnxPortEgrExpShaperClass4Rate        OBJECT-TYPE
    SYNTAX      TExpSecondaryShaperClassRate
    UNITS       "Kbps"
    MAX-ACCESS  read-create
    STATUS      current
    DESCRIPTION
        "The value of tmnxPortEgrExpShaperClass4Rate specifies the explicit
         maximum frame based bandwidth limit, in kilobits per second, of the
         Class 4 traffic using this egress port expanded secondary shaper."
    DEFVAL { -1 }
    ::= { tmnxPortEgrExpShaperEntry 7 }

tmnxPortEgrExpShaperClass5Rate        OBJECT-TYPE
    SYNTAX      TExpSecondaryShaperClassRate
    UNITS       "Kbps"
    MAX-ACCESS  read-create
    STATUS      current
    DESCRIPTION
        "The value of tmnxPortEgrExpShaperClass5Rate specifies the explicit
         maximum frame based bandwidth limit, in kilobits per second, of the
         Class 5 traffic using this egress port expanded secondary shaper."
    DEFVAL { -1 }
    ::= { tmnxPortEgrExpShaperEntry 8 }

tmnxPortEgrExpShaperClass6Rate        OBJECT-TYPE
    SYNTAX      TExpSecondaryShaperClassRate
    UNITS       "Kbps"
    MAX-ACCESS  read-create
    STATUS      current
    DESCRIPTION
        "The value of tmnxPortEgrExpShaperClass6Rate specifies the explicit
         maximum frame based bandwidth limit, in kilobits per second, of the
         Class 6 traffic using this egress port expanded secondary shaper."
    DEFVAL { -1 }
    ::= { tmnxPortEgrExpShaperEntry 9 }

tmnxPortEgrExpShaperClass7Rate        OBJECT-TYPE
    SYNTAX      TExpSecondaryShaperClassRate
    UNITS       "Kbps"
    MAX-ACCESS  read-create
    STATUS      current
    DESCRIPTION
        "The value of tmnxPortEgrExpShaperClass7Rate specifies the explicit
         maximum frame based bandwidth limit, in kilobits per second, of the
         Class 7 traffic using this egress port expanded secondary shaper."
    DEFVAL { -1 }
    ::= { tmnxPortEgrExpShaperEntry 10 }

tmnxPortEgrExpShaperClass8Rate        OBJECT-TYPE
    SYNTAX      TExpSecondaryShaperClassRate
    UNITS       "Kbps"
    MAX-ACCESS  read-create
    STATUS      current
    DESCRIPTION
        "The value of tmnxPortEgrExpShaperClass8Rate specifies the explicit
         maximum frame based bandwidth limit, in kilobits per second, of the
         Class 8 traffic using this egress port expanded secondary shaper."
    DEFVAL { -1 }
    ::= { tmnxPortEgrExpShaperEntry 11 }

tmnxPortEgrExpShaperLastChanged        OBJECT-TYPE
    SYNTAX      TimeStamp
    MAX-ACCESS  read-only
    STATUS      current
    DESCRIPTION
        "The value of tmnxPortEgrExpShaperLastChanged indicates the value of
         sysUpTime when the egress expanded shaper entry was last modified."
    ::= { tmnxPortEgrExpShaperEntry 12 }

tmnxPortEgrExpShaperLoBrstMaxCls OBJECT-TYPE
    SYNTAX       Unsigned32 (1..8)
    MAX-ACCESS   read-create
    STATUS       current
    DESCRIPTION
        "The value of tmnxPortEgrExpShaperLoBrstMaxCls specifies which class
        should use the low priority burst threshold.
        
        All classes starting from 1, up to and including that specified by
        tmnxPortEgrExpShaperLoBrstMaxCls use the low priority burst threshold.
        
        All classes greater than the value of tmnxPortEgrExpShaperLoBrstMaxCls
        up to and including class 8 use the high priority burst threshold."
    DEFVAL { 8 }
    ::= { tmnxPortEgrExpShaperEntry 13 }

tmnxPortEgrExpShaperClass1Thresh OBJECT-TYPE
    SYNTAX       Integer32 (-1|0..8190)
    UNITS        "kbytes"
    MAX-ACCESS   read-create
    STATUS       current
    DESCRIPTION
        "The tmnxPortEgrExpShaperClass1Thresh specifies the monitoring
        non-conformance burst threshold for the exp-secondary-shaper class-1.
        When set to default value '-1', the system will adopt a suitable
        default setting for this threshold."
    DEFVAL { -1 }
    ::= { tmnxPortEgrExpShaperEntry 14 }

tmnxPortEgrExpShaperClass2Thresh OBJECT-TYPE
    SYNTAX       Integer32 (-1|0..8190)
    UNITS        "kbytes"
    MAX-ACCESS   read-create
    STATUS       current
    DESCRIPTION
        "The tmnxPortEgrExpShaperClass2Thresh specifies the monitoring
        non-conformance burst threshold for the exp-secondary-shaper class-2.
        When set to default value '-1', the system will adopt a suitable
        default setting for this threshold."
    DEFVAL { -1 }
    ::= { tmnxPortEgrExpShaperEntry 15 }

tmnxPortEgrExpShaperClass3Thresh OBJECT-TYPE
    SYNTAX       Integer32 (-1|0..8190)
    UNITS        "kbytes"
    MAX-ACCESS   read-create
    STATUS       current
    DESCRIPTION
        "The tmnxPortEgrExpShaperClass3Thresh specifies the monitoring
        non-conformance burst threshold for the exp-secondary-shaper class-3.
        When set to default value '-1', the system will adopt a suitable
        default setting for this threshold."
    DEFVAL { -1 }
    ::= { tmnxPortEgrExpShaperEntry 16 }

tmnxPortEgrExpShaperClass4Thresh OBJECT-TYPE
    SYNTAX       Integer32 (-1|0..8190)
    UNITS        "kbytes"
    MAX-ACCESS   read-create
    STATUS       current
    DESCRIPTION
        "The tmnxPortEgrExpShaperClass4Thresh specifies the monitoring
        non-conformance burst threshold for the exp-secondary-shaper class-4.
        When set to default value '-1', the system will adopt a suitable
        default setting for this threshold."
    DEFVAL { -1 }
    ::= { tmnxPortEgrExpShaperEntry 17 }

tmnxPortEgrExpShaperClass5Thresh OBJECT-TYPE
    SYNTAX       Integer32 (-1|0..8190)
    UNITS        "kbytes"
    MAX-ACCESS   read-create
    STATUS       current
    DESCRIPTION
        "The tmnxPortEgrExpShaperClass5Thresh specifies the monitoring
        non-conformance burst threshold for the exp-secondary-shaper class-5.
        When set to default value '-1', the system will adopt a suitable
        default setting for this threshold."
    DEFVAL { -1 }
    ::= { tmnxPortEgrExpShaperEntry 18 }

tmnxPortEgrExpShaperClass6Thresh OBJECT-TYPE
    SYNTAX       Integer32 (-1|0..8190)
    UNITS        "kbytes"
    MAX-ACCESS   read-create
    STATUS       current
    DESCRIPTION
        "The tmnxPortEgrExpShaperClass6Thresh specifies the monitoring
        non-conformance burst threshold for the exp-secondary-shaper class-6.
        When set to default value '-1', the system will adopt a suitable
        default setting for this threshold."
    DEFVAL { -1 }
    ::= { tmnxPortEgrExpShaperEntry 19 }

tmnxPortEgrExpShaperClass7Thresh OBJECT-TYPE
    SYNTAX       Integer32 (-1|0..8190)
    UNITS        "kbytes"
    MAX-ACCESS   read-create
    STATUS       current
    DESCRIPTION
        "The tmnxPortEgrExpShaperClass7Thresh specifies the monitoring
        non-conformance burst threshold for the exp-secondary-shaper class-7.
        When set to default value '-1', the system will adopt a suitable
        default setting for this threshold."
    DEFVAL { -1 }
    ::= { tmnxPortEgrExpShaperEntry 20 }

tmnxPortEgrExpShaperClass8Thresh OBJECT-TYPE
    SYNTAX       Integer32 (-1|0..8190)
    UNITS        "kbytes"
    MAX-ACCESS   read-create
    STATUS       current
    DESCRIPTION
        "The tmnxPortEgrExpShaperClass8Thresh specifies the monitoring
        non-conformance burst threshold for the exp-secondary-shaper class-8.
        When set to default value '-1', the system will adopt a suitable
        default setting for this threshold."
    DEFVAL { -1 }
    ::= { tmnxPortEgrExpShaperEntry 21 }

tmnxPortEgrExpShaperThresh OBJECT-TYPE
    SYNTAX       Integer32 (-1|0..8190)
    UNITS        "kbytes"
    MAX-ACCESS   read-create
    STATUS       current
    DESCRIPTION
        "The tmnxPortEgrExpShaperThresh specifies the monitoring non-conformance
         burst threshold for the aggregate exp-secondary-shaper.  When set to 
         default value '-1', the system will adopt a suitable default setting 
         for this threshold."
    DEFVAL { -1 }
    ::= { tmnxPortEgrExpShaperEntry 22 }

tmnxPortEgrExpShaperLoBurstLimit OBJECT-TYPE
    SYNTAX       TClassBurstLimit
    UNITS        "bytes"
    MAX-ACCESS   read-create
    STATUS       current
    DESCRIPTION
        "The tmnxPortEgrExpShaperLoBurstLimit specifies the number of bytes to 
         be used as the low burst threshold for the aggregate rate of the 
         classes pertaining to the low burst threshold in the expanded secondary
         shaper."
    DEFVAL { -1 }
    ::= { tmnxPortEgrExpShaperEntry 23 }

tmnxPortEgrExpShaperHiBurstInc OBJECT-TYPE
    SYNTAX       Integer32 (-1|0..65528)
    UNITS        "bytes"
    MAX-ACCESS   read-create
    STATUS       current
    DESCRIPTION
        "The tmnxPortEgrExpShaperHiBurstInc specifies the incremental number of
         bytes above the low burst limit to be used as the high burst threshold 
         for the aggregate rate of the classes pertaining to the high burst 
         threshold in the expanded secondary shaper. When set to the default 
         value '-1', the system will default to a value of '4000' bytes."
    DEFVAL { -1 }
    ::= { tmnxPortEgrExpShaperEntry 24 }

tmnxPortEgrExpShaperCl1BrstLimit OBJECT-TYPE
    SYNTAX       TClassBurstLimit
    UNITS        "bytes"
    MAX-ACCESS   read-create
    STATUS       current
    DESCRIPTION
        "The value of tmnxPortEgrExpShaperCl1BrstLimit specifies the explicit 
         shaping burst size of the class."
    DEFVAL { -1 }
    ::= { tmnxPortEgrExpShaperEntry 25 }

tmnxPortEgrExpShaperCl2BrstLimit OBJECT-TYPE
    SYNTAX       TClassBurstLimit
    UNITS        "bytes"
    MAX-ACCESS   read-create
    STATUS       current
    DESCRIPTION
        "The value of tmnxPortEgrExpShaperCl2BrstLimit specifies the explicit 
         shaping burst size of the class."
    DEFVAL { -1 }
    ::= { tmnxPortEgrExpShaperEntry 26 }

tmnxPortEgrExpShaperCl3BrstLimit OBJECT-TYPE
    SYNTAX       TClassBurstLimit
    UNITS        "bytes"
    MAX-ACCESS   read-create
    STATUS       current
    DESCRIPTION
        "The value of tmnxPortEgrExpShaperCl3BrstLimit specifies the explicit 
         shaping burst size of the class."
    DEFVAL { -1 }
    ::= { tmnxPortEgrExpShaperEntry 27 }

tmnxPortEgrExpShaperCl4BrstLimit OBJECT-TYPE
    SYNTAX       TClassBurstLimit
    UNITS        "bytes"
    MAX-ACCESS   read-create
    STATUS       current
    DESCRIPTION
        "The value of tmnxPortEgrExpShaperCl4BrstLimit specifies the explicit 
         shaping burst size of the class."
    DEFVAL { -1 }
    ::= { tmnxPortEgrExpShaperEntry 28 }

tmnxPortEgrExpShaperCl5BrstLimit OBJECT-TYPE
    SYNTAX       TClassBurstLimit
    UNITS        "bytes"
    MAX-ACCESS   read-create
    STATUS       current
    DESCRIPTION
        "The value of tmnxPortEgrExpShaperCl5BrstLimit specifies the explicit 
         shaping burst size of the class."
    DEFVAL { -1 }
    ::= { tmnxPortEgrExpShaperEntry 29 }

tmnxPortEgrExpShaperCl6BrstLimit OBJECT-TYPE
    SYNTAX       TClassBurstLimit
    UNITS        "bytes"
    MAX-ACCESS   read-create
    STATUS       current
    DESCRIPTION
        "The value of tmnxPortEgrExpShaperCl6BrstLimit specifies the explicit 
         shaping burst size of the class."
    DEFVAL { -1 }
    ::= { tmnxPortEgrExpShaperEntry 30 }

tmnxPortEgrExpShaperCl7BrstLimit OBJECT-TYPE
    SYNTAX       TClassBurstLimit
    UNITS        "bytes"
    MAX-ACCESS   read-create
    STATUS       current
    DESCRIPTION
        "The value of tmnxPortEgrExpShaperCl7BrstLimit specifies the explicit 
         shaping burst size of the class."
    DEFVAL { -1 }
    ::= { tmnxPortEgrExpShaperEntry 31 }

tmnxPortEgrExpShaperCl8BrstLimit OBJECT-TYPE
    SYNTAX       TClassBurstLimit
    UNITS        "bytes"
    MAX-ACCESS   read-create
    STATUS       current
    DESCRIPTION
        "The value of tmnxPortEgrExpShaperCl8BrstLimit specifies the explicit 
         shaping burst size of the class."
    DEFVAL { -1 }
    ::= { tmnxPortEgrExpShaperEntry 32 }

--
--    Port Egress Expanded-Secondary Shaper Stats (64 bit)
--

tPortEgrExpShaperStatsTable OBJECT-TYPE
    SYNTAX      SEQUENCE OF TPortEgrExpShaperStatsEntry
    MAX-ACCESS  not-accessible
    STATUS      current
    DESCRIPTION
        "The tPortEgrExpShaperStatsTable contains the statistics of each 
         egress expanded shaper at the port level configured on this system.
         Most objects are represented in 64 bit. 32-bit version of the objects
         are available in tPortEgrExpShaperStatsHLTable."
    ::= { tmnxPortObjs 62 }

tPortEgrExpShaperStatsEntry    OBJECT-TYPE
    SYNTAX      TPortEgrExpShaperStatsEntry
    MAX-ACCESS  not-accessible
    STATUS      current
    DESCRIPTION
        "Each row in tPortEgrExpShaperStatsEntry represents a particular 
         egress expanded secondary shaper statistics at the port level specified
         by tmnxPortEgrExpShaperName."
    INDEX { tmnxChassisIndex, tmnxPortPortID, tmnxPortEgrExpShaperName }
    ::= { tPortEgrExpShaperStatsTable 1}

TPortEgrExpShaperStatsEntry ::= SEQUENCE
    {
        tPortEgrExpShaperStLstClrdTime    TimeStamp,
        tPortEgrExpShaperCls1StFwdPkts    Counter64,
        tPortEgrExpShaperCls1StFwdOcts    Counter64,
        tPortEgrExpShaperCls1StMonOvrOct  Counter64,
        tPortEgrExpShaperCls2StFwdPkts    Counter64,
        tPortEgrExpShaperCls2StFwdOcts    Counter64,
        tPortEgrExpShaperCls2StMonOvrOct  Counter64,
        tPortEgrExpShaperCls3StFwdPkts    Counter64,
        tPortEgrExpShaperCls3StFwdOcts    Counter64,
        tPortEgrExpShaperCls3StMonOvrOct  Counter64,
        tPortEgrExpShaperCls4StFwdPkts    Counter64,
        tPortEgrExpShaperCls4StFwdOcts    Counter64,
        tPortEgrExpShaperCls4StMonOvrOct  Counter64,
        tPortEgrExpShaperCls5StFwdPkts    Counter64,
        tPortEgrExpShaperCls5StFwdOcts    Counter64,
        tPortEgrExpShaperCls5StMonOvrOct  Counter64,
        tPortEgrExpShaperCls6StFwdPkts    Counter64,
        tPortEgrExpShaperCls6StFwdOcts    Counter64,
        tPortEgrExpShaperCls6StMonOvrOct  Counter64,
        tPortEgrExpShaperCls7StFwdPkts    Counter64,
        tPortEgrExpShaperCls7StFwdOcts    Counter64,
        tPortEgrExpShaperCls7StMonOvrOct  Counter64,
        tPortEgrExpShaperCls8StFwdPkts    Counter64,
        tPortEgrExpShaperCls8StFwdOcts    Counter64,
        tPortEgrExpShaperCls8StMonOvrOct  Counter64,
        tPortEgrExpShaperAggStFwdPkts     Counter64,
        tPortEgrExpShaperAggStFwdOcts     Counter64,
        tPortEgrExpShaperAggStMonOvrOct   Counter64  
    }

tPortEgrExpShaperStLstClrdTime OBJECT-TYPE
    SYNTAX          TimeStamp
    MAX-ACCESS      read-only
    STATUS          current
    DESCRIPTION
        "The value of tPortEgrExpShaperStLstClrdTime indicates the sysUpTime
         when the counters in this table were last cleared."
    ::= { tPortEgrExpShaperStatsEntry 1 }

tPortEgrExpShaperCls1StFwdPkts OBJECT-TYPE
    SYNTAX          Counter64
    MAX-ACCESS      read-only
    STATUS          current
    DESCRIPTION
        "The value of tPortEgrExpShaperCls1StFwdPkts indicates the number of 
         packets forwarded by the class '1' egress expanded shaper."
    ::= { tPortEgrExpShaperStatsEntry 2 }

tPortEgrExpShaperCls1StFwdOcts OBJECT-TYPE
    SYNTAX          Counter64
    MAX-ACCESS      read-only
    STATUS          current
    DESCRIPTION
        "The value of tPortEgrExpShaperCls1StFwdOcts indicates the number of 
         octets forwarded by the class '1' egress expanded shaper."
    ::= { tPortEgrExpShaperStatsEntry 3 }

tPortEgrExpShaperCls1StMonOvrOct OBJECT-TYPE
    SYNTAX          Counter64
    MAX-ACCESS      read-only
    STATUS          current
    DESCRIPTION
        "The value of tPortEgrExpShaperCls1StMonOvrOct indicates the number of 
         octets above the configured monitor-threshold (since last read) by 
         the class '1' egress expanded shaper."
    ::= { tPortEgrExpShaperStatsEntry 4 }

tPortEgrExpShaperCls2StFwdPkts OBJECT-TYPE
    SYNTAX          Counter64
    MAX-ACCESS      read-only
    STATUS          current
    DESCRIPTION
        "The value of tPortEgrExpShaperCls2StFwdPkts indicates the number of 
         packets forwarded by the class '2' egress expanded shaper."
    ::= { tPortEgrExpShaperStatsEntry 5 }

tPortEgrExpShaperCls2StFwdOcts OBJECT-TYPE
    SYNTAX          Counter64
    MAX-ACCESS      read-only
    STATUS          current
    DESCRIPTION
        "The value of tPortEgrExpShaperCls2StFwdOcts indicates the number of 
         octets forwarded by the class '2' egress expanded shaper."
    ::= { tPortEgrExpShaperStatsEntry 6 }

tPortEgrExpShaperCls2StMonOvrOct OBJECT-TYPE
    SYNTAX          Counter64
    MAX-ACCESS      read-only
    STATUS          current
    DESCRIPTION
        "The value of tPortEgrExpShaperCls2StMonOvrOct indicates the number of 
         octets above the configured monitor-threshold (since last read) by 
         the class '2' egress expanded shaper."
    ::= { tPortEgrExpShaperStatsEntry 7 }

tPortEgrExpShaperCls3StFwdPkts OBJECT-TYPE
    SYNTAX          Counter64
    MAX-ACCESS      read-only
    STATUS          current
    DESCRIPTION
        "The value of tPortEgrExpShaperCls3StFwdPkts indicates the number of 
         packets forwarded by the class '3' egress expanded shaper."
    ::= { tPortEgrExpShaperStatsEntry 8 }

tPortEgrExpShaperCls3StFwdOcts OBJECT-TYPE
    SYNTAX          Counter64
    MAX-ACCESS      read-only
    STATUS          current
    DESCRIPTION
        "The value of tPortEgrExpShaperCls3StFwdOcts indicates the number of 
         octets forwarded by the class '3' egress expanded shaper."
    ::= { tPortEgrExpShaperStatsEntry 9 }

tPortEgrExpShaperCls3StMonOvrOct OBJECT-TYPE
    SYNTAX          Counter64
    MAX-ACCESS      read-only
    STATUS          current
    DESCRIPTION
        "The value of tPortEgrExpShaperCls3StMonOvrOct indicates the number of 
         octets above the configured monitor-threshold (since last read) by 
         the class '3' egress expanded shaper."
    ::= { tPortEgrExpShaperStatsEntry 10 }

tPortEgrExpShaperCls4StFwdPkts OBJECT-TYPE
    SYNTAX          Counter64
    MAX-ACCESS      read-only
    STATUS          current
    DESCRIPTION
        "The value of tPortEgrExpShaperCls4StFwdPkts indicates the number of 
         packets forwarded by the class '4' egress expanded shaper."
    ::= { tPortEgrExpShaperStatsEntry 11 }

tPortEgrExpShaperCls4StFwdOcts OBJECT-TYPE
    SYNTAX          Counter64
    MAX-ACCESS      read-only
    STATUS          current
    DESCRIPTION
        "The value of tPortEgrExpShaperCls4StFwdOcts indicates the number of 
         octets forwarded by the class '4' egress expanded shaper."
    ::= { tPortEgrExpShaperStatsEntry 12 }

tPortEgrExpShaperCls4StMonOvrOct OBJECT-TYPE
    SYNTAX          Counter64
    MAX-ACCESS      read-only
    STATUS          current
    DESCRIPTION
        "The value of tPortEgrExpShaperCls4StMonOvrOct indicates the number of 
         octets above the configured monitor-threshold (since last read) by 
         the class '4' egress expanded shaper."
    ::= { tPortEgrExpShaperStatsEntry 13 }

tPortEgrExpShaperCls5StFwdPkts OBJECT-TYPE
    SYNTAX          Counter64
    MAX-ACCESS      read-only
    STATUS          current
    DESCRIPTION
        "The value of tPortEgrExpShaperCls5StFwdPkts indicates the number of 
         packets forwarded by the class '5' egress expanded shaper."
    ::= { tPortEgrExpShaperStatsEntry 14 }

tPortEgrExpShaperCls5StFwdOcts OBJECT-TYPE
    SYNTAX          Counter64
    MAX-ACCESS      read-only
    STATUS          current
    DESCRIPTION
        "The value of tPortEgrExpShaperCls5StFwdOcts indicates the number of 
         octets forwarded by the class '5' egress expanded shaper."
    ::= { tPortEgrExpShaperStatsEntry 15 }

tPortEgrExpShaperCls5StMonOvrOct OBJECT-TYPE
    SYNTAX          Counter64
    MAX-ACCESS      read-only
    STATUS          current
    DESCRIPTION
        "The value of tPortEgrExpShaperCls5StMonOvrOct indicates the number of 
         octets above the configured monitor-threshold (since last read) by 
         the class '5' egress expanded shaper."
    ::= { tPortEgrExpShaperStatsEntry 16 }

tPortEgrExpShaperCls6StFwdPkts OBJECT-TYPE
    SYNTAX          Counter64
    MAX-ACCESS      read-only
    STATUS          current
    DESCRIPTION
        "The value of tPortEgrExpShaperCls6StFwdPkts indicates the number of 
         packets forwarded by the class '6' egress expanded shaper."
    ::= { tPortEgrExpShaperStatsEntry 17 }

tPortEgrExpShaperCls6StFwdOcts OBJECT-TYPE
    SYNTAX          Counter64
    MAX-ACCESS      read-only
    STATUS          current
    DESCRIPTION
        "The value of tPortEgrExpShaperCls6StFwdOcts indicates the number of 
         octets forwarded by the class '6' egress expanded shaper."
    ::= { tPortEgrExpShaperStatsEntry 18 }

tPortEgrExpShaperCls6StMonOvrOct OBJECT-TYPE
    SYNTAX          Counter64
    MAX-ACCESS      read-only
    STATUS          current
    DESCRIPTION
        "The value of tPortEgrExpShaperCls6StMonOvrOct indicates the number of 
         octets above the configured monitor-threshold (since last read) by 
         the class '6' egress expanded shaper."
    ::= { tPortEgrExpShaperStatsEntry 19 }

tPortEgrExpShaperCls7StFwdPkts OBJECT-TYPE
    SYNTAX          Counter64
    MAX-ACCESS      read-only
    STATUS          current
    DESCRIPTION
        "The value of tPortEgrExpShaperCls7StFwdPkts indicates the number of 
         packets forwarded by the class '7' egress expanded shaper."
    ::= { tPortEgrExpShaperStatsEntry 20 }

tPortEgrExpShaperCls7StFwdOcts OBJECT-TYPE
    SYNTAX          Counter64
    MAX-ACCESS      read-only
    STATUS          current
    DESCRIPTION
        "The value of tPortEgrExpShaperCls7StFwdOcts indicates the number of 
         octets forwarded by the class '7' egress expanded shaper."
    ::= { tPortEgrExpShaperStatsEntry 21 }

tPortEgrExpShaperCls7StMonOvrOct OBJECT-TYPE
    SYNTAX          Counter64
    MAX-ACCESS      read-only
    STATUS          current
    DESCRIPTION
        "The value of tPortEgrExpShaperCls7StMonOvrOct indicates the number of 
         octets above the configured monitor-threshold (since last read) by 
         the class '7' egress expanded shaper."
    ::= { tPortEgrExpShaperStatsEntry 22 }

tPortEgrExpShaperCls8StFwdPkts OBJECT-TYPE
    SYNTAX          Counter64
    MAX-ACCESS      read-only
    STATUS          current
    DESCRIPTION
        "The value of tPortEgrExpShaperCls8StFwdPkts indicates the number of 
         packets forwarded by the class '8' egress expanded shaper."
    ::= { tPortEgrExpShaperStatsEntry 23 }

tPortEgrExpShaperCls8StFwdOcts OBJECT-TYPE
    SYNTAX          Counter64
    MAX-ACCESS      read-only
    STATUS          current
    DESCRIPTION
        "The value of tPortEgrExpShaperCls8StFwdOcts indicates the number of 
         octets forwarded by the class '8' egress expanded shaper."
    ::= { tPortEgrExpShaperStatsEntry 24 }

tPortEgrExpShaperCls8StMonOvrOct OBJECT-TYPE
    SYNTAX          Counter64
    MAX-ACCESS      read-only
    STATUS          current
    DESCRIPTION
        "The value of tPortEgrExpShaperCls8StMonOvrOct indicates the number of 
         octets above the configured monitor-threshold (since last read) by 
         the class '8' egress expanded shaper."
    ::= { tPortEgrExpShaperStatsEntry 25 }

tPortEgrExpShaperAggStFwdPkts OBJECT-TYPE
    SYNTAX          Counter64
    MAX-ACCESS      read-only
    STATUS          current
    DESCRIPTION
        "The value of tPortEgrExpShaperAggStFwdPkts indicates the aggregate 
         number of packets forwarded by all of the classes of this egress 
         expanded shaper."
    ::= { tPortEgrExpShaperStatsEntry 26 }

tPortEgrExpShaperAggStFwdOcts OBJECT-TYPE
    SYNTAX          Counter64
    MAX-ACCESS      read-only
    STATUS          current
    DESCRIPTION
        "The value of tPortEgrExpShaperAggStFwdOcts indicates the aggregate 
         number of octets forwarded by all of the classes of this egress 
         expanded shaper."
    ::= { tPortEgrExpShaperStatsEntry 27 }

tPortEgrExpShaperAggStMonOvrOct OBJECT-TYPE
    SYNTAX          Counter64
    MAX-ACCESS      read-only
    STATUS          current
    DESCRIPTION
        "The value of tPortEgrExpShaperAggStMonOvrOct indicates the aggregate
         number of octets above the configured monitor-threshold 
         (since last read) by all of the classes of this egress expanded
         shaper."
    ::= { tPortEgrExpShaperStatsEntry 28 }

--
--    Port Egress Expanded-Secondary Shaper Stats (32 bit)
--

tPortEgrExpShaperStatsHLTable OBJECT-TYPE
    SYNTAX      SEQUENCE OF TPortEgrExpShaperStatsHLEntry
    MAX-ACCESS  not-accessible
    STATUS      current
    DESCRIPTION
        "The tPortEgrExpShaperStatsHLTable contains the statistics of each 
         egress expanded shaper at the port level configured on this system
         represented in higher 32 and lower 32 bit objects."
    ::= { tmnxPortObjs 63 }

tPortEgrExpShaperStatsHLEntry    OBJECT-TYPE
    SYNTAX      TPortEgrExpShaperStatsHLEntry
    MAX-ACCESS  not-accessible
    STATUS      current
    DESCRIPTION
        "Each row in tPortEgrExpShaperStatsHLEntry represents a particular 
         egress expanded secondary shaper statistics at the port level specified
         by tmnxPortEgrExpShaperName."
    INDEX { tmnxChassisIndex, tmnxPortPortID, tmnxPortEgrExpShaperName }
    ::= { tPortEgrExpShaperStatsHLTable 1}

TPortEgrExpShaperStatsHLEntry ::= SEQUENCE
    {
        tPortEgrExpShaperCls1StFwdPktsL    Counter32,
        tPortEgrExpShaperCls1StFwdPktsH    Counter32,
        tPortEgrExpShaperCls1StFwdOctsL    Counter32,
        tPortEgrExpShaperCls1StFwdOctsH    Counter32,
        tPortEgrExpShaperCls1StMonOvrOL    Counter32,
        tPortEgrExpShaperCls1StMonOvrOH    Counter32, 
        tPortEgrExpShaperCls2StFwdPktsL    Counter32,   
        tPortEgrExpShaperCls2StFwdPktsH    Counter32,
        tPortEgrExpShaperCls2StFwdOctsL    Counter32,
        tPortEgrExpShaperCls2StFwdOctsH    Counter32,
        tPortEgrExpShaperCls2StMonOvrOL    Counter32,
        tPortEgrExpShaperCls2StMonOvrOH    Counter32, 
        tPortEgrExpShaperCls3StFwdPktsL    Counter32,
        tPortEgrExpShaperCls3StFwdPktsH    Counter32,
        tPortEgrExpShaperCls3StFwdOctsL    Counter32,
        tPortEgrExpShaperCls3StFwdOctsH    Counter32,
        tPortEgrExpShaperCls3StMonOvrOL    Counter32,
        tPortEgrExpShaperCls3StMonOvrOH    Counter32, 
        tPortEgrExpShaperCls4StFwdPktsL    Counter32,
        tPortEgrExpShaperCls4StFwdPktsH    Counter32,
        tPortEgrExpShaperCls4StFwdOctsL    Counter32,
        tPortEgrExpShaperCls4StFwdOctsH    Counter32,
        tPortEgrExpShaperCls4StMonOvrOL    Counter32,
        tPortEgrExpShaperCls4StMonOvrOH    Counter32,
        tPortEgrExpShaperCls5StFwdPktsL    Counter32,
        tPortEgrExpShaperCls5StFwdPktsH    Counter32,
        tPortEgrExpShaperCls5StFwdOctsL    Counter32,
        tPortEgrExpShaperCls5StFwdOctsH    Counter32,
        tPortEgrExpShaperCls5StMonOvrOL    Counter32,
        tPortEgrExpShaperCls5StMonOvrOH    Counter32,
        tPortEgrExpShaperCls6StFwdPktsL    Counter32,
        tPortEgrExpShaperCls6StFwdPktsH    Counter32,
        tPortEgrExpShaperCls6StFwdOctsL    Counter32,
        tPortEgrExpShaperCls6StFwdOctsH    Counter32,
        tPortEgrExpShaperCls6StMonOvrOL    Counter32,
        tPortEgrExpShaperCls6StMonOvrOH    Counter32,
        tPortEgrExpShaperCls7StFwdPktsL    Counter32,
        tPortEgrExpShaperCls7StFwdPktsH    Counter32,
        tPortEgrExpShaperCls7StFwdOctsL    Counter32,
        tPortEgrExpShaperCls7StFwdOctsH    Counter32,
        tPortEgrExpShaperCls7StMonOvrOL    Counter32,
        tPortEgrExpShaperCls7StMonOvrOH    Counter32,
        tPortEgrExpShaperCls8StFwdPktsL    Counter32,
        tPortEgrExpShaperCls8StFwdPktsH    Counter32,
        tPortEgrExpShaperCls8StFwdOctsL    Counter32,
        tPortEgrExpShaperCls8StFwdOctsH    Counter32,
        tPortEgrExpShaperCls8StMonOvrOL    Counter32,
        tPortEgrExpShaperCls8StMonOvrOH    Counter32,
        tPortEgrExpShaperAggStFwdPktsL     Counter32,
        tPortEgrExpShaperAggStFwdPktsH     Counter32,
        tPortEgrExpShaperAggStFwdOctsL     Counter32,
        tPortEgrExpShaperAggStFwdOctsH     Counter32,
        tPortEgrExpShaperAggStMonOvrOL     Counter32,
        tPortEgrExpShaperAggStMonOvrOH     Counter32 

    }

tPortEgrExpShaperCls1StFwdPktsL OBJECT-TYPE
    SYNTAX          Counter32
    MAX-ACCESS      read-only
    STATUS          current
    DESCRIPTION
        "The value of tPortEgrExpShaperCls1StFwdPktsL indicates the lower 32
         bits of the value of tPortEgrExpShaperCls1StFwdPkts."
    ::= { tPortEgrExpShaperStatsHLEntry 1 }

tPortEgrExpShaperCls1StFwdPktsH OBJECT-TYPE
    SYNTAX          Counter32
    MAX-ACCESS      read-only
    STATUS          current
    DESCRIPTION
        "The value of tPortEgrExpShaperCls1StFwdPktsH indicates the higher 32
         bits of the value of tPortEgrExpShaperCls1StFwdPkts."
    ::= { tPortEgrExpShaperStatsHLEntry 2 }

tPortEgrExpShaperCls1StFwdOctsL OBJECT-TYPE
    SYNTAX          Counter32
    MAX-ACCESS      read-only
    STATUS          current
    DESCRIPTION
        "The value of tPortEgrExpShaperCls1StFwdOctsL indicates the lower 32 
         bits of the value of tPortEgrExpShaperCls1StFwdOcts."
    ::= { tPortEgrExpShaperStatsHLEntry 3 }

tPortEgrExpShaperCls1StFwdOctsH OBJECT-TYPE
    SYNTAX          Counter32
    MAX-ACCESS      read-only
    STATUS          current
    DESCRIPTION
        "The value of tPortEgrExpShaperCls1StFwdOctsH indicates the higher 32
         bits of the value of tPortEgrExpShaperCls1StFwdOcts."
    ::= { tPortEgrExpShaperStatsHLEntry 4 }

tPortEgrExpShaperCls1StMonOvrOL OBJECT-TYPE
    SYNTAX          Counter32
    MAX-ACCESS      read-only
    STATUS          current
    DESCRIPTION
        "The value of tPortEgrExpShaperCls1StMonOvrOL indicates the lower 32 
         bits of the value of tPortEgrExpShaperCls1StMonOvrOct."
    ::= { tPortEgrExpShaperStatsHLEntry 5 }

tPortEgrExpShaperCls1StMonOvrOH OBJECT-TYPE
    SYNTAX          Counter32
    MAX-ACCESS      read-only
    STATUS          current
    DESCRIPTION
        "The value of tPortEgrExpShaperCls1StMonOvrOH indicates the higher 32
         bits of the value of tPortEgrExpShaperCls1StMonOvrOct."
    ::= { tPortEgrExpShaperStatsHLEntry 6 }

tPortEgrExpShaperCls2StFwdPktsL OBJECT-TYPE
    SYNTAX          Counter32
    MAX-ACCESS      read-only
    STATUS          current
    DESCRIPTION
        "The value of tPortEgrExpShaperCls2StFwdPktsL indicates the lower 32
         bits of the value of tPortEgrExpShaperCls2StFwdPkts."
    ::= { tPortEgrExpShaperStatsHLEntry 7 }

tPortEgrExpShaperCls2StFwdPktsH OBJECT-TYPE
    SYNTAX          Counter32
    MAX-ACCESS      read-only
    STATUS          current
    DESCRIPTION
        "The value of tPortEgrExpShaperCls2StFwdPktsH indicates the higher 32
         bits of the value of tPortEgrExpShaperCls2StFwdPkts."
    ::= { tPortEgrExpShaperStatsHLEntry 8 }

tPortEgrExpShaperCls2StFwdOctsL OBJECT-TYPE
    SYNTAX          Counter32
    MAX-ACCESS      read-only
    STATUS          current
    DESCRIPTION
        "The value of tPortEgrExpShaperCls2StFwdOctsL indicates the lower 32
         bits of the value of tPortEgrExpShaperCls2StFwdOcts."
    ::= { tPortEgrExpShaperStatsHLEntry 9 }

tPortEgrExpShaperCls2StFwdOctsH OBJECT-TYPE
    SYNTAX          Counter32
    MAX-ACCESS      read-only
    STATUS          current
    DESCRIPTION
        "The value of tPortEgrExpShaperCls2StFwdOctsH indicates the higher 32
         bits of the value of tPortEgrExpShaperCls2StFwdOcts."
    ::= { tPortEgrExpShaperStatsHLEntry 10 }

tPortEgrExpShaperCls2StMonOvrOL OBJECT-TYPE
    SYNTAX          Counter32
    MAX-ACCESS      read-only
    STATUS          current
    DESCRIPTION
        "The value of tPortEgrExpShaperCls2StMonOvrOL indicates the lower 32 
         bits of the value of tPortEgrExpShaperCls2StMonOvrOct."
    ::= { tPortEgrExpShaperStatsHLEntry 11 }

tPortEgrExpShaperCls2StMonOvrOH OBJECT-TYPE
    SYNTAX          Counter32
    MAX-ACCESS      read-only
    STATUS          current
    DESCRIPTION
        "The value of tPortEgrExpShaperCls2StMonOvrOH indicates the higher 32
         bits of the value of tPortEgrExpShaperCls2StMonOvrOct."
    ::= { tPortEgrExpShaperStatsHLEntry 12 }

tPortEgrExpShaperCls3StFwdPktsL OBJECT-TYPE
    SYNTAX          Counter32
    MAX-ACCESS      read-only
    STATUS          current
    DESCRIPTION
        "The value of tPortEgrExpShaperCls3StFwdPktsL indicates the lower 32  
         bits of the value of tPortEgrExpShaperCls3StFwdPkts."
    ::= { tPortEgrExpShaperStatsHLEntry 13 }

tPortEgrExpShaperCls3StFwdPktsH OBJECT-TYPE
    SYNTAX          Counter32
    MAX-ACCESS      read-only
    STATUS          current
    DESCRIPTION
        "The value of tPortEgrExpShaperCls3StFwdPktsH indicates the higher 32 
         bits of the value of tPortEgrExpShaperCls3StFwdPkts."
    ::= { tPortEgrExpShaperStatsHLEntry 14 }

tPortEgrExpShaperCls3StFwdOctsL OBJECT-TYPE
    SYNTAX          Counter32
    MAX-ACCESS      read-only
    STATUS          current
    DESCRIPTION
        "The value of tPortEgrExpShaperCls3StFwdOctsL indicates the lower 32 
         bits of the value of tPortEgrExpShaperCls3StFwdOcts."
    ::= { tPortEgrExpShaperStatsHLEntry 15 }

tPortEgrExpShaperCls3StFwdOctsH OBJECT-TYPE
    SYNTAX          Counter32
    MAX-ACCESS      read-only
    STATUS          current
    DESCRIPTION
        "The value of tPortEgrExpShaperCls3StFwdOctsH indicates the higher 32 
         bits of the value of tPortEgrExpShaperCls3StFwdOcts."
    ::= { tPortEgrExpShaperStatsHLEntry 16 }

tPortEgrExpShaperCls3StMonOvrOL OBJECT-TYPE
    SYNTAX          Counter32
    MAX-ACCESS      read-only
    STATUS          current
    DESCRIPTION
        "The value of tPortEgrExpShaperCls3StMonOvrOL indicates the lower 32 
         bits of the value of tPortEgrExpShaperCls3StMonOvrOct."
    ::= { tPortEgrExpShaperStatsHLEntry 17 }

tPortEgrExpShaperCls3StMonOvrOH OBJECT-TYPE
    SYNTAX          Counter32
    MAX-ACCESS      read-only
    STATUS          current
    DESCRIPTION
        "The value of tPortEgrExpShaperCls3StMonOvrOH indicates the higher 32
         bits of the value of tPortEgrExpShaperCls3StMonOvrOct."
    ::= { tPortEgrExpShaperStatsHLEntry 18 }

tPortEgrExpShaperCls4StFwdPktsL OBJECT-TYPE
    SYNTAX          Counter32
    MAX-ACCESS      read-only
    STATUS          current
    DESCRIPTION
        "The value of tPortEgrExpShaperCls4StFwdPktsL indicates the lower 32  
         bits of the value of tPortEgrExpShaperCls4StFwdPkts."
    ::= { tPortEgrExpShaperStatsHLEntry 19 }

tPortEgrExpShaperCls4StFwdPktsH OBJECT-TYPE
    SYNTAX          Counter32
    MAX-ACCESS      read-only
    STATUS          current
    DESCRIPTION
        "The value of tPortEgrExpShaperCls4StFwdPktsH indicates the higher 32 
         bits of the value of tPortEgrExpShaperCls4StFwdPkts."
    ::= { tPortEgrExpShaperStatsHLEntry 20 }

tPortEgrExpShaperCls4StFwdOctsL OBJECT-TYPE
    SYNTAX          Counter32
    MAX-ACCESS      read-only
    STATUS          current
    DESCRIPTION
        "The value of tPortEgrExpShaperCls4StFwdOctsL indicates the lower 32 
         bits of the value of tPortEgrExpShaperCls4StFwdOcts."
    ::= { tPortEgrExpShaperStatsHLEntry 21 }

tPortEgrExpShaperCls4StFwdOctsH OBJECT-TYPE
    SYNTAX          Counter32
    MAX-ACCESS      read-only
    STATUS          current
    DESCRIPTION
        "The value of tPortEgrExpShaperCls4StFwdOctsH indicates the higher 32 
         bits of the value of tPortEgrExpShaperCls4StFwdOcts."
    ::= { tPortEgrExpShaperStatsHLEntry 22 }

tPortEgrExpShaperCls4StMonOvrOL OBJECT-TYPE
    SYNTAX          Counter32
    MAX-ACCESS      read-only
    STATUS          current
    DESCRIPTION
        "The value of tPortEgrExpShaperCls4StMonOvrOL indicates the lower 32 
         bits of the value of tPortEgrExpShaperCls4StMonOvrOct."
    ::= { tPortEgrExpShaperStatsHLEntry 23 }

tPortEgrExpShaperCls4StMonOvrOH OBJECT-TYPE
    SYNTAX          Counter32
    MAX-ACCESS      read-only
    STATUS          current
    DESCRIPTION
        "The value of tPortEgrExpShaperCls4StMonOvrOH indicates the higher 32
         bits of the value of tPortEgrExpShaperCls4StMonOvrOct."
    ::= { tPortEgrExpShaperStatsHLEntry 24 }

tPortEgrExpShaperCls5StFwdPktsL OBJECT-TYPE
    SYNTAX          Counter32
    MAX-ACCESS      read-only
    STATUS          current
    DESCRIPTION
        "The value of tPortEgrExpShaperCls5StFwdPktsL indicates the lower 32  
         bits of the value of tPortEgrExpShaperCls5StFwdPkts."
    ::= { tPortEgrExpShaperStatsHLEntry 25 }

tPortEgrExpShaperCls5StFwdPktsH OBJECT-TYPE
    SYNTAX          Counter32
    MAX-ACCESS      read-only
    STATUS          current
    DESCRIPTION
        "The value of tPortEgrExpShaperCls5StFwdPktsH indicates the higher 32 
         bits of the value of tPortEgrExpShaperCls5StFwdPkts."
    ::= { tPortEgrExpShaperStatsHLEntry 26 }

tPortEgrExpShaperCls5StFwdOctsL OBJECT-TYPE
    SYNTAX          Counter32
    MAX-ACCESS      read-only
    STATUS          current
    DESCRIPTION
        "The value of tPortEgrExpShaperCls5StFwdOctsL indicates the lower 32 
         bits of the value of tPortEgrExpShaperCls5StFwdOcts."
    ::= { tPortEgrExpShaperStatsHLEntry 27 }

tPortEgrExpShaperCls5StFwdOctsH OBJECT-TYPE
    SYNTAX          Counter32
    MAX-ACCESS      read-only
    STATUS          current
    DESCRIPTION
        "The value of tPortEgrExpShaperCls5StFwdOctsH indicates the higher 32 
         bits of the value of tPortEgrExpShaperCls5StFwdOcts."
    ::= { tPortEgrExpShaperStatsHLEntry 28 }

tPortEgrExpShaperCls5StMonOvrOL OBJECT-TYPE
    SYNTAX          Counter32
    MAX-ACCESS      read-only
    STATUS          current
    DESCRIPTION
        "The value of tPortEgrExpShaperCls5StMonOvrOL indicates the lower 32 
         bits of the value of tPortEgrExpShaperCls5StMonOvrOct."
    ::= { tPortEgrExpShaperStatsHLEntry 29 }

tPortEgrExpShaperCls5StMonOvrOH OBJECT-TYPE
    SYNTAX          Counter32
    MAX-ACCESS      read-only
    STATUS          current
    DESCRIPTION
        "The value of tPortEgrExpShaperCls5StMonOvrOH indicates the higher 32
         bits of the value of tPortEgrExpShaperCls5StMonOvrOct."
    ::= { tPortEgrExpShaperStatsHLEntry 30 }

tPortEgrExpShaperCls6StFwdPktsL OBJECT-TYPE
    SYNTAX          Counter32
    MAX-ACCESS      read-only
    STATUS          current
    DESCRIPTION
        "The value of tPortEgrExpShaperCls6StFwdPktsL indicates the lower 32  
         bits of the value of tPortEgrExpShaperCls6StFwdPkts."
    ::= { tPortEgrExpShaperStatsHLEntry 31 }

tPortEgrExpShaperCls6StFwdPktsH OBJECT-TYPE
    SYNTAX          Counter32
    MAX-ACCESS      read-only
    STATUS          current
    DESCRIPTION
        "The value of tPortEgrExpShaperCls6StFwdPktsH indicates the higher 32 
         bits of the value of tPortEgrExpShaperCls6StFwdPkts."
    ::= { tPortEgrExpShaperStatsHLEntry 32 }

tPortEgrExpShaperCls6StFwdOctsL OBJECT-TYPE
    SYNTAX          Counter32
    MAX-ACCESS      read-only
    STATUS          current
    DESCRIPTION
        "The value of tPortEgrExpShaperCls6StFwdOctsL indicates the lower 32 
         bits of the value of tPortEgrExpShaperCls6StFwdOcts."
    ::= { tPortEgrExpShaperStatsHLEntry 33 }

tPortEgrExpShaperCls6StFwdOctsH OBJECT-TYPE
    SYNTAX          Counter32
    MAX-ACCESS      read-only
    STATUS          current
    DESCRIPTION
        "The value of tPortEgrExpShaperCls6StFwdOctsH indicates the higher 32 
         bits of the value of tPortEgrExpShaperCls6StFwdOcts."
    ::= { tPortEgrExpShaperStatsHLEntry 34 }

tPortEgrExpShaperCls6StMonOvrOL OBJECT-TYPE
    SYNTAX          Counter32
    MAX-ACCESS      read-only
    STATUS          current
    DESCRIPTION
        "The value of tPortEgrExpShaperCls6StMonOvrOL indicates the lower 32 
         bits of the value of tPortEgrExpShaperCls6StMonOvrOct."
    ::= { tPortEgrExpShaperStatsHLEntry 35 }

tPortEgrExpShaperCls6StMonOvrOH OBJECT-TYPE
    SYNTAX          Counter32
    MAX-ACCESS      read-only
    STATUS          current
    DESCRIPTION
        "The value of tPortEgrExpShaperCls6StMonOvrOH indicates the higher 32
         bits of the value of tPortEgrExpShaperCls6StMonOvrOct."
    ::= { tPortEgrExpShaperStatsHLEntry 36 }

tPortEgrExpShaperCls7StFwdPktsL OBJECT-TYPE
    SYNTAX          Counter32
    MAX-ACCESS      read-only
    STATUS          current
    DESCRIPTION
        "The value of tPortEgrExpShaperCls7StFwdPktsL indicates the lower 32  
         bits of the value of tPortEgrExpShaperCls7StFwdPkts."
    ::= { tPortEgrExpShaperStatsHLEntry 37 }

tPortEgrExpShaperCls7StFwdPktsH OBJECT-TYPE
    SYNTAX          Counter32
    MAX-ACCESS      read-only
    STATUS          current
    DESCRIPTION
        "The value of tPortEgrExpShaperCls7StFwdPktsH indicates the higher 32 
         bits of the value of tPortEgrExpShaperCls7StFwdPkts."
    ::= { tPortEgrExpShaperStatsHLEntry 38 }

tPortEgrExpShaperCls7StFwdOctsL OBJECT-TYPE
    SYNTAX          Counter32
    MAX-ACCESS      read-only
    STATUS          current
    DESCRIPTION
        "The value of tPortEgrExpShaperCls7StFwdOctsL indicates the lower 32 
         bits of the value of tPortEgrExpShaperCls7StFwdOcts."
    ::= { tPortEgrExpShaperStatsHLEntry 39 }

tPortEgrExpShaperCls7StFwdOctsH OBJECT-TYPE
    SYNTAX          Counter32
    MAX-ACCESS      read-only
    STATUS          current
    DESCRIPTION
        "The value of tPortEgrExpShaperCls7StFwdOctsH indicates the higher 32 
         bits of the value of tPortEgrExpShaperCls7StFwdOcts."
    ::= { tPortEgrExpShaperStatsHLEntry 40 }

tPortEgrExpShaperCls7StMonOvrOL OBJECT-TYPE
    SYNTAX          Counter32
    MAX-ACCESS      read-only
    STATUS          current
    DESCRIPTION
        "The value of tPortEgrExpShaperCls7StMonOvrOL indicates the lower 32 
         bits of the value of tPortEgrExpShaperCls7StMonOvrOct."
    ::= { tPortEgrExpShaperStatsHLEntry 41 }

tPortEgrExpShaperCls7StMonOvrOH OBJECT-TYPE
    SYNTAX          Counter32
    MAX-ACCESS      read-only
    STATUS          current
    DESCRIPTION
        "The value of tPortEgrExpShaperCls7StMonOvrOH indicates the higher 32
         bits of the value of tPortEgrExpShaperCls7StMonOvrOct."
    ::= { tPortEgrExpShaperStatsHLEntry 42 }

tPortEgrExpShaperCls8StFwdPktsL OBJECT-TYPE
    SYNTAX          Counter32
    MAX-ACCESS      read-only
    STATUS          current
    DESCRIPTION
        "The value of tPortEgrExpShaperCls8StFwdPktsL indicates the lower 32  
         bits of the value of tPortEgrExpShaperCls8StFwdPkts."
    ::= { tPortEgrExpShaperStatsHLEntry 43 }

tPortEgrExpShaperCls8StFwdPktsH OBJECT-TYPE
    SYNTAX          Counter32
    MAX-ACCESS      read-only
    STATUS          current
    DESCRIPTION
        "The value of tPortEgrExpShaperCls8StFwdPktsH indicates the higher 32 
         bits of the value of tPortEgrExpShaperCls8StFwdPkts."
    ::= { tPortEgrExpShaperStatsHLEntry 44 }

tPortEgrExpShaperCls8StFwdOctsL OBJECT-TYPE
    SYNTAX          Counter32
    MAX-ACCESS      read-only
    STATUS          current
    DESCRIPTION
        "The value of tPortEgrExpShaperCls8StFwdOctsL indicates the lower 32 
         bits of the value of tPortEgrExpShaperCls8StFwdOcts."
    ::= { tPortEgrExpShaperStatsHLEntry 45 }

tPortEgrExpShaperCls8StFwdOctsH OBJECT-TYPE
    SYNTAX          Counter32
    MAX-ACCESS      read-only
    STATUS          current
    DESCRIPTION
        "The value of tPortEgrExpShaperCls8StFwdOctsH indicates the higher 32 
         bits of the value of tPortEgrExpShaperCls8StFwdOcts."
    ::= { tPortEgrExpShaperStatsHLEntry 46 }

tPortEgrExpShaperCls8StMonOvrOL OBJECT-TYPE
    SYNTAX          Counter32
    MAX-ACCESS      read-only
    STATUS          current
    DESCRIPTION
        "The value of tPortEgrExpShaperCls8StMonOvrOL indicates the lower 32 
         bits of the value of tPortEgrExpShaperCls8StMonOvrOct."
    ::= { tPortEgrExpShaperStatsHLEntry 47 }

tPortEgrExpShaperCls8StMonOvrOH OBJECT-TYPE
    SYNTAX          Counter32
    MAX-ACCESS      read-only
    STATUS          current
    DESCRIPTION
        "The value of tPortEgrExpShaperCls8StMonOvrOH indicates the higher 32
         bits of the value of tPortEgrExpShaperCls8StMonOvrOct."
    ::= { tPortEgrExpShaperStatsHLEntry 48 }

tPortEgrExpShaperAggStFwdPktsL OBJECT-TYPE
    SYNTAX          Counter32
    MAX-ACCESS      read-only
    STATUS          current
    DESCRIPTION
        "The value of tPortEgrExpShaperAggStFwdPktsL indicates the lower 32 
         bits of the value of tPortEgrExpShaperAggStFwdPkts."
    ::= { tPortEgrExpShaperStatsHLEntry 49 }

tPortEgrExpShaperAggStFwdPktsH OBJECT-TYPE
    SYNTAX          Counter32
    MAX-ACCESS      read-only
    STATUS          current
    DESCRIPTION
        "The value of tPortEgrExpShaperAggStFwdPktsH indicates the higher 32 
         bits of the value of tPortEgrExpShaperAggStFwdPkts."
    ::= { tPortEgrExpShaperStatsHLEntry 50 }

tPortEgrExpShaperAggStFwdOctsL OBJECT-TYPE
    SYNTAX          Counter32
    MAX-ACCESS      read-only
    STATUS          current
    DESCRIPTION
        "The value of tPortEgrExpShaperAggStFwdOctsL indicates the lower 32 
         bits of the value of tPortEgrExpShaperAggStFwdOcts."
    ::= { tPortEgrExpShaperStatsHLEntry 51 }

tPortEgrExpShaperAggStFwdOctsH OBJECT-TYPE
    SYNTAX          Counter32
    MAX-ACCESS      read-only
    STATUS          current
    DESCRIPTION
        "The value of tPortEgrExpShaperAggStFwdOctsH indicates the higher 32 
         bits of the value of tPortEgrExpShaperAggStFwdOcts."
    ::= { tPortEgrExpShaperStatsHLEntry 52 }

tPortEgrExpShaperAggStMonOvrOL OBJECT-TYPE
    SYNTAX          Counter32
    MAX-ACCESS      read-only
    STATUS          current
    DESCRIPTION
        "The value of tPortEgrExpShaperAggStMonOvrOL indicates the lower 32 
         bits of the value of tPortEgrExpShaperAggStMonOvrOct."
    ::= { tPortEgrExpShaperStatsHLEntry 53 }

tPortEgrExpShaperAggStMonOvrOH OBJECT-TYPE
    SYNTAX          Counter32
    MAX-ACCESS      read-only
    STATUS          current
    DESCRIPTION
        "The value of tPortEgrExpShaperAggStMonOvrOH indicates the higher 32 
         bits of the value of tPortEgrExpShaperAggStMonOvrOct."
    ::= { tPortEgrExpShaperStatsHLEntry 54 }


--
--    Port Egress VPort Aggregate Stats (64 bit) 
--

tPortEgrVPortAggStatsTable OBJECT-TYPE
    SYNTAX      SEQUENCE OF TPortEgrVPortAggStatsEntry
    MAX-ACCESS  not-accessible
    STATUS      current
    DESCRIPTION
        "The tPortEgrVPortAggStatsTable contains the statistics of each 
         virtual port at the port egress level configured on this system.
         Most objects are represented in 64 bit. 32-bit version of the objects
         are available in tPortEgrVPortAggStatsHLTable."
    ::= { tmnxPortObjs 64 }

tPortEgrVPortAggStatsEntry    OBJECT-TYPE
    SYNTAX      TPortEgrVPortAggStatsEntry
    MAX-ACCESS  not-accessible
    STATUS      current
    DESCRIPTION
        "Each row in tPortEgrVPortAggStatsEntry represents a particular 
         virtual port at the port egress level specified  by tPortEgrVPortName
         and tPortEgrVPStLvl."
    INDEX { tmnxChassisIndex, tmnxPortPortID, tPortEgrVPortName, 
            tPortEgrVPStLvl}
    ::= { tPortEgrVPortAggStatsTable 1}

TPortEgrVPortAggStatsEntry ::= SEQUENCE
    {
        tPortEgrVPStLvl              Unsigned32,
        tPortEgrVPStLstClrdTime      TimeStamp,
        tPortEgrVPStLvlFwdPkt        Counter64,
        tPortEgrVPStLvlFwdOct        Counter64,
        tPortEgrVPStLvlDpdPkt        Counter64,
        tPortEgrVPStLvlDpdOct        Counter64
    }

tPortEgrVPStLvl     OBJECT-TYPE
    SYNTAX      Unsigned32 (1..8|'ffffffff'H)
    MAX-ACCESS  not-accessible
    STATUS      current
    DESCRIPTION
        "The value of tPortEgrVPStLvl indicates the priority level
         for the port scheduler to which a subscriber host queue can be 
         port-parented. When the value of tPortEgrVPStLvl is specified as
         '0xffffffff H', snmp GET on this table returns aggregate statistics."
    ::= { tPortEgrVPortAggStatsEntry 1 }

tPortEgrVPStLstClrdTime OBJECT-TYPE
    SYNTAX          TimeStamp
    MAX-ACCESS      read-only
    STATUS          current
    DESCRIPTION
        "The value of tPortEgrVPStLstClrdTime indicates the sysUpTime
         when the counters in this table were last cleared."
    ::= { tPortEgrVPortAggStatsEntry 2 }

tPortEgrVPStLvlFwdPkt OBJECT-TYPE
    SYNTAX          Counter64
    MAX-ACCESS      read-only
    STATUS          current
    DESCRIPTION
        "The value of tPortEgrVPStLvlFwdPkt indicates the number of 
         packets forwarded by the virtual port for the priority level 
         specified by tPortEgrVPStLvl."
    ::= { tPortEgrVPortAggStatsEntry 3 }

tPortEgrVPStLvlFwdOct OBJECT-TYPE
    SYNTAX          Counter64
    MAX-ACCESS      read-only
    STATUS          current
    DESCRIPTION
        "The value of tPortEgrVPStLvlFwdOct indicates the number of 
         octets forwarded by the virtual port for the priority level 
         specified by tPortEgrVPStLvl."
    ::= { tPortEgrVPortAggStatsEntry 4 }

tPortEgrVPStLvlDpdPkt OBJECT-TYPE
    SYNTAX          Counter64
    MAX-ACCESS      read-only
    STATUS          current
    DESCRIPTION
        "The value of tPortEgrVPStLvlDpdPkt indicates the number of 
         packets dropped by the virtual port for the priority level 
         specified by tPortEgrVPStLvl."
    ::= { tPortEgrVPortAggStatsEntry 5 }

tPortEgrVPStLvlDpdOct OBJECT-TYPE
    SYNTAX          Counter64
    MAX-ACCESS      read-only
    STATUS          current
    DESCRIPTION
        "The value of tPortEgrVPStLvlDpdOct indicates the number of 
         octets dropped by the virtual port for the priority level 
         specified by tPortEgrVPStLvl."
    ::= { tPortEgrVPortAggStatsEntry 6 }

--
--    Port Egress VPort Aggregate Stats (32 bit)
--

tPortEgrVPortAggStatsHLTable OBJECT-TYPE
    SYNTAX      SEQUENCE OF TPortEgrVPortAggStatsHLEntry
    MAX-ACCESS  not-accessible
    STATUS      current
    DESCRIPTION
        "The tPortEgrVPortAggStatsHLTable contains the statistics of each 
         virtual port at the port egress level configured on this system
         represented in higher 32 and lower 32 bit objects."
    ::= { tmnxPortObjs 65 }

tPortEgrVPortAggStatsHLEntry    OBJECT-TYPE
    SYNTAX      TPortEgrVPortAggStatsHLEntry
    MAX-ACCESS  not-accessible
    STATUS      current
    DESCRIPTION
        "Each row in tPortEgrVPortAggStatsHLEntry represents a particular 
         virtual port statistics at the port egress level specified
         by tPortEgrVPortName and tPortEgrVPStLvl."
    INDEX { tmnxChassisIndex, tmnxPortPortID, tPortEgrVPortName,
            tPortEgrVPStLvl }
    ::= { tPortEgrVPortAggStatsHLTable 1}

TPortEgrVPortAggStatsHLEntry ::= SEQUENCE
    {
        tPortEgrVPStLvlFwdPktL    Counter32,
        tPortEgrVPStLvlFwdPktH    Counter32,
        tPortEgrVPStLvlFwdOctL    Counter32,
        tPortEgrVPStLvlFwdOctH    Counter32,
        tPortEgrVPStLvlDpdPktL    Counter32,
        tPortEgrVPStLvlDpdPktH    Counter32,
        tPortEgrVPStLvlDpdOctL    Counter32,
        tPortEgrVPStLvlDpdOctH    Counter32 
    }

tPortEgrVPStLvlFwdPktL OBJECT-TYPE
    SYNTAX          Counter32
    MAX-ACCESS      read-only
    STATUS          current
    DESCRIPTION
        "The value of tPortEgrVPStLvlFwdPktL indicates the lower 32
         bits of the value of tPortEgrVPStLvlFwdPkt."
    ::= { tPortEgrVPortAggStatsHLEntry 1 }

tPortEgrVPStLvlFwdPktH OBJECT-TYPE
    SYNTAX          Counter32
    MAX-ACCESS      read-only
    STATUS          current
    DESCRIPTION
        "The value of tPortEgrVPStLvlFwdPktH indicates the higher 32
         bits of the value of tPortEgrVPStLvlFwdPkt."
    ::= { tPortEgrVPortAggStatsHLEntry 2 }

tPortEgrVPStLvlFwdOctL OBJECT-TYPE
    SYNTAX          Counter32
    MAX-ACCESS      read-only
    STATUS          current
    DESCRIPTION
        "The value of tPortEgrVPStLvlFwdOctL indicates the lower 32 
         bits of the value of tPortEgrVPStLvlFwdOct."
    ::= { tPortEgrVPortAggStatsHLEntry 3 }

tPortEgrVPStLvlFwdOctH OBJECT-TYPE
    SYNTAX          Counter32
    MAX-ACCESS      read-only
    STATUS          current
    DESCRIPTION
        "The value of tPortEgrVPStLvlFwdOctH indicates the higher 32
         bits of the value of tPortEgrVPStLvlFwdOct."
    ::= { tPortEgrVPortAggStatsHLEntry 4 }

tPortEgrVPStLvlDpdPktL OBJECT-TYPE
    SYNTAX          Counter32
    MAX-ACCESS      read-only
    STATUS          current
    DESCRIPTION
        "The value of tPortEgrVPStLvlDpdPktL indicates the lower 32
         bits of the value of tPortEgrVPStLvlDpdPkt."
    ::= { tPortEgrVPortAggStatsHLEntry 5 }

tPortEgrVPStLvlDpdPktH OBJECT-TYPE
    SYNTAX          Counter32
    MAX-ACCESS      read-only
    STATUS          current
    DESCRIPTION
        "The value of tPortEgrVPStLvlDpdPktH indicates the higher 32
         bits of the value of tPortEgrVPStLvlDpdPkt."
    ::= { tPortEgrVPortAggStatsHLEntry 6 }

tPortEgrVPStLvlDpdOctL OBJECT-TYPE
    SYNTAX          Counter32
    MAX-ACCESS      read-only
    STATUS          current
    DESCRIPTION
        "The value of tPortEgrVPStLvlDpdOctL indicates the lower 32 
         bits of the value of tPortEgrVPStLvlDpdOct."
    ::= { tPortEgrVPortAggStatsHLEntry 7 }

tPortEgrVPStLvlDpdOctH OBJECT-TYPE
    SYNTAX          Counter32
    MAX-ACCESS      read-only
    STATUS          current
    DESCRIPTION
        "The value of tPortEgrVPStLvlDpdOctH indicates the higher 32
         bits of the value of tPortEgrVPStLvlDpdOct."
    ::= { tPortEgrVPortAggStatsHLEntry 8 }

--
--  Digital Diagnostic Monitor Table
--
tmnxDDMLaneTable                 OBJECT-TYPE
    SYNTAX      SEQUENCE OF TmnxDDMLaneEntry
    MAX-ACCESS  not-accessible
    STATUS      current
    DESCRIPTION
        "The tmnxDDMLaneTable has an entry for each CFP/CFP2/QSFP in the system
         that supports Lane Digital Diagnostic Monitoring (DDM). The table is
         indexed by tmnxPortPortID and tmnxDDMLaneId. Each row in this table is
         dynamically added and removed internally by the system based on the
         presence or absence of DDM capable CFP/CFP2/QSFP components."
    ::= { tmnxPortObjs 66 }

tmnxDDMLaneEntry                 OBJECT-TYPE
    SYNTAX      TmnxDDMLaneEntry
    MAX-ACCESS  not-accessible
    STATUS      current
    DESCRIPTION
        "Each row represents a particular CFP/CFP2/QSFP that supports Digital
         Diagnostic Monitoring Lanes.
         Entries are created and deleted internally by the system."
    INDEX { tmnxChassisIndex, tmnxPortPortID, tmnxDDMLaneId }
    ::= { tmnxDDMLaneTable 1}

TmnxDDMLaneEntry                 ::= SEQUENCE
{
    tmnxDDMLaneId                       Unsigned32,
    tmnxDDMLaneTemperature              Integer32,
    tmnxDDMLaneTempLowWarn              Integer32,
    tmnxDDMLaneTempLowAlarm             Integer32,
    tmnxDDMLaneTempHiWarn               Integer32,
    tmnxDDMLaneTempHiAlarm              Integer32,
    tmnxDDMLaneTxBiasCurrent            Integer32,
    tmnxDDMLaneTxBiasCurrentLowWarn     Integer32,
    tmnxDDMLaneTxBiasCurrentLowAlarm    Integer32,
    tmnxDDMLaneTxBiasCurrentHiWarn      Integer32,
    tmnxDDMLaneTxBiasCurrentHiAlarm     Integer32,
    tmnxDDMLaneTxOutputPower            Integer32,
    tmnxDDMLaneTxOutputPowerLowWarn     Integer32,
    tmnxDDMLaneTxOutputPowerLowAlarm    Integer32,
    tmnxDDMLaneTxOutputPowerHiWarn      Integer32,
    tmnxDDMLaneTxOutputPowerHiAlarm     Integer32,
    tmnxDDMLaneRxOpticalPower           Integer32,
    tmnxDDMLaneRxOpticalPwrLowWarn      Integer32,
    tmnxDDMLaneRxOpticalPwrLowAlarm     Integer32,
    tmnxDDMLaneRxOpticalPwrHiWarn       Integer32,
    tmnxDDMLaneRxOpticalPwrHiAlarm      Integer32,
    tmnxDDMLaneRxOpticalPowerType       INTEGER,
    tmnxDDMLaneFailedThresholds         TmnxDigitalDiagnosticFailureBits
}

tmnxDDMLaneId                    OBJECT-TYPE
    SYNTAX      Unsigned32 (1..16)
    MAX-ACCESS  not-accessible
    STATUS      current
    DESCRIPTION
        "The value of tmnxDDMLaneId specifies the Optical Lane ID for the row.
         The maximum ID for a given port is restricted to the value of
         tmnxPortSFPNumLanes for the given port. "
    ::= { tmnxDDMLaneEntry 1 }

tmnxDDMLaneTemperature           OBJECT-TYPE
    SYNTAX      Integer32
    MAX-ACCESS  read-only
    STATUS      current
    DESCRIPTION
        "The value of tmnxDDMLaneTemperature indicates the current temperature
         of the CFP/CFP2/QSFP in 1/256th degrees Celsius.

         The formula for translating between the value of tmnxDDMLaneTemperature
         and degrees Celsius is:
                tmnxDDMLaneTemperature / 256

         For example:
         The SNMP value 5734 is 22.4 degrees Celsius."
    ::= { tmnxDDMLaneEntry 2 }

tmnxDDMLaneTempLowWarn           OBJECT-TYPE
    SYNTAX      Integer32
    MAX-ACCESS  read-only
    STATUS      current
    DESCRIPTION
        "The value of tmnxDDMLaneTempLowWarn indicates the temperature
         of the CFP/CFP2/QSFP in degrees Celsius that triggers a low-Warning."
    ::= { tmnxDDMLaneEntry 3 }

tmnxDDMLaneTempLowAlarm          OBJECT-TYPE
    SYNTAX      Integer32
    MAX-ACCESS  read-only
    STATUS      current
    DESCRIPTION
        "The value of tmnxDDMLaneTempLowAlarm indicates the temperature
         of the CFP/CFP2/QSFP in degrees Celsius that triggers a low-alarm."
    ::= { tmnxDDMLaneEntry 4 }

tmnxDDMLaneTempHiWarn            OBJECT-TYPE
    SYNTAX      Integer32
    MAX-ACCESS  read-only
    STATUS      current
    DESCRIPTION
        "The value of tmnxDDMLaneTempHiWarn indicates the temperature
         of the CFP/CFP2/QSFP in degrees Celsius that triggers a hi-Warning."
    ::= { tmnxDDMLaneEntry 5 }

tmnxDDMLaneTempHiAlarm           OBJECT-TYPE
    SYNTAX      Integer32
    MAX-ACCESS  read-only
    STATUS      current
    DESCRIPTION
        "The value of tmnxDDMLaneTempHiAlarm indicates the temperature
         of the CFP/CFP2/QSFP in degrees Celsius that triggers a hi-alarm."
    ::= { tmnxDDMLaneEntry 6 }

tmnxDDMLaneTxBiasCurrent         OBJECT-TYPE
    SYNTAX      Integer32
    MAX-ACCESS  read-only
    STATUS      current
    DESCRIPTION
        "The value of tmnxDDMLaneTxBiasCurrent indicates the current Transmit
         Bias Current of the CFP/CFP2/QSFP in 1/500 milliamperes (mA).

         The formula for translating between the value of
         tmnxDDMLaneTxBiasCurrent and amperes is:
                tmnxDDMLaneTxBiasCurrent / 500

         For example:
         The SNMP value 2565 is 5.1 milliamperes (mA)."
    ::= { tmnxDDMLaneEntry 7 }

tmnxDDMLaneTxBiasCurrentLowWarn  OBJECT-TYPE
    SYNTAX      Integer32
    MAX-ACCESS  read-only
    STATUS      current
    DESCRIPTION
        "The value of tmnxDDMLaneTxBiasCurrentLowWarn indicates the Transmit
         Bias Current of the CFP/CFP2/QSFP in micro-Amperes (uA) that triggers
         a low-Warning."
    ::= { tmnxDDMLaneEntry 8 }

tmnxDDMLaneTxBiasCurrentLowAlarm OBJECT-TYPE
    SYNTAX      Integer32
    MAX-ACCESS  read-only
    STATUS      current
    DESCRIPTION
        "The value of tmnxDDMLaneTxBiasCurrentLowAlarm indicates the Transmit
         Bias Current of the CFP/CFP2/QSFP in micro-Amperes (uA) that triggers
         a low-alarm."
    ::= { tmnxDDMLaneEntry 9 }

tmnxDDMLaneTxBiasCurrentHiWarn   OBJECT-TYPE
    SYNTAX      Integer32
    MAX-ACCESS  read-only
    STATUS      current
    DESCRIPTION
        "The value of tmnxDDMLaneTxBiasCurrentHiWarn indicates the Transmit
         Bias Current of the CFP/CFP2/QSFP in micro-Amperes (uA) that triggers
         a hi-Warning."
    ::= { tmnxDDMLaneEntry 10 }

tmnxDDMLaneTxBiasCurrentHiAlarm  OBJECT-TYPE
    SYNTAX      Integer32
    MAX-ACCESS  read-only
    STATUS      current
    DESCRIPTION
        "The value of tmnxDDMLaneTxBiasCurrentHiAlarm indicates the Transmit
         Bias Current of the CFP/CFP2/QSFP in micro-Amperes (uA) that triggers
         a hi-alarm."
    ::= { tmnxDDMLaneEntry 11 }

tmnxDDMLaneTxOutputPower         OBJECT-TYPE
    SYNTAX      Integer32
    MAX-ACCESS  read-only
    STATUS      current
    DESCRIPTION
        "The value of tmnxDDMLaneTxOutputPower indicates the current Output
         Power of the CFP/CFP2/QSFP in one tenths of a microwatt (uW).

         For example:
         Using the SNMP value of 790, and using units of tenths of microwatt,
         790 becomes 79 microwatts or 0.079 milliwatts. Converting to dBm:
               10 x log10(0.079) = -11.0 dBm"
    ::= { tmnxDDMLaneEntry 12 }

tmnxDDMLaneTxOutputPowerLowWarn  OBJECT-TYPE
    SYNTAX      Integer32
    MAX-ACCESS  read-only
    STATUS      current
    DESCRIPTION
        "The value of tmnxDDMLaneTxOutputPowerLowWarn indicates the Output Power
         of the CFP/CFP2/QSFP in one tenths of a microwatt (uW) that triggers
         a low-Warning."
    ::= { tmnxDDMLaneEntry 13 }

tmnxDDMLaneTxOutputPowerLowAlarm OBJECT-TYPE
    SYNTAX      Integer32
    MAX-ACCESS  read-only
    STATUS      current
    DESCRIPTION
        "The value of tmnxDDMLaneTxOutputPowerLowAlarm indicates the Output
         Power of the CFP/CFP2/QSFP in one tenths of a microwatt (uW) that 
         triggers a low-alarm."
    ::= { tmnxDDMLaneEntry 14 }

tmnxDDMLaneTxOutputPowerHiWarn   OBJECT-TYPE
    SYNTAX      Integer32
    MAX-ACCESS  read-only
    STATUS      current
    DESCRIPTION
        "The value of tmnxDDMLaneTxOutputPowerHiWarn indicates the Output Power
         of the CFP/CFP2/QSFP in one tenths of a microwatt (uW) that triggers 
         a hi-warning."
    ::= { tmnxDDMLaneEntry 15 }

tmnxDDMLaneTxOutputPowerHiAlarm  OBJECT-TYPE
    SYNTAX      Integer32
    MAX-ACCESS  read-only
    STATUS      current
    DESCRIPTION
        "The value of tmnxDDMLaneTxOutputPowerHiAlarm indicates the Output Power
         of the CFP/CFP2/QSFP in one tenths of a microwatt (uW) that triggers 
         a hi-alarm."
    ::= { tmnxDDMLaneEntry 16 }

tmnxDDMLaneRxOpticalPower        OBJECT-TYPE
    SYNTAX      Integer32
    MAX-ACCESS  read-only
    STATUS      current
    DESCRIPTION
        "The value of tmnxDDMLaneRxOpticalPower indicates the current Received
         Optical Power of the CFP/CFP2/QSFP in one tenths of a microwatt (uW).

         For example:
         Using the SNMP value of 790, and using units of tenths of microwatt,
         790 becomes 79 microwatts or 0.079 milliwatts. Converting to dBm:
               10 x log10(0.079) = -11.0 dBm"
    ::= { tmnxDDMLaneEntry 17 }

tmnxDDMLaneRxOpticalPwrLowWarn   OBJECT-TYPE
    SYNTAX      Integer32
    MAX-ACCESS  read-only
    STATUS      current
    DESCRIPTION
        "The value of tmnxDDMLaneRxOpticalPwrLowWarn indicates the Received
         Optical Power of the CFP/CFP2/QSFP in one tenths of a microwatt (uW) 
         that triggers a low-Warning."
    ::= { tmnxDDMLaneEntry 18 }

tmnxDDMLaneRxOpticalPwrLowAlarm  OBJECT-TYPE
    SYNTAX      Integer32
    MAX-ACCESS  read-only
    STATUS      current
    DESCRIPTION
        "The value of tmnxDDMLaneRxOpticalPwrLowAlarm indicates the Received
         Optical Power of the CFP/CFP2/QSFP in one tenths of a microwatt (uW) 
         that triggers a low-alarm."
    ::= { tmnxDDMLaneEntry 19 }

tmnxDDMLaneRxOpticalPwrHiWarn    OBJECT-TYPE
    SYNTAX      Integer32
    MAX-ACCESS  read-only
    STATUS      current
    DESCRIPTION
        "The value of tmnxDDMLaneRxOpticalPwrHiWarn indicates the Received
         Optical Power of the CFP/CFP2/QSFP in one tenths of a microwatt (uW) 
         that triggers a hi-Warning."
    ::= { tmnxDDMLaneEntry 20 }

tmnxDDMLaneRxOpticalPwrHiAlarm   OBJECT-TYPE
    SYNTAX      Integer32
    MAX-ACCESS  read-only
    STATUS      current
    DESCRIPTION
        "The value of tmnxDDMLaneRxOpticalPwrHiAlarm indicates the Received
         Optical Power of the CFP/CFP2/QSFP in one tenths of a microwatt (uW) 
         that triggers a hi-alarm."
    ::= { tmnxDDMLaneEntry 21 }

tmnxDDMLaneRxOpticalPowerType    OBJECT-TYPE
    SYNTAX      INTEGER {
                    oma      (0),   -- Optical Modulation Amplitude
                    average  (1)    -- Average rx optical power
                }
    MAX-ACCESS  read-only
    STATUS      current
    DESCRIPTION
        "The value of tmnxDDMLaneRxOpticalPowerType indicates whether the
         tmnxDDMLaneRxOpticalPower was taken as an average, or as an Optical
         Modulation Amplitude (OMA)."
    ::= { tmnxDDMLaneEntry 22 }

tmnxDDMLaneFailedThresholds      OBJECT-TYPE
    SYNTAX      TmnxDigitalDiagnosticFailureBits
    MAX-ACCESS  read-only
    STATUS      current
    DESCRIPTION
        "The value of tmnxDDMLaneFailedThresholds indicates which objects
        of the monitored CFP/CFP2/QSFP is in a failed or cleared threshold 
        state.
        A set bit indicates that the specified threshold has been exceeded."
    ::= { tmnxDDMLaneEntry 23 }

-- ----------------------------------------
-- Port Network Egress QoS Queue Group Arbiter Statistics Table
-- ----------------------------------------
tPortNetEgrQGrpArbitStatTable OBJECT-TYPE
    SYNTAX          SEQUENCE OF TPortNetEgrQGrpArbitStatEntry
    MAX-ACCESS      not-accessible
    STATUS          current
    DESCRIPTION     
        "The value of tPortNetEgrQGrpArbitStatTable contains egress QoS queue
         group arbiter statistics on network side."
    ::= { tmnxPortObjs 68 }

tPortNetEgrQGrpArbitStatEntry OBJECT-TYPE
    SYNTAX          TPortNetEgrQGrpArbitStatEntry
    MAX-ACCESS      not-accessible
    STATUS          current
    DESCRIPTION     
        "The value of tPortNetEgrQGrpArbitStatEntry defines an entry in the
         tPortNetEgrQGrpArbitStatTable. It represents statistics about a 
         specific QoS egress queue group arbiter."
    INDEX           { tmnxChassisIndex, tmnxPortPortID, tPortNetEgrQGrpName,
                      tPortNetEgrQGrpInstanceId, tPortNetEgrQGrpArbitStatName }
    ::= { tPortNetEgrQGrpArbitStatTable 1 }

TPortNetEgrQGrpArbitStatEntry ::=
    SEQUENCE {
        tPortNetEgrQGrpArbitStatName             TNamedItem,
        tPortNetEgrQGrpArbitStatFwdPkts          Counter64,
        tPortNetEgrQGrpArbitStatFwdPktsL         Counter32,
        tPortNetEgrQGrpArbitStatFwdPktsH         Counter32,
        tPortNetEgrQGrpArbitStatFwdOcts          Counter64,
        tPortNetEgrQGrpArbitStatFwdOctsL         Counter32,
        tPortNetEgrQGrpArbitStatFwdOctsH         Counter32
    }

tPortNetEgrQGrpArbitStatName OBJECT-TYPE
    SYNTAX          TNamedItem
    MAX-ACCESS      not-accessible
    STATUS          current
    DESCRIPTION     
        "The value of tPortNetEgrQGrpArbitStatName specifies the name of the 
         egress QoS arbiter of this port network queue group."
    ::= { tPortNetEgrQGrpArbitStatEntry 1 }

tPortNetEgrQGrpArbitStatFwdPkts OBJECT-TYPE
    SYNTAX          Counter64
    MAX-ACCESS      read-only
    STATUS          current
    DESCRIPTION     
       "The value of tPortNetEgrQGrpArbitStatFwdPkts indicates the number of 
        fowrwarded packets by the egress queue group arbiter Pchip."
    ::= { tPortNetEgrQGrpArbitStatEntry 2 }

tPortNetEgrQGrpArbitStatFwdPktsL OBJECT-TYPE
    SYNTAX          Counter32
    MAX-ACCESS      read-only
    STATUS          current
    DESCRIPTION     
       "The value of tPortNetEgrQGrpArbitStatFwdPktsL indicates the lower 32
        bits of tPortNetEgrQGrpArbitStatFwdPkts."
    ::= { tPortNetEgrQGrpArbitStatEntry 3 }

tPortNetEgrQGrpArbitStatFwdPktsH OBJECT-TYPE
    SYNTAX          Counter32
    MAX-ACCESS      read-only
    STATUS          current
    DESCRIPTION     
       "The value of tPortNetEgrQGrpArbitStatFwdPktsH indicates the upper 32
        bits of tPortNetEgrQGrpArbitStatFwdPkts."
    ::= { tPortNetEgrQGrpArbitStatEntry 4 }

tPortNetEgrQGrpArbitStatFwdOcts OBJECT-TYPE
    SYNTAX          Counter64
    MAX-ACCESS      read-only
    STATUS          current
    DESCRIPTION     
       "The value of tPortNetEgrQGrpArbitStatFwdOcts indicates the number of 
        fowrwarded octets by the egress queue group arbiter Pchip."
    ::= { tPortNetEgrQGrpArbitStatEntry 5 }

tPortNetEgrQGrpArbitStatFwdOctsL OBJECT-TYPE
    SYNTAX          Counter32
    MAX-ACCESS      read-only
    STATUS          current
    DESCRIPTION     
       "The value of tPortNetEgrQGrpArbitStatFwdOctsL indicates the lower 32
        bits of tPortNetEgrQGrpArbitStatFwdOcts."
    ::= { tPortNetEgrQGrpArbitStatEntry 6 }

tPortNetEgrQGrpArbitStatFwdOctsH OBJECT-TYPE
    SYNTAX          Counter32
    MAX-ACCESS      read-only
    STATUS          current
    DESCRIPTION     
       "The value of tPortNetEgrQGrpArbitStatFwdOctsH indicates the upper 32
        bits of tPortNetEgrQGrpArbitStatFwdOcts."
    ::= { tPortNetEgrQGrpArbitStatEntry 7 }

--
--      Port Policies
--

tmnxPortPlcyTableLastCh OBJECT-TYPE
    SYNTAX      TimeStamp
    MAX-ACCESS  read-only
    STATUS      current
    DESCRIPTION
        "The value of the object tmnxPortPlcyTableLastCh indicates
         the value of sysUpTime at the time of the last modification of
         an entry in the tmnxPortPlcyTable."
    ::= { tmnxPortPlcyObjs 1 }

tmnxPortPlcyTable OBJECT-TYPE
    SYNTAX      SEQUENCE OF TmnxPortPlcyEntry
    MAX-ACCESS  not-accessible
    STATUS      current
    DESCRIPTION
        "The tmnxPortPlcyTable allows configuration of 
         port policies.
         
         A port policy has port parameters that can be applied
         to applicable ports associated with such a policy."
    ::= { tmnxPortPlcyObjs 2 }

tmnxPortPlcyEntry OBJECT-TYPE
    SYNTAX      TmnxPortPlcyEntry
    MAX-ACCESS  not-accessible
    STATUS      current
    DESCRIPTION
        "Each row represents the configuration
         of a specific port policy.
        
         Rows in this table can be created and deleted via SNMP SET
         operations to tmnxPortPlcyRowStatus."
    INDEX { IMPLIED tmnxPortPlcyName }
    ::= { tmnxPortPlcyTable 1 }

TmnxPortPlcyEntry ::=
    SEQUENCE {
        tmnxPortPlcyName                 TNamedItem,
        tmnxPortPlcyRowStatus            RowStatus,
        tmnxPortPlcyLastCh               TimeStamp,
        tmnxPortPlcyDescription          TItemDescription,
        tmnxPortPlcyEgrPortSchedPlcy     TNamedItemOrEmpty
    }

tmnxPortPlcyName OBJECT-TYPE
    SYNTAX      TNamedItem
    MAX-ACCESS  not-accessible
    STATUS      current
    DESCRIPTION
        "The value of tmnxPortPlcyName specifies 
         the identifier of a port policy."
    ::= { tmnxPortPlcyEntry 1 }

tmnxPortPlcyRowStatus OBJECT-TYPE
    SYNTAX      RowStatus
    MAX-ACCESS  read-create
    STATUS      current
    DESCRIPTION
        "The value of tmnxPortPlcyRowStatus controls the creation and
         deletion of rows in the table."
    ::= { tmnxPortPlcyEntry 2 }

tmnxPortPlcyLastCh OBJECT-TYPE
    SYNTAX      TimeStamp
    MAX-ACCESS  read-only
    STATUS      current
    DESCRIPTION
        "The value of tmnxPortPlcyLastCh indicates the sysUpTime at
         the time of the most recent management-initiated change to this
         policy."
    ::= { tmnxPortPlcyEntry 3 }

tmnxPortPlcyDescription OBJECT-TYPE
    SYNTAX      TItemDescription
    MAX-ACCESS  read-create
    STATUS      current
    DESCRIPTION
        "The value of tmnxPortPlcyDescription specifies the user provided
         description of this policy."
    DEFVAL { "" }
    ::= { tmnxPortPlcyEntry 4 }

tmnxPortPlcyEgrPortSchedPlcy OBJECT-TYPE
    SYNTAX      TNamedItemOrEmpty
    MAX-ACCESS  read-create
    STATUS      current
    DESCRIPTION
       "The value of tmnxPortPlcyEgrPortSchedPlcy specifies
        the egress QoS port-scheduler policy. 
        
        This object must correspond to the index 
        of a row in TIMETRA-QOS-MIB::tPortSchedulerPlcyTable."
    DEFVAL    { "" }
    ::= { tmnxPortPlcyEntry 5 }

-- Pseudo-Wire Port table

tmnxPwPortTblLastChanged  OBJECT-TYPE
    SYNTAX          TimeStamp
    MAX-ACCESS      read-only
    STATUS          current
    DESCRIPTION
        "The value of tmnxPwPortTblLastChanged indicates the sysUpTime
         at the time of the last modification of tmnxPwPortTable.

         If no changes were made to the entry since the last re-initialization
         of the local network management subsystem, then this object contains a
         zero value."
    ::= { tmnxPortObjs 69 }

tmnxPwPortTable OBJECT-TYPE
    SYNTAX          SEQUENCE OF TmnxPwPortEntry
    MAX-ACCESS      not-accessible
    STATUS          current
    DESCRIPTION
        "A table that contains pseudo-wire port information in the system."
    ::= { tmnxPortObjs 70 }

tmnxPwPortEntry OBJECT-TYPE
    SYNTAX          TmnxPwPortEntry
    MAX-ACCESS      not-accessible
    STATUS          current
    DESCRIPTION
        "A row-entry that contains port specific pseudo-wire information."
    INDEX           { tmnxPwPortId }
    ::= { tmnxPwPortTable 1 }

TmnxPwPortEntry ::=
    SEQUENCE {
        tmnxPwPortId                    Unsigned32,
        tmnxPwPortRowStatus             RowStatus,
        tmnxPwPortLastChgd              TimeStamp,
        tmnxPwPortEncapType             INTEGER
    }

tmnxPwPortId OBJECT-TYPE
    SYNTAX          Unsigned32 (1..10239)
    MAX-ACCESS      not-accessible
    STATUS          current
    DESCRIPTION
        "This value of the object tmnxPwPortId specifies the pseudo-wire
         port in the system."
    ::= { tmnxPwPortEntry 1 }

tmnxPwPortRowStatus OBJECT-TYPE
    SYNTAX          RowStatus
    MAX-ACCESS      read-create
    STATUS          current
    DESCRIPTION
        "This value of the object tmnxPwPortRowStatus specifies the
         status of this row."
    ::= { tmnxPwPortEntry 2 }

tmnxPwPortLastChgd OBJECT-TYPE
    SYNTAX       TimeStamp
    MAX-ACCESS   read-only
    STATUS       current
    DESCRIPTION  
        "The value of tmnxPwPortLastChgd indicates the timestamp of last
        change to this row in tmnxPwPortTable."
    ::= { tmnxPwPortEntry 3 }  

tmnxPwPortEncapType OBJECT-TYPE
    SYNTAX       INTEGER {
                     dot1q (2),
                     qinq  (10)
                 }
    MAX-ACCESS   read-create
    STATUS       current
    DESCRIPTION  
        "The value of tmnxPwPortEncapType specifies the encapsulation type
         of this pseudo-wire port entry."
    DEFVAL { dot1q }
    ::= { tmnxPwPortEntry 4 }  

-- --------------------------------------------------
-- dot1X PAE Port table
-- --------------------------------------------------

tmnxDot1xPaePortTblLastChanged OBJECT-TYPE
    SYNTAX          TimeStamp
    MAX-ACCESS      read-only
    STATUS          current
    DESCRIPTION     "The value of tmnxDot1xPaePortTblLastChanged indicates the
                     sysUpTime at the time of the last modification of
                     tmnxDot1xPaePortTable.

                     If no changes were made to the entry since the last
                     re-initialization of the local network management
                     subsystem, then this object contains a zero value."
    ::= { tmnxPortObjs 77 }

tmnxDot1xPaePortTable OBJECT-TYPE
    SYNTAX          SEQUENCE OF Tmnxdot1xPaePortEntry
    MAX-ACCESS      not-accessible
    STATUS          current
    DESCRIPTION     "A table that contains dot1x PAE port information in the
                     system."
    ::= { tmnxPortObjs 78 }

tmnxDot1xPaePortEntry OBJECT-TYPE
    SYNTAX          Tmnxdot1xPaePortEntry
    MAX-ACCESS      not-accessible
    STATUS          current
    DESCRIPTION     "A row-entry that contains port specific dot1x PAE
                     information."
    INDEX           { dot1xPaePortNumber }
    ::= { tmnxDot1xPaePortTable 1 }

Tmnxdot1xPaePortEntry ::=
    SEQUENCE {
        tmnxDot1xPaePortTunneling   TruthValue
    }

tmnxDot1xPaePortTunneling OBJECT-TYPE
    SYNTAX          TruthValue
    MAX-ACCESS      read-write
    STATUS          current
    DESCRIPTION     "The value of tmnxDot1xPaePortTunneling specifies whether
                     the dot1x packet tunneling for the ethernet port is
                     enabled or disabled. When tunneling is enabled, the port
                     will not process any untagged dot1x packets but will
                     tunnel them through instead."
    DEFVAL { false }
    ::= { tmnxDot1xPaePortEntry 1 }


--
--  Coherent Optical Port Configuration Table
--
tmnxCohOptPortCfgTable           OBJECT-TYPE
    SYNTAX      SEQUENCE OF TmnxCohOptPortCfgEntry
    MAX-ACCESS  not-accessible
    STATUS      current
    DESCRIPTION
        "The tmnxCohOptPortCfgTable contains information pertaining to the
         configuration of DWDM coherent optical ports in the Alcatel-Lucent
         SROS system."
    ::= { tmnxPortObjs 71 }

tmnxCohOptPortCfgEntry           OBJECT-TYPE
    SYNTAX      TmnxCohOptPortCfgEntry
    MAX-ACCESS  not-accessible
    STATUS      current
    DESCRIPTION
        "Each row entry represents the configuration for a DWDM coherent
         optical port in the system. Entries cannot be created or deleted via
         SNMP SET operations."
    INDEX { tmnxChassisIndex, tmnxPortPortID }
    ::= { tmnxCohOptPortCfgTable 1 }

TmnxCohOptPortCfgEntry ::=
    SEQUENCE {
        tmnxCohOptPortCfgAlarms        TmnxCoherentOpticalAlarm,
        tmnxCohOptPortCfgRxChan        TmnxOpticalDwdmChannel,
        tmnxCohOptPortDispCtrlMode     TmnxOpticalDispCtrlMode,
        tmnxCohOptPortManCfgDisp       Integer32,
        tmnxCohOptPortDispSwpStart     Integer32,
        tmnxCohOptPortDispSwpEnd       Integer32,
        tmnxCohOptPortCfgTxPower       Integer32,
        tmnxCohOptPortCfgCprWinSize    Unsigned32,
        tmnxCohOptPortCfgRxLosThresh   Integer32,
        tmnxCohOptPortRxLosReaction    TmnxPortLosReaction
    }

tmnxCohOptPortCfgAlarms          OBJECT-TYPE
    SYNTAX      TmnxCoherentOpticalAlarm
    MAX-ACCESS  read-write
    STATUS      current
    DESCRIPTION
        "The value of tmnxCohOptPortCfgAlarms specifies the alarms that are
         monitored by the coherent optical interface. If an alarm bit is
         set, then the corresponding alarm will generate a raise or clear
         notification when its state changes. An unset bit specifies that the
         alarm corresponding to the bit will not report on its state
         transitions."
    DEFVAL { {moduleFault, module, netRx, netTx, hostTx} }
    ::= { tmnxCohOptPortCfgEntry 1 }

tmnxCohOptPortCfgRxChan          OBJECT-TYPE
    SYNTAX      TmnxOpticalDwdmChannel
    MAX-ACCESS  read-write
    STATUS      current
    DESCRIPTION
        "The value of tmnxCohOptPortCfgRxChan specifies the DWDM ITU channel at
         which the tunable coherent optical module should operate.

         If a value of zero(0) has been specified, tmnxCohOptPortPresRxChan
         will be changed by the system to be equivalent to
         tmnxPortDwdmLaserChannel.

         tmnxCohOptPortCfgRxChan should be set to the same value as
         tmnxPortDwdmLaserChannel in most cases, but may be set to a different
         value when the received wavelength is different from the transmitted
         wavelength."
    DEFVAL { 0 }
    ::= { tmnxCohOptPortCfgEntry 2 }

tmnxCohOptPortDispCtrlMode       OBJECT-TYPE
    SYNTAX      TmnxOpticalDispCtrlMode
    MAX-ACCESS  read-write
    STATUS      current
    DESCRIPTION
        "The value of tmnxCohOptPortDispCtrlMode specifies the current
         dispersion compensation mode of the coherent optical module.

         When tmnxCohOptPortDispCtrlMode is set to 'automatic(0)', the
         dispersion setpoint is automatically determined but under the
         constraints specified by tmnxCohOptPortDispSwpStart and
         tmnxCohOptPortDispSwpEnd.

         When tmnxCohOptPortDispCtrlMode is set to 'manual(1)', the dispersion
         setpoint is fixed to the value specified by tmnxCohOptPortManCfgDisp."
    DEFVAL { automatic }
    ::= { tmnxCohOptPortCfgEntry 3 }

tmnxCohOptPortManCfgDisp         OBJECT-TYPE
    SYNTAX      Integer32 (-50000..50000)
    UNITS       "picoseconds per nanometer"
    MAX-ACCESS  read-write
    STATUS      current
    DESCRIPTION
        "The value of tmnxCohOptPortManCfgDisp specifies the manually
         configured dispersion of the coherent optical module. This parameter
         is valid when the tmnxCohOptPortDispCtrlMode is 'manual(1)'."
    DEFVAL { 0 }
    ::= { tmnxCohOptPortCfgEntry 4 }

tmnxCohOptPortDispSwpStart       OBJECT-TYPE
    SYNTAX      Integer32 (-50000..50000)
    UNITS       "picoseconds per nanometer"
    MAX-ACCESS  read-write
    STATUS      current
    DESCRIPTION
        "The value of tmnxCohOptPortDispSwpStart specifies the start value for
         dispersion sweeping on a coherent optical module."
    DEFVAL { -25500 }
    ::= { tmnxCohOptPortCfgEntry 5 }

tmnxCohOptPortDispSwpEnd         OBJECT-TYPE
    SYNTAX      Integer32 (-50000..50000)
    UNITS       "picoseconds per nanometer"
    MAX-ACCESS  read-write
    STATUS      current
    DESCRIPTION
        "The value of tmnxCohOptPortDispSwpEnd specifies the end value for
         dispersion sweeping on a coherent optical module."
    DEFVAL { 2000 }
    ::= { tmnxCohOptPortCfgEntry 6 }

tmnxCohOptPortCfgTxPower         OBJECT-TYPE
    SYNTAX      Integer32 (-2000..300)
    UNITS       "mBm"
    MAX-ACCESS  read-write
    STATUS      current
    DESCRIPTION
        "The value of tmnxCohOptPortCfgTxPower specifies the desired average
         output power of the interface's transmitted optical signal when the
         port is enabled.

         The UNITS millibels (mBm) are units of 0.01 decibel relative to one
         milliwatt (0 dBm) or dBm multiplied by 100. The mBm is used when an
         integer is required. For example -5.21 dBm is equivalent to -521 mBm."
    DEFVAL { 100 }
    ::= { tmnxCohOptPortCfgEntry 7 }

tmnxCohOptPortCfgCprWinSize      OBJECT-TYPE
    SYNTAX      Unsigned32 (2|4|8|16|32|64)
    UNITS       "symbols"
    MAX-ACCESS  read-write
    STATUS      current
    DESCRIPTION
        "The value of tmnxCohOptPortCfgCprWinSize specifies the manually
         configured Carrier Phase Recovery (CPR) window size.

         The configured CPR window size is independent of the optimal window
         size, tmnxCohOptPortCprWnSzSrchResult, found by a search using
         tmnxCohOptPortCprWinSizeSearch. Once the network manager has found an
         optimal window size in tmnxCohOptPortCprWnSzSrchResult, the network
         manager has the option to use it for tmnxCohOptPortCfgCprWinSize."
    DEFVAL { 32 }
    ::= { tmnxCohOptPortCfgEntry 8 }

tmnxCohOptPortCfgRxLosThresh     OBJECT-TYPE
    SYNTAX      Integer32 (-2400..-1300)
    UNITS       "mBm"
    MAX-ACCESS  read-write
    STATUS      current
    DESCRIPTION
        "The value of tmnxCohOptPortCfgRxLosThresh specifies the desired
         average input power LOS (Loss Of Signal) threshold of the interface's
         received optical signal.

         The UNITS millibels (mBm) are units of 0.01 decibel relative to one
         milliwatt (0 dBm) or dBm multiplied by 100. The mBm is used when an
         integer is required. For example -15.21 dBm is equivalent to -1521
         mBm."
    DEFVAL { -2300 }
    ::= { tmnxCohOptPortCfgEntry 9 }

tmnxCohOptPortRxLosReaction      OBJECT-TYPE
    SYNTAX      TmnxPortLosReaction
    MAX-ACCESS  read-write
    STATUS      current
    DESCRIPTION
        "The value of tmnxCohOptPortRxLosReaction specifies the type of
         action that is taken in the event of an RX Loss Of Signal (LOS). The
         valid modes are as follows:

                - none     - Specifies that the interface not be taken down on
                             crossing the optical RX LOS threshold, to allow
                             the FEC to keep correcting as much as it can.
                - squelch  - Specifies that the interface be taken down on
                             crossing the optical RX LOS threshold."
    DEFVAL { squelch }
    ::= { tmnxCohOptPortCfgEntry 10 }

--
--  Coherent Optical Port Command Table
--
tmnxCohOptPortCommandTable       OBJECT-TYPE
    SYNTAX      SEQUENCE OF TmnxCohOptPortCommandEntry
    MAX-ACCESS  not-accessible
    STATUS      current
    DESCRIPTION
        "The tmnxCohOptPortCommandTable contains information pertaining to
         the execution of commands on DWDM coherent optical ports in the
         Alcatel-Lucent SROS system."
    ::= { tmnxPortObjs 72 }

tmnxCohOptPortCommandEntry       OBJECT-TYPE
    SYNTAX      TmnxCohOptPortCommandEntry
    MAX-ACCESS  not-accessible
    STATUS      current
    DESCRIPTION
        "Each row entry exists only if the associated tmnxCohOptPortCfgEntry
         exists. Entries cannot be created or deleted via SNMP SET operations."
    AUGMENTS { tmnxCohOptPortCfgEntry }
    ::= { tmnxCohOptPortCommandTable 1 }

TmnxCohOptPortCommandEntry ::=
    SEQUENCE {
        tmnxCohOptPortCprWinSizeSearch  INTEGER,
        tmnxCohOptPortCprWnSzSrchStatus INTEGER,
        tmnxCohOptPortCprWnSzSrchResult Unsigned32
    }

tmnxCohOptPortCprWinSizeSearch   OBJECT-TYPE
    SYNTAX      INTEGER {
                   noCmd   (1),
                   execute (2)
                }
    MAX-ACCESS  read-write
    STATUS      current
    DESCRIPTION
        "The value of tmnxCohOptPortCprWinSizeSearch specifies the execution
         of a search for the optimal CPR window size when the value specified
         is 'execute(2)'. When the value specified is 'noCmd(1)', no action
         will be taken.
         
         The status of the search can be found in
         tmnxCohOptPortCprWnSzSrchStatus. The search result can be found in
         tmnxCohOptPortCprWnSzSrchResult.
         
         If the value specified is 'execute(2)' and the
         tmnxCohOptPortCprWnSzSrchStatus is 'inProgress(2)', the action will be
         rejected with an error status of inconsistentValue.
         
         In an SNNP get response, tmnxCohOptPortCprWinSizeSearch will have a
         value of 'noCmd(1)'."
    DEFVAL { noCmd }
    ::= { tmnxCohOptPortCommandEntry 1 }

tmnxCohOptPortCprWnSzSrchStatus  OBJECT-TYPE
    SYNTAX      INTEGER {
                   none       (1),
                   requested  (2),
                   starting   (3),
                   inProgress (4),
                   succeeded  (5),
                   failed     (6)
                }
    MAX-ACCESS  read-only
    STATUS      current
    DESCRIPTION
        "The value of tmnxCohOptPortCprWnSzSrchStatus indicates the status of
         the last search for the CPR optimal window size, executed by
         tmnxCohOptPortCprWinSizeSearch with a value of 'execute(2)'.
         
         The value will be 'none(1)' if no search has been performed since the
         last system startup or since the last reset of the associated MDA or
         IOM.

         The value will be 'requested(2)' if the search was requested by the
         user but has not started because the tmnxCohOptPortModState is not
         'ready(8)'.

         The value will be 'starting(3)' if the search was requested and the
         tmnxCohOptPortModRxTurnUpStates has not achieved 'adcSignal'.
         
         The value will be 'inProgress(4)' if the search is in progress.
         
         The value will be 'succeeded(5)' if the search has completed
         successfully.
         
         The value will be 'failed(6)' if the search has completed with
         a failure."
    ::= { tmnxCohOptPortCommandEntry 2 }

tmnxCohOptPortCprWnSzSrchResult  OBJECT-TYPE
    SYNTAX      Unsigned32
    UNITS       "symbols"
    MAX-ACCESS  read-only
    STATUS      current
    DESCRIPTION
        "The value of tmnxCohOptPortCprWnSzSrchResult indicates the CPR
         optimal window size found on the last search for the CPR optimal
         window size, executed by tmnxCohOptPortCprWinSizeSearch with a value
         of 'execute(2)'. The value of tmnxCohOptPortCprWnSzSrchResult may not
         be equivalent to what is configured for tmnxCohOptPortCfgCprWinSize.
         
         The tmnxCohOptPortCprWnSzSrchResult value of 0 indicates that no CPR
         optimal window size was found."
    ::= { tmnxCohOptPortCommandEntry 3 }

--
--  Coherent Optical Port Operational Table
--
tmnxCohOptPortOperTable          OBJECT-TYPE
    SYNTAX      SEQUENCE OF TmnxCohOptPortOperEntry
    MAX-ACCESS  not-accessible
    STATUS      current
    DESCRIPTION
        "The tmnxCohOptPortOperTable contains information pertaining to the
         operational state of DWDM coherent optical ports in the Alcatel-Lucent
         SROS system."
    ::= { tmnxPortObjs 73 }

tmnxCohOptPortOperEntry          OBJECT-TYPE
    SYNTAX      TmnxCohOptPortOperEntry
    MAX-ACCESS  not-accessible
    STATUS      current
    DESCRIPTION
        "Each row entry represents the operational state for a DWDM coherent
         optical port in the system. Entries cannot be created or deleted via
         SNMP SET operations."
    INDEX { tmnxChassisIndex, tmnxPortPortID }
    ::= { tmnxCohOptPortOperTable 1 }

TmnxCohOptPortOperEntry ::=
    SEQUENCE {
        tmnxCohOptPortAlarmState        TmnxCoherentOpticalAlarm,
        tmnxCohOptPortDefectPoints      TmnxCoherentOpticalDefectPoint,
        tmnxCohOptPortPresRxChan        TmnxOpticalDwdmChannel,
        tmnxCohOptPortModState          INTEGER,
        tmnxCohOptPortModTxTurnUpStates BITS,
        tmnxCohOptPortModRxTurnUpStates BITS,
        tmnxCohOptPortRxSNRXPolar       Integer32,
        tmnxCohOptPortRxSNRYPolar       Integer32,
        tmnxCohOptPortRxQMargin         Integer32
    }

tmnxCohOptPortAlarmState         OBJECT-TYPE
    SYNTAX      TmnxCoherentOpticalAlarm
    MAX-ACCESS  read-only
    STATUS      current
    DESCRIPTION
        "The value of tmnxCohOptPortAlarmState indicates the coherent optical
         alarms currently active on the port."
    ::= { tmnxCohOptPortOperEntry 1 }

tmnxCohOptPortDefectPoints       OBJECT-TYPE
    SYNTAX      TmnxCoherentOpticalDefectPoint
    MAX-ACCESS  read-only
    STATUS      current
    DESCRIPTION
        "The value of tmnxCohOptPortDefectPoints indicates the coherent optical
         defect points currently active on the port."
    ::= { tmnxCohOptPortOperEntry 2 }

tmnxCohOptPortPresRxChan         OBJECT-TYPE
    SYNTAX      TmnxOpticalDwdmChannel
    MAX-ACCESS  read-only
    STATUS      current
    DESCRIPTION
        "The value of tmnxCohOptPortPresRxChan indicates the DWDM ITU channel
         at which the coherent optical module is operating."
    ::= { tmnxCohOptPortOperEntry 3 }

tmnxCohOptPortModState           OBJECT-TYPE
    SYNTAX      INTEGER {
                    reset         (0),
                    init          (1),
                    lowPower      (2),
                    highPowerUp   (3),
                    highPowerDown (4),
                    txOff         (5),
                    txTurnOff     (6),
                    txTurnOn      (7),
                    ready         (8),
                    fault         (9)
                }
    MAX-ACCESS  read-only
    STATUS      current
    DESCRIPTION
        "The value of tmnxCohOptPortModState indicates the state of the
         coherent optical module.

             reset          - The MDIO (Management Data Input/Output) interface
                              is held in a high impedance state and all module
                              circuits are in low-power mode.
             init           - The MDIO remains in high impedance and the module
                              registers are initialized.
             lowPower       - All high-power comsuming circuits are in their
                              low-power condition.
             highPowerUp    - The module powers up all the functional circuitry
                              and completes all required initialization of the
                              module hardware.
             highPowerDown  - The module powers down power-consuming circuitry
                              that can be switched to a low-power state.
             txOff          - The transmitter is turned off, but all other
                              parts of the module remain high powered and
                              functional.
             txTurnOff      - The module turns off the network transmitter.
             txTurnOn       - The module enables the transmitter.
             ready          - The module is in a steady-state, ready for
                              passing data.
             fault          - A module fault has occurred and as a result the
                              module is put into its low-power mode."
    ::= { tmnxCohOptPortOperEntry 4 }

tmnxCohOptPortModTxTurnUpStates  OBJECT-TYPE
    SYNTAX      BITS {
                    init              (0),
                    laserTurnUp       (1),
                    laserReadyOff     (2),
                    laserReady        (3),
                    modulatorConverge (4),
                    outputPowerAdjust (5)
                }
    MAX-ACCESS  read-only
    STATUS      current
    DESCRIPTION
        "The value of tmnxCohOptPortModTxTurnUpStates indicates the
         completed TX turn-up states of the coherent optical module.

             init               - The entry state, in which configuration of
                                  the TX path is performed.
             laserTurnUp        - This state begins the process of tuning the
                                  TX laser and locking devices on the TX path.
             laserReadyOff      - When the laser is ready for operation, but
                                  light emission is suppressed, this state is
                                  entered.
             laserReady         - This state brings the laser to full power and
                                  frequency lock.
             modulatorConverge  - This state enables the TX modulator driver
                                  and waits for convergence of the modulator
                                  automatic bias control loop.
             outputPowerAdjust  - This state sets and controls the TX output
                                  power using a VOA."
    ::= { tmnxCohOptPortOperEntry 5 }

tmnxCohOptPortModRxTurnUpStates  OBJECT-TYPE
    SYNTAX      BITS {
                    init         (0),
                    laserReady   (1),
                    waitForInput (2),
                    adcSignal    (3),
                    opticalLock  (4),
                    demodLock    (5)
                }
    MAX-ACCESS  read-only
    STATUS      current
    DESCRIPTION
        "The value of tmnxCohOptPortModRxTurnUpStates indicates the completed
         RX turn-up states of the coherent optical module.

             init          - The entry state, in which configuration of the RX
                             path is performed.
             laserReady    - The RX LO (Local Oscillator) laser is tuned.
             waitForInput  - The RX input tap is monitored for power that
                             exceeds the LOS threshold.
             adcSignal     - When RX input power above LOS is detected, the
                             module transitions to the ADC Signal
                             (Analog-to-Digital Converter Signal) state. In the
                             ADC Signal state the module calibrates the
                             optical ADCs.
             opticalLock   - This state (and state demodLock) reflects DSP
                             operations by the demodulator.
             demodLock     - In this state, RX path turn-up is achieved."
    ::= { tmnxCohOptPortOperEntry 6 }

tmnxCohOptPortRxSNRXPolar        OBJECT-TYPE
    SYNTAX      Integer32
    UNITS       "0.1 dB"
    MAX-ACCESS  read-only
    STATUS      current
    DESCRIPTION
        "The value of tmnxCohOptPortRxSNRYPolar indicates the network RX
         electrical SNR (Signal-to-Noise Ratio) of X polarization."
    ::= { tmnxCohOptPortOperEntry 7 }

tmnxCohOptPortRxSNRYPolar        OBJECT-TYPE
    SYNTAX      Integer32
    UNITS       "0.1 dB"
    MAX-ACCESS  read-only
    STATUS      current
    DESCRIPTION
        "The value of tmnxCohOptPortRxSNRYPolar indicates the network RX
         electrical SNR of Y polarization."
    ::= { tmnxCohOptPortOperEntry 8 }

tmnxCohOptPortRxQMargin          OBJECT-TYPE
    SYNTAX      Integer32
    UNITS       "0.1 dB"
    MAX-ACCESS  read-only
    STATUS      current
    DESCRIPTION
        "The value of tmnxCohOptPortRxQMargin indicates the RX Q (quality)
         Margin, represented in tenths of a dB."
    ::= { tmnxCohOptPortOperEntry 9 }

-- ----------------------------------------
-- Coherent Optical Port Stats Table
-- ----------------------------------------
tmnxCohOptPortStatsTable         OBJECT-TYPE
    SYNTAX      SEQUENCE OF TmnxCohOptPortStatsEntry
    MAX-ACCESS  not-accessible
    STATUS      current
    DESCRIPTION
        "The tmnxCohOptPortStatsTable contains statistics information for DWDM
         coherent optical ports in the Alcatel-Lucent SROS system."
    ::= { tmnxPortStatsObjs 8 }

tmnxCohOptPortStatsEntry         OBJECT-TYPE
    SYNTAX      TmnxCohOptPortStatsEntry
    MAX-ACCESS  not-accessible
    STATUS      current
    DESCRIPTION
        "Each row entry includes statistics for a DWDM coherent optical port in
         the system. Entries cannot be created or deleted via SNMP SET
         operations."
    INDEX { tmnxChassisIndex, tmnxPortPortID }
    ::= { tmnxCohOptPortStatsTable 1 }

TmnxCohOptPortStatsEntry ::=
    SEQUENCE {
        tmnxCohOptPortStatsElapsedSec    Counter32,
        tmnxCohOptPortRxBER              Gauge32,
        tmnxCohOptPortRxBERAvg           Gauge32,
        tmnxCohOptPortRxBERMin           Gauge32,
        tmnxCohOptPortRxBERMax           Gauge32,
        tmnxCohOptPortRxSNR              Gauge32,
        tmnxCohOptPortRxSNRAvg           Gauge32,
        tmnxCohOptPortRxSNRMin           Gauge32,
        tmnxCohOptPortRxSNRMax           Gauge32,
        tmnxCohOptPortRxChromaticDisp    Integer32,
        tmnxCohOptPortRxChromaticDispAvg Integer32,
        tmnxCohOptPortRxChromaticDispMin Integer32,
        tmnxCohOptPortRxChromaticDispMax Integer32,
        tmnxCohOptPortRxDiffGrpDly       Gauge32,
        tmnxCohOptPortRxDiffGrpDlyAvg    Gauge32,
        tmnxCohOptPortRxDiffGrpDlyMin    Gauge32,
        tmnxCohOptPortRxDiffGrpDlyMax    Gauge32,
        tmnxCohOptPortRxFreqOffset       Integer32,
        tmnxCohOptPortRxFreqOffsetAvg    Integer32,
        tmnxCohOptPortRxFreqOffsetMin    Integer32,
        tmnxCohOptPortRxFreqOffsetMax    Integer32,
        tmnxCohOptPortRxQ                Integer32,
        tmnxCohOptPortRxQAvg             Integer32,
        tmnxCohOptPortRxQMin             Integer32,
        tmnxCohOptPortRxQMax             Integer32,
        tmnxCohOptPortRxPower            Integer32,
        tmnxCohOptPortRxPowerAvg         Integer32,
        tmnxCohOptPortRxPowerMin         Integer32,
        tmnxCohOptPortRxPowerMax         Integer32,
        tmnxCohOptPortTxPower            Integer32,
        tmnxCohOptPortTxPowerAvg         Integer32,
        tmnxCohOptPortTxPowerMin         Integer32,
        tmnxCohOptPortTxPowerMax         Integer32
    }

tmnxCohOptPortStatsElapsedSec    OBJECT-TYPE
    SYNTAX      Counter32
    UNITS       "seconds"
    MAX-ACCESS  read-only
    STATUS      current
    DESCRIPTION
        "The value of tmnxCohOptPortStatsElapsedSec indicates the number of
         elapsed seconds since the start of coherent optical stats collection
         after the last port statistics clear."
    ::= { tmnxCohOptPortStatsEntry 1 }

tmnxCohOptPortRxBER              OBJECT-TYPE
    SYNTAX      Gauge32
    MAX-ACCESS  read-only
    STATUS      current
    DESCRIPTION
        "The value of tmnxCohOptPortRxBER indicates the RX Bit Error Rate (BER)
         since the last port statistics clear, represented as an IEEE 754
         32-bit floating point number."
    ::= { tmnxCohOptPortStatsEntry 2 }

tmnxCohOptPortRxBERAvg           OBJECT-TYPE
    SYNTAX      Gauge32
    MAX-ACCESS  read-only
    STATUS      current
    DESCRIPTION
        "The value of tmnxCohOptPortRxBERAvg indicates the RX average BER since
         the last port statistics clear, represented as an IEEE 754 32-bit
         floating point number."
    ::= { tmnxCohOptPortStatsEntry 3 }

tmnxCohOptPortRxBERMin           OBJECT-TYPE
    SYNTAX      Gauge32
    MAX-ACCESS  read-only
    STATUS      current
    DESCRIPTION
        "The value of tmnxCohOptPortRxBERMin indicates the RX minimum BER since
         the last port statistics clear, represented as an IEEE 754 32-bit
         floating point number."
    ::= { tmnxCohOptPortStatsEntry 4 }

tmnxCohOptPortRxBERMax           OBJECT-TYPE
    SYNTAX      Gauge32
    MAX-ACCESS  read-only
    STATUS      current
    DESCRIPTION
        "The value of tmnxCohOptPortRxBERMax indicates the RX maximum BER since
         the last port statistics clear, represented as an IEEE 754 32-bit
         floating point number."
    ::= { tmnxCohOptPortStatsEntry 5 }

tmnxCohOptPortRxSNR              OBJECT-TYPE
    SYNTAX      Gauge32
    UNITS       "0.1 dB"
    MAX-ACCESS  read-only
    STATUS      current
    DESCRIPTION
        "The value of tmnxCohOptPortRxSNR indicates the RX Signal-to-Noise
         Ratio (SNR) since the last port statistics clear, represented in
         tenths of a dB."
    ::= { tmnxCohOptPortStatsEntry 6 }

tmnxCohOptPortRxSNRAvg           OBJECT-TYPE
    SYNTAX      Gauge32
    UNITS       "0.1 dB"
    MAX-ACCESS  read-only
    STATUS      current
    DESCRIPTION
        "The value of tmnxCohOptPortRxSNRAvg indicates the RX average SNR since
         the last port statistics clear, represented in tenths of a dB."
    ::= { tmnxCohOptPortStatsEntry 7 }

tmnxCohOptPortRxSNRMin           OBJECT-TYPE
    SYNTAX      Gauge32
    UNITS       "0.1 dB"
    MAX-ACCESS  read-only
    STATUS      current
    DESCRIPTION
        "The value of tmnxCohOptPortRxSNRMin indicates the RX minimum SNR since
         the last port statistics clear, represented in tenths of a dB."
    ::= { tmnxCohOptPortStatsEntry 8 }

tmnxCohOptPortRxSNRMax           OBJECT-TYPE
    SYNTAX      Gauge32
    UNITS       "0.1 dB"
    MAX-ACCESS  read-only
    STATUS      current
    DESCRIPTION
        "The value of tmnxCohOptPortRxSNRMax indicates the RX maximum SNR since
         the last port statistics clear, represented in tenths of a dB."
    ::= { tmnxCohOptPortStatsEntry 9 }

tmnxCohOptPortRxChromaticDisp    OBJECT-TYPE
    SYNTAX      Integer32
    UNITS       "picoseconds per nanometer"
    MAX-ACCESS  read-only
    STATUS      current
    DESCRIPTION
        "The value of tmnxCohOptPortRxChromaticDisp indicates the RX chromatic
         dispersion since the last port statistics clear."
    ::= { tmnxCohOptPortStatsEntry 10 }

tmnxCohOptPortRxChromaticDispAvg OBJECT-TYPE
    SYNTAX      Integer32
    UNITS       "picoseconds per nanometer"
    MAX-ACCESS  read-only
    STATUS      current
    DESCRIPTION
        "The value of tmnxCohOptPortRxChromaticDispAvg indicates the RX average
         chromatic dispersion since the last port statistics clear."
    ::= { tmnxCohOptPortStatsEntry 11 }

tmnxCohOptPortRxChromaticDispMin OBJECT-TYPE
    SYNTAX      Integer32
    UNITS       "picoseconds per nanometer"
    MAX-ACCESS  read-only
    STATUS      current
    DESCRIPTION
        "The value of tmnxCohOptPortRxChromaticDispMin indicates the RX minimum
         chromatic dispersion since the last port statistics clear."
    ::= { tmnxCohOptPortStatsEntry 12 }

tmnxCohOptPortRxChromaticDispMax OBJECT-TYPE
    SYNTAX      Integer32
    UNITS       "picoseconds per nanometer"
    MAX-ACCESS  read-only
    STATUS      current
    DESCRIPTION
        "The value of tmnxCohOptPortRxChromaticDispMax indicates the RX maximum
         chromatic dispersion since the last port statistics clear."
    ::= { tmnxCohOptPortStatsEntry 13 }

tmnxCohOptPortRxDiffGrpDly       OBJECT-TYPE
    SYNTAX      Gauge32
    UNITS       "picoseconds"
    MAX-ACCESS  read-only
    STATUS      current
    DESCRIPTION
        "The value of tmnxCohOptPortRxDiffGrpDly indicates the RX differential
         group delay since the last port statistics clear."
    ::= { tmnxCohOptPortStatsEntry 14 }

tmnxCohOptPortRxDiffGrpDlyAvg    OBJECT-TYPE
    SYNTAX      Gauge32
    UNITS       "picoseconds"
    MAX-ACCESS  read-only
    STATUS      current
    DESCRIPTION
        "The value of tmnxCohOptPortRxDiffGrpDlyAvg indicates the RX average
         differential group delay since the last port statistics clear."
    ::= { tmnxCohOptPortStatsEntry 15 }

tmnxCohOptPortRxDiffGrpDlyMin    OBJECT-TYPE
    SYNTAX      Gauge32
    UNITS       "picoseconds"
    MAX-ACCESS  read-only
    STATUS      current
    DESCRIPTION
        "The value of tmnxCohOptPortRxDiffGrpDlyMin indicates the RX minimum
         differential group delay since the last port statistics clear."
    ::= { tmnxCohOptPortStatsEntry 16 }

tmnxCohOptPortRxDiffGrpDlyMax    OBJECT-TYPE
    SYNTAX      Gauge32
    UNITS       "picoseconds"
    MAX-ACCESS  read-only
    STATUS      current
    DESCRIPTION
        "The value of tmnxCohOptPortRxDiffGrpDlyMax indicates the RX maximum
         differential group delay since the last port statistics clear."
    ::= { tmnxCohOptPortStatsEntry 17 }

tmnxCohOptPortRxFreqOffset       OBJECT-TYPE
    SYNTAX      Integer32
    UNITS       "MHz"
    MAX-ACCESS  read-only
    STATUS      current
    DESCRIPTION
        "The value of tmnxCohOptPortRxFreqOffset indicates the RX frequency
         offset since the last port statistics clear."
    ::= { tmnxCohOptPortStatsEntry 18 }

tmnxCohOptPortRxFreqOffsetAvg    OBJECT-TYPE
    SYNTAX      Integer32
    UNITS       "MHz"
    MAX-ACCESS  read-only
    STATUS      current
    DESCRIPTION
        "The value of tmnxCohOptPortRxFreqOffsetAvg indicates the RX average
         frequency offset since the last port statistics clear."
    ::= { tmnxCohOptPortStatsEntry 19 }

tmnxCohOptPortRxFreqOffsetMin    OBJECT-TYPE
    SYNTAX      Integer32
    UNITS       "MHz"
    MAX-ACCESS  read-only
    STATUS      current
    DESCRIPTION
        "The value of tmnxCohOptPortRxFreqOffsetMin indicates the RX minimum
         frequency offset since the last port statistics clear."
    ::= { tmnxCohOptPortStatsEntry 20 }

tmnxCohOptPortRxFreqOffsetMax    OBJECT-TYPE
    SYNTAX      Integer32
    UNITS       "MHz"
    MAX-ACCESS  read-only
    STATUS      current
    DESCRIPTION
        "The value of tmnxCohOptPortRxFreqOffsetMax indicates the RX maximum
         frequency offset since the last port statistics clear."
    ::= { tmnxCohOptPortStatsEntry 21 }

tmnxCohOptPortRxQ                OBJECT-TYPE
    SYNTAX      Integer32
    UNITS       "0.1 dB"
    MAX-ACCESS  read-only
    STATUS      current
    DESCRIPTION
        "The value of tmnxCohOptPortRxQ indicates the RX Q since the last port
         statistics clear, represented in tenths of a dB."
    ::= { tmnxCohOptPortStatsEntry 22 }

tmnxCohOptPortRxQAvg             OBJECT-TYPE
    SYNTAX      Integer32
    UNITS       "0.1 dB"
    MAX-ACCESS  read-only
    STATUS      current
    DESCRIPTION
        "The value of tmnxCohOptPortRxQAvg indicates the RX average Q since
         the last port statistics clear, represented in tenths of a dB."
    ::= { tmnxCohOptPortStatsEntry 23 }

tmnxCohOptPortRxQMin             OBJECT-TYPE
    SYNTAX      Integer32
    UNITS       "0.1 dB"
    MAX-ACCESS  read-only
    STATUS      current
    DESCRIPTION
        "The value of tmnxCohOptPortRxQMin indicates the RX minimum Q since
         the last port statistics clear, represented in tenths of a dB."
    ::= { tmnxCohOptPortStatsEntry 24 }

tmnxCohOptPortRxQMax             OBJECT-TYPE
    SYNTAX      Integer32
    UNITS       "0.1 dB"
    MAX-ACCESS  read-only
    STATUS      current
    DESCRIPTION
        "The value of tmnxCohOptPortRxQMax indicates the RX maximum Q since
         the last port statistics clear, represented in tenths of a dB."
    ::= { tmnxCohOptPortStatsEntry 25 }

tmnxCohOptPortRxPower            OBJECT-TYPE
    SYNTAX      Integer32
    UNITS       "mBm"
    MAX-ACCESS  read-only
    STATUS      current
    DESCRIPTION
        "The value of tmnxCohOptPortRxPower indicates the RX optical power
         since the last port statistics clear."
    ::= { tmnxCohOptPortStatsEntry 26 }

tmnxCohOptPortRxPowerAvg         OBJECT-TYPE
    SYNTAX      Integer32
    UNITS       "mBm"
    MAX-ACCESS  read-only
    STATUS      current
    DESCRIPTION
        "The value of tmnxCohOptPortRxPowerAvg indicates the RX average optical
         power since the last port statistics clear."
    ::= { tmnxCohOptPortStatsEntry 27 }

tmnxCohOptPortRxPowerMin         OBJECT-TYPE
    SYNTAX      Integer32
    UNITS       "mBm"
    MAX-ACCESS  read-only
    STATUS      current
    DESCRIPTION
        "The value of tmnxCohOptPortRxPowerMin indicates the RX minimum optical
         power since the last port statistics clear."
    ::= { tmnxCohOptPortStatsEntry 28 }

tmnxCohOptPortRxPowerMax         OBJECT-TYPE
    SYNTAX      Integer32
    UNITS       "mBm"
    MAX-ACCESS  read-only
    STATUS      current
    DESCRIPTION
        "The value of tmnxCohOptPortRxPowerMax indicates the RX maximum optical
         power since the last port statistics clear."
    ::= { tmnxCohOptPortStatsEntry 29 }

tmnxCohOptPortTxPower            OBJECT-TYPE
    SYNTAX      Integer32
    UNITS       "mBm"
    MAX-ACCESS  read-only
    STATUS      current
    DESCRIPTION
        "The value of tmnxCohOptPortTxPower indicates the TX optical power
         since the last port statistics clear."
    ::= { tmnxCohOptPortStatsEntry 30 }

tmnxCohOptPortTxPowerAvg         OBJECT-TYPE
    SYNTAX      Integer32
    UNITS       "mBm"
    MAX-ACCESS  read-only
    STATUS      current
    DESCRIPTION
        "The value of tmnxCohOptPortTxPowerAvg indicates the TX average optical
         power since the last port statistics clear."
    ::= { tmnxCohOptPortStatsEntry 31 }

tmnxCohOptPortTxPowerMin         OBJECT-TYPE
    SYNTAX      Integer32
    UNITS       "mBm"
    MAX-ACCESS  read-only
    STATUS      current
    DESCRIPTION
        "The value of tmnxCohOptPortTxPowerMin indicates the TX minimum optical
         power since the last port statistics clear."
    ::= { tmnxCohOptPortStatsEntry 32 }

tmnxCohOptPortTxPowerMax         OBJECT-TYPE
    SYNTAX      Integer32
    UNITS       "mBm"
    MAX-ACCESS  read-only
    STATUS      current
    DESCRIPTION
        "The value of tmnxCohOptPortTxPowerMax indicates the TX maximum optical
         power since the last port statistics clear."
    ::= { tmnxCohOptPortStatsEntry 33 }

------------------------------------------------
-- HSMDA Port Queue-Group Queue Statistics Table
------------------------------------------------
tPortEgrHsmdaQStatTable OBJECT-TYPE
    SYNTAX         SEQUENCE OF TPortEgrHsmdaQStatEntry
    MAX-ACCESS     not-accessible
    STATUS         current
    DESCRIPTION
        "The tPortEgrHsmdaQStatTable contains egress port HSMDA queue-group 
         Queue statistics."
    ::= { tmnxPortObjs 74 }

tPortEgrHsmdaQStatEntry OBJECT-TYPE
    SYNTAX         TPortEgrHsmdaQStatEntry
    MAX-ACCESS     not-accessible
    STATUS         current
    DESCRIPTION
        "The value of tPortEgrHsmdaQStatEntry specifies egress port HSMDA  
         queue-group Queue statistics."
    INDEX { tmnxChassisIndex, tmnxPortPortID, tPortAccEgrQGrpName, 
            tPortAccEgrQGrpInstanceId, tPortEgrHsmdaQStatQueueId }
    ::= { tPortEgrHsmdaQStatTable 1 }

TPortEgrHsmdaQStatEntry ::= SEQUENCE {
        tPortEgrHsmdaQStatQueueId            TEgressHsmdaQueueId,
        tPortEgrHsmdaQStatFwdInProfPkts      Counter64,
        tPortEgrHsmdaQStatFwdInProfPktH      Counter32,
        tPortEgrHsmdaQStatFwdInProfPktL      Counter32,
        tPortEgrHsmdaQStatDpdInProfPkts      Counter64,
        tPortEgrHsmdaQStatDpdInProfPktH      Counter32,
        tPortEgrHsmdaQStatDpdInProfPktL      Counter32,
        tPortEgrHsmdaQStatFwdOutProfPkts     Counter64,
        tPortEgrHsmdaQStatFwdOutProfPktH     Counter32,
        tPortEgrHsmdaQStatFwdOutProfPktL     Counter32,
        tPortEgrHsmdaQStatDpdOutProfPkts     Counter64,
        tPortEgrHsmdaQStatDpdOutProfPktH     Counter32,
        tPortEgrHsmdaQStatDpdOutProfPktL     Counter32,
        tPortEgrHsmdaQStatFwdInProfOcts      Counter64,
        tPortEgrHsmdaQStatFwdInProfOctH      Counter32,
        tPortEgrHsmdaQStatFwdInProfOctL      Counter32,
        tPortEgrHsmdaQStatDpdInProfOcts      Counter64,
        tPortEgrHsmdaQStatDpdInProfOctH      Counter32,
        tPortEgrHsmdaQStatDpdInProfOctL      Counter32,
        tPortEgrHsmdaQStatFwdOutProfOcts     Counter64,
        tPortEgrHsmdaQStatFwdOutProfOctH     Counter32,
        tPortEgrHsmdaQStatFwdOutProfOctL     Counter32,
        tPortEgrHsmdaQStatDpdOutProfOcts     Counter64,
        tPortEgrHsmdaQStatDpdOutProfOctH     Counter32,
        tPortEgrHsmdaQStatDpdOutProfOctL     Counter32
    }

tPortEgrHsmdaQStatQueueId  OBJECT-TYPE
    SYNTAX          TEgressHsmdaQueueId
    MAX-ACCESS      not-accessible
    STATUS          current
    DESCRIPTION     
        "The value of tPortEgrHsmdaQStatQueueId specifies the HSMDA queue ID 
         for the statistics."
    ::= { tPortEgrHsmdaQStatEntry 1 }

tPortEgrHsmdaQStatFwdInProfPkts        OBJECT-TYPE
    SYNTAX      Counter64
    MAX-ACCESS  read-only
    STATUS      current
    DESCRIPTION
        "The value of tPortEgrHsmdaQStatFwdInProfPkts indicates the number of
         in-profile packets forwarded on this egress port."
    ::= { tPortEgrHsmdaQStatEntry 2 }

tPortEgrHsmdaQStatFwdInProfPktH        OBJECT-TYPE
    SYNTAX      Counter32
    MAX-ACCESS  read-only
    STATUS      current
    DESCRIPTION
        "The value of tPortEgrHsmdaQStatFwdInProfPktH indicates the upper 
         32-bits of tPortEgrHsmdaQStatFwdInProfPkts."
    ::= { tPortEgrHsmdaQStatEntry 3 }

tPortEgrHsmdaQStatFwdInProfPktL        OBJECT-TYPE
    SYNTAX      Counter32
    MAX-ACCESS  read-only
    STATUS      current
    DESCRIPTION
        "The value of tPortEgrHsmdaQStatFwdInProfPktL indicates the lower 
         32-bits of tPortEgrHsmdaQStatFwdInProfPkts."
    ::= { tPortEgrHsmdaQStatEntry 4 }

tPortEgrHsmdaQStatDpdInProfPkts        OBJECT-TYPE
    SYNTAX      Counter64
    MAX-ACCESS  read-only
    STATUS      current
    DESCRIPTION
        "The value of tPortEgrHsmdaQStatDpdInProfPkts indicates the number of
         in-profile packets dropped on this egress port."
    ::= { tPortEgrHsmdaQStatEntry 5 }

tPortEgrHsmdaQStatDpdInProfPktH        OBJECT-TYPE
    SYNTAX      Counter32
    MAX-ACCESS  read-only
    STATUS      current
    DESCRIPTION
        "The value of tPortEgrHsmdaQStatDpdInProfPktH indicates the upper 
         32-bits of tPortEgrHsmdaQStatDpdInProfPkts."
    ::= { tPortEgrHsmdaQStatEntry 6 }

tPortEgrHsmdaQStatDpdInProfPktL        OBJECT-TYPE
    SYNTAX      Counter32
    MAX-ACCESS  read-only
    STATUS      current
    DESCRIPTION
        "The value of tPortEgrHsmdaQStatDpdInProfPktL indicates the lower 
         32-bits of tPortEgrHsmdaQStatDpdInProfPkts."
    ::= { tPortEgrHsmdaQStatEntry 7 }

tPortEgrHsmdaQStatFwdOutProfPkts        OBJECT-TYPE
    SYNTAX      Counter64
    MAX-ACCESS  read-only
    STATUS      current
    DESCRIPTION
        "The value of tPortEgrHsmdaQStatFwdOutProfPkts indicates the number of
         out-of-profile packets forwarded on this egress port."
    ::= { tPortEgrHsmdaQStatEntry 8 }

tPortEgrHsmdaQStatFwdOutProfPktH        OBJECT-TYPE
    SYNTAX      Counter32
    MAX-ACCESS  read-only
    STATUS      current
    DESCRIPTION
        "The value of tPortEgrHsmdaQStatFwdOutProfPktH indicates the upper 
         32-bits of tPortEgrHsmdaQStatFwdOutProfPkts."
    ::= { tPortEgrHsmdaQStatEntry 9 }

tPortEgrHsmdaQStatFwdOutProfPktL        OBJECT-TYPE
    SYNTAX      Counter32
    MAX-ACCESS  read-only
    STATUS      current
    DESCRIPTION
        "The value of tPortEgrHsmdaQStatFwdOutProfPktL indicates the lower 
         32-bits of tPortEgrHsmdaQStatFwdOutProfPkts."
    ::= { tPortEgrHsmdaQStatEntry 10 }

tPortEgrHsmdaQStatDpdOutProfPkts        OBJECT-TYPE
    SYNTAX      Counter64
    MAX-ACCESS  read-only
    STATUS      current
    DESCRIPTION
        "The value of tPortEgrHsmdaQStatDpdOutProfPkts indicates the number of
         out-of-profile packets dropped on this egress port."
    ::= { tPortEgrHsmdaQStatEntry 11 }

tPortEgrHsmdaQStatDpdOutProfPktH        OBJECT-TYPE
    SYNTAX      Counter32
    MAX-ACCESS  read-only
    STATUS      current
    DESCRIPTION
        "The value of tPortEgrHsmdaQStatDpdOutProfPktH indicates the upper 
         32-bits of tPortEgrHsmdaQStatDpdOutProfPkts."
    ::= { tPortEgrHsmdaQStatEntry 12 }

tPortEgrHsmdaQStatDpdOutProfPktL        OBJECT-TYPE
    SYNTAX      Counter32
    MAX-ACCESS  read-only
    STATUS      current
    DESCRIPTION
        "The value of tPortEgrHsmdaQStatDpdOutProfPktL indicates the lower 
         32-bits of tPortEgrHsmdaQStatDpdOutProfPkts."
    ::= { tPortEgrHsmdaQStatEntry 13 }

tPortEgrHsmdaQStatFwdInProfOcts        OBJECT-TYPE
    SYNTAX      Counter64
    MAX-ACCESS  read-only
    STATUS      current
    DESCRIPTION
        "The value of tPortEgrHsmdaQStatFwdInProfOcts indicates the number of
         out-of-profile octects forwarded on this egress port."
    ::= { tPortEgrHsmdaQStatEntry 14 }

tPortEgrHsmdaQStatFwdInProfOctH        OBJECT-TYPE
    SYNTAX      Counter32
    MAX-ACCESS  read-only
    STATUS      current
    DESCRIPTION
        "The value of tPortEgrHsmdaQStatFwdInProfOctH indicates the upper 
         32-bits of tPortEgrHsmdaQStatFwdInProfOcts."
    ::= { tPortEgrHsmdaQStatEntry 15 }

tPortEgrHsmdaQStatFwdInProfOctL        OBJECT-TYPE
    SYNTAX      Counter32
    MAX-ACCESS  read-only
    STATUS      current
    DESCRIPTION
        "The value of tPortEgrHsmdaQStatFwdInProfOctL indicates the lower 
         32-bits of tPortEgrHsmdaQStatFwdInProfOcts."
    ::= { tPortEgrHsmdaQStatEntry 16 }

tPortEgrHsmdaQStatDpdInProfOcts        OBJECT-TYPE
    SYNTAX      Counter64
    MAX-ACCESS  read-only
    STATUS      current
    DESCRIPTION
        "The value of tPortEgrHsmdaQStatDpdInProfOcts indicates the number of
         out-of-profile octects dropped on this egress port."
    ::= { tPortEgrHsmdaQStatEntry 17 }

tPortEgrHsmdaQStatDpdInProfOctH        OBJECT-TYPE
    SYNTAX      Counter32
    MAX-ACCESS  read-only
    STATUS      current
    DESCRIPTION
        "The value of tPortEgrHsmdaQStatDpdInProfOctH indicates the upper 
         32-bits of tPortEgrHsmdaQStatDpdInProfOcts."
    ::= { tPortEgrHsmdaQStatEntry 18 }

tPortEgrHsmdaQStatDpdInProfOctL        OBJECT-TYPE
    SYNTAX      Counter32
    MAX-ACCESS  read-only
    STATUS      current
    DESCRIPTION
        "The value of tPortEgrHsmdaQStatDpdInProfOctL indicates the lower 
         32-bits of tPortEgrHsmdaQStatDpdInProfOcts."
    ::= { tPortEgrHsmdaQStatEntry 19 }

tPortEgrHsmdaQStatFwdOutProfOcts        OBJECT-TYPE
    SYNTAX      Counter64
    MAX-ACCESS  read-only
    STATUS      current
    DESCRIPTION
        "The value of tPortEgrHsmdaQStatFwdOutProfOcts indicates the number of
         out-of-profile octects forwarded on this egress port."
    ::= { tPortEgrHsmdaQStatEntry 20 }

tPortEgrHsmdaQStatFwdOutProfOctH        OBJECT-TYPE
    SYNTAX      Counter32
    MAX-ACCESS  read-only
    STATUS      current
    DESCRIPTION
        "The value of tPortEgrHsmdaQStatFwdOutProfOctH indicates the upper 
         32-bits of tPortEgrHsmdaQStatFwdOutProfOcts."
    ::= { tPortEgrHsmdaQStatEntry 21 }

tPortEgrHsmdaQStatFwdOutProfOctL        OBJECT-TYPE
    SYNTAX      Counter32
    MAX-ACCESS  read-only
    STATUS      current
    DESCRIPTION
        "The value of tPortEgrHsmdaQStatFwdOutProfOctL indicates the lower 
         32-bits of tPortEgrHsmdaQStatFwdOutProfOcts."
    ::= { tPortEgrHsmdaQStatEntry 22 }

tPortEgrHsmdaQStatDpdOutProfOcts        OBJECT-TYPE
    SYNTAX      Counter64
    MAX-ACCESS  read-only
    STATUS      current
    DESCRIPTION
        "The value of tPortEgrHsmdaQStatDpdOutProfOcts indicates the number of
         out-of-profile octects dropped on egress this egress port."
    ::= { tPortEgrHsmdaQStatEntry 23 }

tPortEgrHsmdaQStatDpdOutProfOctH        OBJECT-TYPE
    SYNTAX      Counter32
    MAX-ACCESS  read-only
    STATUS      current
    DESCRIPTION
        "The value of tPortEgrHsmdaQStatDpdOutProfOctH indicates the upper 
         32-bits of tPortEgrHsmdaQStatDpdOutProfOcts."
    ::= { tPortEgrHsmdaQStatEntry 24 }

tPortEgrHsmdaQStatDpdOutProfOctL        OBJECT-TYPE
    SYNTAX      Counter32
    MAX-ACCESS  read-only
    STATUS      current
    DESCRIPTION
        "The value of tPortEgrHsmdaQStatDpdOutProfOctL indicates the lower 
         32-bits of tPortEgrHsmdaQStatDpdOutProfOcts."
    ::= { tPortEgrHsmdaQStatEntry 25 }

--------------------------------------------------
-- HSMDA Port Queue-Group Counter Statistics Table
--------------------------------------------------
tPortEgrHsmdaCStatTable OBJECT-TYPE
    SYNTAX         SEQUENCE OF TPortEgrHsmdaCStatEntry
    MAX-ACCESS     not-accessible
    STATUS         current
    DESCRIPTION
        "The tPortEgrHsmdaCStatTable contains egress port HSMDA queue-group 
         Counter statistics."
    ::= { tmnxPortObjs 75 }

tPortEgrHsmdaCStatEntry OBJECT-TYPE
    SYNTAX         TPortEgrHsmdaCStatEntry
    MAX-ACCESS     not-accessible
    STATUS         current
    DESCRIPTION
        "The value of tPortEgrHsmdaCStatEntry specifies egress port HSMDA
         queue-group Counter statistics."
    INDEX { tmnxChassisIndex, tmnxPortPortID, tPortAccEgrQGrpName, 
            tPortAccEgrQGrpInstanceId, tPortEgrHsmdaCStatCntrId }
    ::= { tPortEgrHsmdaCStatTable 1 }

TPortEgrHsmdaCStatEntry ::= SEQUENCE {
        tPortEgrHsmdaCStatCntrId             TEgressHsmdaCounterId,
        tPortEgrHsmdaCStatFwdInProfPkts      Counter64,
        tPortEgrHsmdaCStatFwdInProfPktH      Counter32,
        tPortEgrHsmdaCStatFwdInProfPktL      Counter32,
        tPortEgrHsmdaCStatDpdInProfPkts      Counter64,
        tPortEgrHsmdaCStatDpdInProfPktH      Counter32,
        tPortEgrHsmdaCStatDpdInProfPktL      Counter32,
        tPortEgrHsmdaCStatFwdOutProfPkts     Counter64,
        tPortEgrHsmdaCStatFwdOutProfPktH     Counter32,
        tPortEgrHsmdaCStatFwdOutProfPktL     Counter32,
        tPortEgrHsmdaCStatDpdOutProfPkts     Counter64,
        tPortEgrHsmdaCStatDpdOutProfPktH     Counter32,
        tPortEgrHsmdaCStatDpdOutProfPktL     Counter32,
        tPortEgrHsmdaCStatFwdInProfOcts      Counter64,
        tPortEgrHsmdaCStatFwdInProfOctH      Counter32,
        tPortEgrHsmdaCStatFwdInProfOctL      Counter32,
        tPortEgrHsmdaCStatDpdInProfOcts      Counter64,
        tPortEgrHsmdaCStatDpdInProfOctH      Counter32,
        tPortEgrHsmdaCStatDpdInProfOctL      Counter32,
        tPortEgrHsmdaCStatFwdOutProfOcts     Counter64,
        tPortEgrHsmdaCStatFwdOutProfOctH     Counter32,
        tPortEgrHsmdaCStatFwdOutProfOctL     Counter32,
        tPortEgrHsmdaCStatDpdOutProfOcts     Counter64,
        tPortEgrHsmdaCStatDpdOutProfOctH     Counter32,
        tPortEgrHsmdaCStatDpdOutProfOctL     Counter32
    }

tPortEgrHsmdaCStatCntrId  OBJECT-TYPE
    SYNTAX          TEgressHsmdaCounterId
    MAX-ACCESS      not-accessible
    STATUS          current
    DESCRIPTION     
        "The value of tPortEgrHsmdaCStatCntrId specifies the HSMDA counter ID 
         for the statistics."
    ::= { tPortEgrHsmdaCStatEntry 1 }

tPortEgrHsmdaCStatFwdInProfPkts        OBJECT-TYPE
    SYNTAX      Counter64
    MAX-ACCESS  read-only
    STATUS      current
    DESCRIPTION
        "The value of tPortEgrHsmdaCStatFwdInProfPkts indicates the number of
         in-profile packets forwarded for the egress counter, specified by the
         index tPortEgrHsmdaCStatCntrId, on this port."
    ::= { tPortEgrHsmdaCStatEntry 2 }

tPortEgrHsmdaCStatFwdInProfPktH        OBJECT-TYPE
    SYNTAX      Counter32
    MAX-ACCESS  read-only
    STATUS      current
    DESCRIPTION
        "The value of tPortEgrHsmdaCStatFwdInProfPktH indicates the upper 
         32-bits of tPortEgrHsmdaCStatFwdInProfPkts."
    ::= { tPortEgrHsmdaCStatEntry 3 }

tPortEgrHsmdaCStatFwdInProfPktL        OBJECT-TYPE
    SYNTAX      Counter32
    MAX-ACCESS  read-only
    STATUS      current
    DESCRIPTION
        "The value of tPortEgrHsmdaCStatFwdInProfPktL indicates the lower 
         32-bits of tPortEgrHsmdaCStatFwdInProfPkts."
    ::= { tPortEgrHsmdaCStatEntry 4 }

tPortEgrHsmdaCStatDpdInProfPkts        OBJECT-TYPE
    SYNTAX      Counter64
    MAX-ACCESS  read-only
    STATUS      current
    DESCRIPTION
        "The value of tPortEgrHsmdaCStatDpdInProfPkts indicates the number of
         in-profile packets dropped for the egress counter, specified by the
         index tPortEgrHsmdaCStatCntrId, on this port."
    ::= { tPortEgrHsmdaCStatEntry 5 }

tPortEgrHsmdaCStatDpdInProfPktH        OBJECT-TYPE
    SYNTAX      Counter32
    MAX-ACCESS  read-only
    STATUS      current
    DESCRIPTION
        "The value of tPortEgrHsmdaCStatDpdInProfPktH indicates the upper 
         32-bits of tPortEgrHsmdaCStatDpdInProfPkts."
    ::= { tPortEgrHsmdaCStatEntry 6 }

tPortEgrHsmdaCStatDpdInProfPktL        OBJECT-TYPE
    SYNTAX      Counter32
    MAX-ACCESS  read-only
    STATUS      current
    DESCRIPTION
        "The value of tPortEgrHsmdaCStatDpdInProfPktL indicates the lower 
         32-bits of tPortEgrHsmdaCStatDpdInProfPkts."
    ::= { tPortEgrHsmdaCStatEntry 7 }

tPortEgrHsmdaCStatFwdOutProfPkts        OBJECT-TYPE
    SYNTAX      Counter64
    MAX-ACCESS  read-only
    STATUS      current
    DESCRIPTION
        "The value of tPortEgrHsmdaCStatFwdOutProfPkts indicates the number of
         out-of-profile packets forwarded for the egress counter, specified by 
         the index tPortEgrHsmdaCStatCntrId, on this port."
    ::= { tPortEgrHsmdaCStatEntry 8 }

tPortEgrHsmdaCStatFwdOutProfPktH        OBJECT-TYPE
    SYNTAX      Counter32
    MAX-ACCESS  read-only
    STATUS      current
    DESCRIPTION
        "The value of tPortEgrHsmdaCStatFwdOutProfPktH indicates the upper 
         32-bits of tPortEgrHsmdaCStatFwdOutProfPkts."
    ::= { tPortEgrHsmdaCStatEntry 9 }

tPortEgrHsmdaCStatFwdOutProfPktL        OBJECT-TYPE
    SYNTAX      Counter32
    MAX-ACCESS  read-only
    STATUS      current
    DESCRIPTION
        "The value of tPortEgrHsmdaCStatFwdOutProfPktL indicates the lower 
         32-bits of tPortEgrHsmdaCStatFwdOutProfPkts."
    ::= { tPortEgrHsmdaCStatEntry 10 }

tPortEgrHsmdaCStatDpdOutProfPkts        OBJECT-TYPE
    SYNTAX      Counter64
    MAX-ACCESS  read-only
    STATUS      current
    DESCRIPTION
        "The value of tPortEgrHsmdaCStatDpdOutProfPkts indicates the number of
         out-of-profile packets dropped or the egress counter, specified by the
         index tPortEgrHsmdaCStatCntrId, on this port."
    ::= { tPortEgrHsmdaCStatEntry 11 }

tPortEgrHsmdaCStatDpdOutProfPktH        OBJECT-TYPE
    SYNTAX      Counter32
    MAX-ACCESS  read-only
    STATUS      current
    DESCRIPTION
        "The value of tPortEgrHsmdaCStatDpdOutProfPktH indicates the upper 
         32-bits of tPortEgrHsmdaCStatDpdOutProfPkts."
    ::= { tPortEgrHsmdaCStatEntry 12 }

tPortEgrHsmdaCStatDpdOutProfPktL        OBJECT-TYPE
    SYNTAX      Counter32
    MAX-ACCESS  read-only
    STATUS      current
    DESCRIPTION
        "The value of tPortEgrHsmdaCStatDpdOutProfPktL indicates the lower 
         32-bits of tPortEgrHsmdaCStatDpdOutProfPkts."
    ::= { tPortEgrHsmdaCStatEntry 13 }

tPortEgrHsmdaCStatFwdInProfOcts        OBJECT-TYPE
    SYNTAX      Counter64
    MAX-ACCESS  read-only
    STATUS      current
    DESCRIPTION
        "The value of tPortEgrHsmdaCStatFwdInProfOcts indicates the number of
         out-of-profile octects forwarded for the egress counter, specified by 
         the index tPortEgrHsmdaCStatCntrId, on this port."
    ::= { tPortEgrHsmdaCStatEntry 14 }

tPortEgrHsmdaCStatFwdInProfOctH        OBJECT-TYPE
    SYNTAX      Counter32
    MAX-ACCESS  read-only
    STATUS      current
    DESCRIPTION
        "The value of tPortEgrHsmdaCStatFwdInProfOctH indicates the upper 
         32-bits of tPortEgrHsmdaCStatFwdInProfOcts."
    ::= { tPortEgrHsmdaCStatEntry 15 }

tPortEgrHsmdaCStatFwdInProfOctL        OBJECT-TYPE
    SYNTAX      Counter32
    MAX-ACCESS  read-only
    STATUS      current
    DESCRIPTION
        "The value of tPortEgrHsmdaCStatFwdInProfOctL indicates the lower 
         32-bits of tPortEgrHsmdaCStatFwdInProfOcts."
    ::= { tPortEgrHsmdaCStatEntry 16 }

tPortEgrHsmdaCStatDpdInProfOcts        OBJECT-TYPE
    SYNTAX      Counter64
    MAX-ACCESS  read-only
    STATUS      current
    DESCRIPTION
        "The value of tPortEgrHsmdaCStatDpdInProfOcts indicates the number of
         out-of-profile octects dropped for the egress counter, specified by the
         index tPortEgrHsmdaCStatCntrId, on this port."
    ::= { tPortEgrHsmdaCStatEntry 17 }

tPortEgrHsmdaCStatDpdInProfOctH        OBJECT-TYPE
    SYNTAX      Counter32
    MAX-ACCESS  read-only
    STATUS      current
    DESCRIPTION
        "The value of tPortEgrHsmdaCStatDpdInProfOctH indicates the upper 
         32-bits of tPortEgrHsmdaCStatDpdInProfOcts."
    ::= { tPortEgrHsmdaCStatEntry 18 }

tPortEgrHsmdaCStatDpdInProfOctL        OBJECT-TYPE
    SYNTAX      Counter32
    MAX-ACCESS  read-only
    STATUS      current
    DESCRIPTION
        "The value of tPortEgrHsmdaCStatDpdInProfOctL indicates the lower 
         32-bits of tPortEgrHsmdaCStatDpdInProfOcts."
    ::= { tPortEgrHsmdaCStatEntry 19 }

tPortEgrHsmdaCStatFwdOutProfOcts        OBJECT-TYPE
    SYNTAX      Counter64
    MAX-ACCESS  read-only
    STATUS      current
    DESCRIPTION
        "The value of tPortEgrHsmdaCStatFwdOutProfOcts indicates the number of
         out-of-profile octects forwarded for the egress counter, specified by 
         the index tPortEgrHsmdaCStatCntrId, on this port."
    ::= { tPortEgrHsmdaCStatEntry 20 }

tPortEgrHsmdaCStatFwdOutProfOctH        OBJECT-TYPE
    SYNTAX      Counter32
    MAX-ACCESS  read-only
    STATUS      current
    DESCRIPTION
        "The value of tPortEgrHsmdaCStatFwdOutProfOctH indicates the upper 
         32-bits of tPortEgrHsmdaCStatFwdOutProfOcts."
    ::= { tPortEgrHsmdaCStatEntry 21 }

tPortEgrHsmdaCStatFwdOutProfOctL        OBJECT-TYPE
    SYNTAX      Counter32
    MAX-ACCESS  read-only
    STATUS      current
    DESCRIPTION
        "The value of tPortEgrHsmdaCStatFwdOutProfOctL indicates the lower 
         32-bits of tPortEgrHsmdaCStatFwdOutProfOcts."
    ::= { tPortEgrHsmdaCStatEntry 22 }

tPortEgrHsmdaCStatDpdOutProfOcts        OBJECT-TYPE
    SYNTAX      Counter64
    MAX-ACCESS  read-only
    STATUS      current
    DESCRIPTION
        "The value of tPortEgrHsmdaCStatDpdOutProfOcts indicates the number of
         out-of-profile octects dropped for the egress counter, specified by the
         index tPortEgrHsmdaCStatCntrId, on this port."
    ::= { tPortEgrHsmdaCStatEntry 23 }

tPortEgrHsmdaCStatDpdOutProfOctH        OBJECT-TYPE
    SYNTAX      Counter32
    MAX-ACCESS  read-only
    STATUS      current
    DESCRIPTION
        "The value of tPortEgrHsmdaCStatDpdOutProfOctH indicates the upper 
         32-bits of tPortEgrHsmdaCStatDpdOutProfOcts."
    ::= { tPortEgrHsmdaCStatEntry 24 }

tPortEgrHsmdaCStatDpdOutProfOctL        OBJECT-TYPE
    SYNTAX      Counter32
    MAX-ACCESS  read-only
    STATUS      current
    DESCRIPTION
        "The value of tPortEgrHsmdaCStatDpdOutProfOctL indicates the lower 
         32-bits of tPortEgrHsmdaCStatDpdOutProfOcts."
    ::= { tPortEgrHsmdaCStatEntry 25 }


--
--  Port Egress Vport Scheduler statistics table
--
tPortEgrVPortSchedStatTblLastCh      OBJECT-TYPE
    SYNTAX       TimeStamp
    MAX-ACCESS   read-only
    STATUS       current
    DESCRIPTION
        "The value of the object tPortEgrVPortSchedStatTblLastCh indicates the 
         timestamp of the last change to the tPortEgrVPortSchedStatTable."
    ::= { tmnxPortObjs 79 }

tPortEgrVPortSchedStatTable       OBJECT-TYPE
    SYNTAX      SEQUENCE OF TPortEgrVPortSchedStatEntry
    MAX-ACCESS  not-accessible
    STATUS      current
    DESCRIPTION
        "The tPortEgrVPortSchedStatTable contains statistics information
         about the egress port schedulers at a vport."
    ::= { tmnxPortObjs 80 }

tPortEgrVPortSchedStatEntry       OBJECT-TYPE
    SYNTAX      TPortEgrVPortSchedStatEntry
    MAX-ACCESS  not-accessible
    STATUS      current
    DESCRIPTION
        "Each conceptual row contains detailed statistics information
        about an egress port scheduler at a vport.

        Entries in this table are created and removed automatically by the 
        system."
    INDEX { tmnxChassisIndex,
            tmnxPortPortID,
            tPortEgrVPortName,
            tPortEgrVPSchedStatName
     }
    ::= { tPortEgrVPortSchedStatTable 1 }

TPortEgrVPortSchedStatEntry ::= SEQUENCE
    {
        tPortEgrVPSchedStatName          TNamedItem,
        tPortEgrVPSchedStatFwdPkts       Counter64,
        tPortEgrVPSchedStatFwdOcts       Counter64
    }

tPortEgrVPSchedStatName        OBJECT-TYPE
    SYNTAX      TNamedItem
    MAX-ACCESS  not-accessible
    STATUS      current
    DESCRIPTION
        "The value of tPortEgrVPSchedStatName specifies the name
         of the port scheduler."
    ::= { tPortEgrVPortSchedStatEntry 1 }

tPortEgrVPSchedStatFwdPkts   OBJECT-TYPE
    SYNTAX      Counter64
    MAX-ACCESS  read-only
    STATUS      current
    DESCRIPTION
        "The value of tPortEgrVPSchedStatFwdPkts indicates the number of 
         forwarded packets."
    ::= { tPortEgrVPortSchedStatEntry 2 }
    
tPortEgrVPSchedStatFwdOcts  OBJECT-TYPE
    SYNTAX      Counter64
    MAX-ACCESS  read-only
    STATUS      current
    DESCRIPTION
        "The value of tPortEgrVPSchedStatFwdOcts indicates the number of 
         forwarded octets."
    ::= { tPortEgrVPortSchedStatEntry 3 }  

tmnxPortEtherSymMonTblLastChange OBJECT-TYPE
    SYNTAX      TimeStamp
    MAX-ACCESS  read-only
    STATUS      current
    DESCRIPTION
        "The value of tmnxPortEtherSymMonTblLastChange indicates the time, since
         system startup that a configuration changed state in the
         tmnxPortEtherSymbolMonitorTable."
    ::= { tmnxPortObjs 81 }

tmnxPortEtherSymbolMonitorTable  OBJECT-TYPE
    SYNTAX      SEQUENCE OF TmnxPortEtherSymbolMonitorEntry
    MAX-ACCESS  not-accessible
    STATUS      current
    DESCRIPTION
        "The tmnxPortEtherSymbolMonitorTable maintains the configuration and
         state of Symbol Error Signal Degrade over a sliding window for the
         Ethernet Port."
    ::= { tmnxPortObjs 82 }

tmnxPortEtherSymbolMonitorEntry  OBJECT-TYPE
    SYNTAX      TmnxPortEtherSymbolMonitorEntry
    MAX-ACCESS  not-accessible
    STATUS      current
    DESCRIPTION
        "The tmnxPortEtherSymbolMonitorEntry consists of the information related
         to an individual Ethernet Port Symbol Error Signal Degrade state."
    AUGMENTS { tmnxPortEtherEntry }
    ::= { tmnxPortEtherSymbolMonitorTable 1 }

TmnxPortEtherSymbolMonitorEntry  ::= SEQUENCE {
    tmnxPortEtherSymMonEnabled       TmnxEnabledDisabled,
    tmnxPortEtherSymMonSdThreshold   Unsigned32,
    tmnxPortEtherSymMonSdTMultiplier Unsigned32,
    tmnxPortEtherSymMonSfThreshold   Unsigned32,
    tmnxPortEtherSymMonSfTMultiplier Unsigned32,
    tmnxPortEtherSymMonWindowSize    Unsigned32,
    tmnxPortEtherSymMonAlarmReason   TmnxPortEtherMonReportStatus,
    tmnxPortEtherSymMonErrorCount    Counter64
}

tmnxPortEtherSymMonEnabled       OBJECT-TYPE
    SYNTAX      TmnxEnabledDisabled
    MAX-ACCESS  read-write
    STATUS      current
    DESCRIPTION
        "The value of tmnxPortEtherSymMonEnabled specifies whether or not Symbol
         Monitoring is enabled on the port."
    DEFVAL { disabled }
    ::= { tmnxPortEtherSymbolMonitorEntry 1 }

tmnxPortEtherSymMonSdThreshold   OBJECT-TYPE
    SYNTAX      Unsigned32 (0..9)
    MAX-ACCESS  read-write
    STATUS      current
    DESCRIPTION
        "The value of tmnxPortEtherSymMonSdThreshold specifies a packet error
         rate threshold used to determine when to send a
         tmnxEqPortEtherSymMonAlarm notification for a Symbol Monitor Signal
         Degradation (SD) failure and tmnxEqPortEtherSymMonAlarmClear
         notification for a Symbol Monitor SD failure clear.

         tmnxPortEtherSymMonSdThreshold is the absolute value of the exponent
         of the rate expressed as 10e-n.

         The Symbol Monitor SD error rate threshold is calculated as:
         tmnxPortEtherSymMonSdTMultiplier * 10e-tmnxPortEtherSymMonSdThreshold.

         A value of 0 disables CRC SD monitioring."
    DEFVAL { 0 }
    ::= { tmnxPortEtherSymbolMonitorEntry 2 }

tmnxPortEtherSymMonSdTMultiplier OBJECT-TYPE
    SYNTAX      Unsigned32 (1..9)
    MAX-ACCESS  read-write
    STATUS      current
    DESCRIPTION
        "The value of tmnxPortEtherSymMonSdTMultiplier specifies the
         tmnxPortEtherSymMonSdThreshold multiplier value.

         The Symbol Monitor SD error rate threshold is calculated as:
         tmnxPortEtherSymMonSdTMultiplier * 10e-tmnxPortEtherSymMonSdThreshold."
    DEFVAL { 1 }
    ::= { tmnxPortEtherSymbolMonitorEntry 3 }

tmnxPortEtherSymMonSfThreshold   OBJECT-TYPE
    SYNTAX      Unsigned32 (0..9)
    MAX-ACCESS  read-write
    STATUS      current
    DESCRIPTION
        "The value of tmnxPortEtherSymMonSfThreshold specifies a packet error
         rate threshold used to determine when to send a
         tmnxEqPortEtherSymMonAlarm notification for a Symbol Monitor Signal
         Failure (SF) failure.

         Crossing the tmnxPortEtherSymMonSfThreshold will result in the
         tmnxPortOperStatus being set to 'outOfService'.

         tmnxPortEtherSymMonSfThreshold is the absolute value of the exponent
         of the rate expressed as 10e-n.

         The Symbol Monitor SF error rate threshold is calculated as:
         tmnxPortEtherSymMonSfTMultiplier * 10e-tmnxPortEtherSymMonSfThreshold.

         A value of 0 disables Symbol Monitor SF monitoring."
    DEFVAL { 0 }
    ::= { tmnxPortEtherSymbolMonitorEntry 4 }

tmnxPortEtherSymMonSfTMultiplier OBJECT-TYPE
    SYNTAX      Unsigned32 (1..9)
    MAX-ACCESS  read-write
    STATUS      current
    DESCRIPTION
        "The value of tmnxPortEtherSymMonSfTMultiplier specifies the
         tmnxPortEtherSymMonSfThreshold multiplier value.

         The Symbol Monitor SF error rate threshold is calculated as:
         tmnxPortEtherSymMonSfTMultiplier * 10e-tmnxPortEtherSymMonSfThreshold."
    DEFVAL { 1 }
    ::= { tmnxPortEtherSymbolMonitorEntry 5 }

tmnxPortEtherSymMonWindowSize       OBJECT-TYPE
    SYNTAX      Unsigned32 (5..60)
    UNITS       "seconds"
    MAX-ACCESS  read-write
    STATUS      current
    DESCRIPTION
        "The value of tmnxPortEtherSymMonWindowSize specifies the size of the
         sliding window in seconds over which the
         tmnxPortEtherSymMonSdThreshold and tmnxPortEtherSymMonSfThreshold
         are applied."
    DEFVAL { 10 }
    ::= { tmnxPortEtherSymbolMonitorEntry 6 }

tmnxPortEtherSymMonAlarmReason   OBJECT-TYPE
    SYNTAX      TmnxPortEtherMonReportStatus
    MAX-ACCESS  read-only
    STATUS      current
    DESCRIPTION
        "The value of tmnxPortEtherSymMonAlarmReason indicates the current
         status of the Ethernet Symbol Monitored alarms on the port."
    ::= { tmnxPortEtherSymbolMonitorEntry 7 }

tmnxPortEtherSymMonErrorCount   OBJECT-TYPE
    SYNTAX      Counter64
    MAX-ACCESS  read-only
    STATUS      current
    DESCRIPTION
        "The value of tmnxPortEtherSymMonErrorCount indicates the total number
         of Symbol Monitor errors since tmnxPortEtherSymMonEnabled was set to 
         'enabled (1)'."
    ::= { tmnxPortEtherSymbolMonitorEntry 8 }

--
--  Port Notification Objects
--
 tmnxPortNotifyPortId  OBJECT-TYPE
    SYNTAX      TmnxPortID
    MAX-ACCESS  accessible-for-notify
    STATUS      current
    DESCRIPTION
        "Used by tmnx port Notifications, the OID indicates the
         port or sonet path associated with the alarm."
    ::= { tmnxPortNotificationObjects 1 }

 tmnxPortNotifySonetAlarmReason  OBJECT-TYPE
    SYNTAX      INTEGER {
                    notUsed (0),
                    loc(1),
                    lais(2),
                    lrdi(3),
                    ss1f(4),
                    sb1err(5),
                    lb2erSd(6),
                    lb2erSf(7),
                    slof(8),
                    slos(9),
                    stxptr(10),
                    srxptr(11),
                    lrei(12)
                }
    MAX-ACCESS   accessible-for-notify
    STATUS       current
    DESCRIPTION
        "Used by tmnx sonet Port Notifications, the value of
         tmnxPortNotifySonetAlarmReason indicates the reason a sonet port
         alarm has been raised."
    ::= { tmnxPortNotificationObjects 2 }

 tmnxPortNotifySonetPathAlarmReason  OBJECT-TYPE
    SYNTAX      INTEGER {
                    notUsed (0),
                    pais(1),
                    plop(2),
                    prdi(3),
                    pb3err(4),
                    pplm(5),
                    prei(6),
                    puneq(7),
                    plcd(8)
                }
    MAX-ACCESS  accessible-for-notify
    STATUS      current
    DESCRIPTION
        "Used by tmnx sonet path Notifications, the value of
         tmnxPortNotifySonetPathAlarmReason indicates the reason a sonet path
         alarm has been raised."
    ::= { tmnxPortNotificationObjects 3 }

tmnxPortNotifyError  OBJECT-TYPE
    SYNTAX      INTEGER {
                    txClockError (1),
                    rxClockError(2),
                    txFifoError(3),
                    laserError(4),
                    miscError(5)
                }
    MAX-ACCESS  accessible-for-notify
    STATUS      current
    DESCRIPTION
        "Used by tmnxEqPortError notification, the value of
         tmnxPortNotifyError indicates the reason a port has
         an error."
    ::= { tmnxPortNotificationObjects 4 }

 tmnxPortNotifyDS3AlarmReason  OBJECT-TYPE
    SYNTAX      INTEGER {
                    notUsed (0),
                    ais (1),
                    los (2),
                    oof (3),
                    rai (4),
                    looped (5)
                }
    MAX-ACCESS   accessible-for-notify
    STATUS       current
    DESCRIPTION
        "Used by tmnx DS3 Port Notifications, the value of
         tmnxPortNotifyDS3AlarmReason indicates the reason a DS3 interface
         alarm has been raised."
    ::= { tmnxPortNotificationObjects 5 }

 tmnxPortNotifyDS1AlarmReason  OBJECT-TYPE
    SYNTAX      INTEGER {
                    notUsed (0),
                    ais (1),
                    los (2),
                    oof (3),
                    rai (4),
                    looped (5),
                    berSd (6),
                    berSf (7)
                }
    MAX-ACCESS   accessible-for-notify
    STATUS       current
    DESCRIPTION
        "Used by tmnx DS1 Port Notifications, the value of
         tmnxPortNotifyDS1AlarmReason indicates the reason a DS1 interface
         alarm has been raised."
    ::= { tmnxPortNotificationObjects 6 }

 tmnxPortNotifyBundleId  OBJECT-TYPE
    SYNTAX      TmnxBundleID
    MAX-ACCESS  accessible-for-notify
    STATUS      current
    DESCRIPTION
        "Used by tmnx bundle Notifications, the value indicates the
         bundle associated with the alarm."
    ::= { tmnxPortNotificationObjects 7 }

 tmnxPortNotifyEtherAlarmReason  OBJECT-TYPE
    SYNTAX       TmnxPortEtherReportValue
    MAX-ACCESS   accessible-for-notify
    STATUS       current
    DESCRIPTION
        "Used by tmnx ethernet Port Notifications, the value of
         tmnxPortNotifyEtherAlarmReason indicates the reason a ethernet port
         alarm has been raised."
    ::= { tmnxPortNotificationObjects 8 }

 tmnxDDMFailedObject OBJECT-TYPE
    SYNTAX      INTEGER {
                    unknown                      (0),
                    temperature-low-warning      (1),
                    temperature-low-alarm        (2),
                    temperature-high-warning     (3),
                    temperature-high-alarm       (4),
                    supplyVoltage-low-warning    (5),
                    supplyVoltage-low-alarm      (6),
                    supplyVoltage-high-warning   (7),
                    supplyVoltage-high-alarm     (8),
                    txBiasCurrent-low-warning    (9),
                    txBiasCurrent-low-alarm     (10),
                    txBiasCurrent-high-warning  (11),
                    txBiasCurrent-high-alarm    (12),
                    txOutputPower-low-warning   (13),
                    txOutputPower-low-alarm     (14),
                    txOutputPower-high-warning  (15),
                    txOutputPower-high-alarm    (16),
                    rxOpticalPower-low-warning  (17),
                    rxOpticalPower-low-alarm    (18),
                    rxOpticalPower-high-warning (19),
                    rxOpticalPower-high-alarm   (20),
                    aux1-low-warning            (21),
                    aux1-low-alarm              (22),
                    aux1-high-warning           (23),
                    aux1-high-alarm             (24),
                    aux2-low-warning            (25),
                    aux2-low-alarm              (26),
                    aux2-high-warning           (27),
                    aux2-high-alarm             (28)
                }
    MAX-ACCESS   accessible-for-notify
    STATUS       current
    DESCRIPTION
        "Used by Digital Diagnostic Monitoring (DDM) Notifications, the
         value of tmnxDDMFailedObject indicates which object of the
         monitored SFF is in a failed or cleared threshold state."
    ::= { tmnxPortNotificationObjects 9 }

 tmnxDSXClockSyncStateObject  OBJECT-TYPE
    SYNTAX       TmnxDSXClockSyncState
    MAX-ACCESS   accessible-for-notify
    STATUS       current
    DESCRIPTION
        "Used by tmnxDSXClockSyncStateChange.  The value of
         tmnxDSXClockSyncStateObject indicates the clock sync state
         of a DS3 or DS1 channel with clock source adaptive or
         differential."
    ::= { tmnxPortNotificationObjects 10 }

 tmnxPortNotifyDescription  OBJECT-TYPE
    SYNTAX       DisplayString
    MAX-ACCESS   accessible-for-notify
    STATUS       current
    DESCRIPTION
        "The object tmnxPortNotifyDescription is a printable character
         string."
    ::= { tmnxPortNotificationObjects 11 }

 tmnxPortNotifyWTAlarmReason  OBJECT-TYPE
    SYNTAX      INTEGER {
                    notUsed (0),
                    encFail (1),
                    encDegr (2),
                    pwrFail (3),
                    pwrDegr (4),
                    pwrHigh (5),
                    pwrLow  (6),
                    missing (7)
                }
    MAX-ACCESS   accessible-for-notify
    STATUS       current
    DESCRIPTION
        "Used by Wavelength Tracker Port Notifications, the value of
         tmnxPortNotifyWTAlarmReason indicates the reason a Wavelength
         Tracker port alarm has been raised. The values correspond to the
         TmnxWaveTrackerAlarm bits."
    ::= { tmnxPortNotificationObjects 12 }

tmnxHostMatchNotifyIntDestId OBJECT-TYPE
    SYNTAX       TmnxSubMgtIntDestId
    MAX-ACCESS   accessible-for-notify
    STATUS       current
    DESCRIPTION
        "Used by tPortAccEgrQGrpHostMatchFailure and
         tPortEgrVPortHostMatchFailure. The value of
         tmnxHostMatchNotifyIntDestId indicates the intermediate destination
         id of the host which was used to lookup the port egress queue-group
         or virtual port."
    ::= { tmnxPortNotificationObjects 13 }

tmnxHostMatchNotifyOrgString OBJECT-TYPE
    SYNTAX       TmnxSubMgtOrgStrOrZero
    MAX-ACCESS   accessible-for-notify
    STATUS       current
    DESCRIPTION
        "Used by tPortAccEgrQGrpHostMatchFailure and
         tPortEgrVPortHostMatchFailure. The value of 
         tmnxHostMatchNotifyOrgString indicates the organization string of
         the host which was used to lookup the port egress queue-group or
         virtual port."
    ::= { tmnxPortNotificationObjects 14 }

tmnxHostMatchNotifySubIdent OBJECT-TYPE
    SYNTAX       TmnxSubIdentStringOrEmpty
    MAX-ACCESS   accessible-for-notify
    STATUS       current
    DESCRIPTION
        "Used by tPortAccEgrQGrpHostMatchFailure and
         tPortEgrVPortHostMatchFailure. The value of 
         tmnxHostMatchNotifySubIdent indicates the subscriber identification
         string of the host which was used to lookup the port egress
         queue-group or virtual port."
    ::= { tmnxPortNotificationObjects 15 }

tmnxObjAppResvSize OBJECT-TYPE
    SYNTAX       Unsigned32
    UNITS        "kilo-bytes"
    MAX-ACCESS   accessible-for-notify
    STATUS       current
    DESCRIPTION
        "The value of tmnxObjAppResvSize indicates operational value of reserved
        size of the associated object (MDA or port).

        This is used by tmnxResvCbsPoolThreshGreen, tmnxResvCbsPoolThreshAmber
        and tmnxResvCbsPoolThreshRed notifications."
    ::= { tmnxPortNotificationObjects 16 }

tmnxObjAppResvCbsOld OBJECT-TYPE
    SYNTAX       Unsigned32
    UNITS        "percent"
    MAX-ACCESS   accessible-for-notify
    STATUS       current
    DESCRIPTION
        "The value of tmnxObjAppResvCbsOld indicates old value of reserved
         CBS of the associated object (MDA or port). When tmnxObjAppResvCbsOld 
         is set to '4294967295', tmnxObjAppResvCbsOld indicates invalid reserved
         size value.

         This is used by tmnxResvCbsPoolThreshGreen, tmnxResvCbsPoolThreshAmber
         and tmnxResvCbsPoolThreshRed notifications."
    ::= { tmnxPortNotificationObjects 17 }

tmnxObjAppResvCbsNew OBJECT-TYPE
    SYNTAX       Unsigned32
    UNITS        "percent"
    MAX-ACCESS   accessible-for-notify
    STATUS       current
    DESCRIPTION
        "The value of tmnxObjAppResvCbsNew indicates new value of reserved
        CBS of the associated object (MDA or port).

        This is used by tmnxResvCbsPoolThreshGreen, tmnxResvCbsPoolThreshAmber
        and tmnxResvCbsPoolThreshRed notifications."
    ::= { tmnxPortNotificationObjects 18 }

tmnxObjAppSumOfQResvSize OBJECT-TYPE
    SYNTAX       Unsigned32
    UNITS        "kilo-bytes"
    MAX-ACCESS   accessible-for-notify
    STATUS       current
    DESCRIPTION
        "The value of tmnxObjAppSumOfQResvSize indicates sum of the reserved
        CBS queue size of reserved CBS of the associated object (MDA or port).
         
        This is used by tmnxResvCbsPoolThreshGreen, tmnxResvCbsPoolThreshAmber
        and tmnxResvCbsPoolThreshRed notifications."
    ::= { tmnxPortNotificationObjects 19 }

tmnxObjType OBJECT-TYPE
    SYNTAX      INTEGER {
                    mda (1),
                    port (2),
                    unused (3),
                    bundle (4)
                }
    MAX-ACCESS  accessible-for-notify
    STATUS      current
    DESCRIPTION
        "The object tmnxObjType defines the type of object for which this
        notification is sent."
    ::= { tmnxPortNotificationObjects 20 }

tmnxObjPortId OBJECT-TYPE
    SYNTAX      TmnxPortID
    MAX-ACCESS  accessible-for-notify
    STATUS      current
    DESCRIPTION
        "The object tmnxObjPortId is used to identify the specific Port object."
    ::= { tmnxPortNotificationObjects 21 }

tmnxObjMdaId OBJECT-TYPE
    SYNTAX      TmnxPortID
    MAX-ACCESS  accessible-for-notify
    STATUS      current
    DESCRIPTION
        "The tmnxObjMdaId is used to identify the specific MDA object.
        If tmnxObjType is 'mda', then the tmnxObjMdaId is encoded as a
        physical port with the port being '0'."
    ::= { tmnxPortNotificationObjects 22 }

tmnxObjAppType OBJECT-TYPE
    SYNTAX      INTEGER {
                    accessIngress (1),
                    accessEgress (2),
                    networkIngress (3),
                    networkEgress (4),
                    ingress (5),
                    egress (6)
                }
    MAX-ACCESS  accessible-for-notify
    STATUS      current
    DESCRIPTION
        "The object tmnxObjAppType specifies the nature of usage the pool
        tmnxObjAppPool is used for. The pools could be used for access or
        network traffic at either ingress or egress.

        The value of 'ingress' and 'egress' is used with objects using
        named-pool policy."
    ::= { tmnxPortNotificationObjects 23 }

tmnxObjAppPool OBJECT-TYPE
    SYNTAX      TNamedItemOrEmpty
    MAX-ACCESS  accessible-for-notify
    STATUS      current
    DESCRIPTION
        "The object tmnxObjAppPool specifies the name of the pool being used."
    ::= { tmnxPortNotificationObjects 24 }

tmnxObjNamedPoolPolicy OBJECT-TYPE
    SYNTAX      TNamedItemOrEmpty
    MAX-ACCESS  accessible-for-notify
    STATUS      current
    DESCRIPTION
        "The value of tmnxObjNamedPoolPolicy indicates the name of 
        the tmnxPortIngNamedPoolPlcy or tmnxPortEgrNamedPoolPlcy object
        to which this notification belongs."
    ::= { tmnxPortNotificationObjects 25 }

tmnxPortNotifyEtherCrcThreshold  OBJECT-TYPE
    SYNTAX      Unsigned32
    MAX-ACCESS  accessible-for-notify
    STATUS      current
    DESCRIPTION
        "The value of tmnxPortNotifyEtherCrcThreshold indicates the threshold
         value used in a Ethernet Port CRC Monitoring alarm."
    ::= { tmnxPortNotificationObjects 27 }

tmnxPortNotifyEtherCrcMultiplier OBJECT-TYPE
    SYNTAX      Unsigned32
    MAX-ACCESS  accessible-for-notify
    STATUS      current
    DESCRIPTION
        "The value of tmnxPortNotifyEtherCrcMultiplier indicates the threshold
         multiplier value used in a Ethernet Port CRC Monitoring alarm."
    ::= { tmnxPortNotificationObjects 28 }

tmnxPortNotifyEtherCrcAlarmValue OBJECT-TYPE
    SYNTAX      TmnxPortEtherMonReportValue
    MAX-ACCESS  accessible-for-notify
    STATUS      current
    DESCRIPTION
        "The value of tmnxPortNotifyEtherCrcAlarmValue indicates the enumerated
         alarm raised or cleared in a Ethernet Port CRC Monitoring alarm."
    ::= { tmnxPortNotificationObjects 29 }

tmnxObjAppResvSizeOld OBJECT-TYPE
    SYNTAX       Unsigned32
    UNITS        "kilo-bytes"
    MAX-ACCESS   accessible-for-notify
    STATUS       current
    DESCRIPTION
        "The value of tmnxObjAppResvSizeOld indicates old value of reserved
        size of the associated object (MDA or port). When tmnxObjAppResvSizeOld 
        is set to '4294967295', tmnxObjAppResvSizeOld indicates invalid reserved
        size value.

        This is used by tmnxResvCbsPoolThreshGreen, tmnxResvCbsPoolThreshAmber
        and tmnxResvCbsPoolThreshRed notifications."
    ::= { tmnxPortNotificationObjects 30 }

tmnxDDMLaneIdOrModule            OBJECT-TYPE
    SYNTAX      Unsigned32 (0|1..16)
    MAX-ACCESS  accessible-for-notify
    STATUS      current
    DESCRIPTION
        "The value of tmnxDDMLaneIdOrModule indicates which component of the
        Digital Diagnostic Monitoring (DDM) SFF device caused the notification
        to be raised. A value of zero (0) indicates the SFF module failed,
        otherwise the SFF Lane ID is specified. For SFF modules that do not
        support Lanes, this object will always be set to the value zero (0)."
    ::= { tmnxPortNotificationObjects 31 }

tmnxPortNotifyEtherSymThreshold  OBJECT-TYPE
    SYNTAX      Unsigned32
    MAX-ACCESS  accessible-for-notify
    STATUS      current
    DESCRIPTION
        "The value of tmnxPortNotifyEtherSymThreshold indicates the threshold
         value used in a Ethernet Port Symbol Monitoring alarm."
    ::= { tmnxPortNotificationObjects 32 }

tmnxPortNotifyEtherSymMultiplier OBJECT-TYPE
    SYNTAX      Unsigned32
    MAX-ACCESS  accessible-for-notify
    STATUS      current
    DESCRIPTION
        "The value of tmnxPortNotifyEtherSymMultiplier indicates the threshold
         multiplier value used in a Ethernet Port Symbol Monitoring alarm."
    ::= { tmnxPortNotificationObjects 33 }

tmnxPortNotifyEtherSymAlarmValue OBJECT-TYPE
    SYNTAX      TmnxPortEtherMonReportValue
    MAX-ACCESS  accessible-for-notify
    STATUS      current
    DESCRIPTION
        "The value of tmnxPortNotifyEtherSymAlarmValue indicates the enumerated
         alarm raised or cleared in a Ethernet Port Symbol Monitoring alarm."
    ::= { tmnxPortNotificationObjects 34 }

--
--  TIMETRA-PORT-MIB Notifications
--

--
--  Equipment Alarms
--
 tmnxEqOobPortFailure   NOTIFICATION-TYPE
    OBJECTS {
        tmnxChassisNotifyChassisId,
        tmnxPortNotifyPortId
    }
    STATUS  obsolete
    DESCRIPTION
        "Generated when the out-of-band Ethernet port has failed.  On the
         Alcatel-Lucent SROS system, the out-of-band port is the CPM management
         interface.

         This notification was made obsolete in the 2.1 release.

         The Out-of-band, OOB, port is what id refered to as the
         management port or cpm port.  It has an entry in ifTable
         and linkup, linkDown and tmnxEqPortError notifications
         are sent for the management port just as for any other
         port in the system."
    ::= { tmnxPortNotification 1 }

 tmnxEqPortFailure  NOTIFICATION-TYPE
    OBJECTS {
        tmnxChassisNotifyChassisId,
        tmnxPortNotifyPortId
    }
    STATUS  obsolete
    DESCRIPTION
        "Generated when a port has failed.

         This notification was made obsolete in the 2.1 release.

         tmnxEqPortError is used instead of tmnxEqPortFailure.

         Standard IETF linkDown notification is sent when a
         physical port failure is detected.  tmnxEqPortError is
         sent with a ASCII reason message when port errors are
         detected.

         It was originally intended that tmnxEqPortError be used
         to report errors that do not cause port state change to
         'down'.

         tmnxEqPortFailure was intended to report errors that
         do cause the port state change to 'down'.

         However, in the implementation tmnxEqPortError is used
         for both fatal and non-fatal errors."
    ::= { tmnxPortNotification 2 }

 tmnxEqPortSonetAlarm     NOTIFICATION-TYPE
    OBJECTS {
        tmnxPortNotifyPortId,
        tmnxPortNotifySonetAlarmReason
    }
    STATUS  current
    DESCRIPTION
        "Generated when a SONET/SDH port alarm condition is detected.
         It is generated only when the type of alarm being raised is enabled
         in tmnxSonetReportAlarm."
    ::= { tmnxPortNotification 4 }

 tmnxEqPortSonetAlarmClear        NOTIFICATION-TYPE
    OBJECTS {
        tmnxPortNotifyPortId,
        tmnxPortNotifySonetAlarmReason
    }
    STATUS  current
    DESCRIPTION
        "Generated when a SONET/SDH port alarm condition is cleared.
         It is generated only when the type of alarm being cleared is enabled
         in tmnxSonetReportAlarm."
    ::= { tmnxPortNotification 5 }

 tmnxEqPortSonetPathAlarm   NOTIFICATION-TYPE
    OBJECTS {
        tmnxPortNotifyPortId,
        tmnxPortNotifySonetPathAlarmReason
    }
    STATUS  current
    DESCRIPTION
        "Generated when a SONET/SDH path alarm condition is detected.
         It is generated only when the type of alarm being raised is enabled
         in tmnxSonetPathReportAlarm."
    ::= { tmnxPortNotification 6 }

 tmnxEqPortSonetPathAlarmClear      NOTIFICATION-TYPE
    OBJECTS {
        tmnxPortNotifyPortId,
        tmnxPortNotifySonetPathAlarmReason
    }
    STATUS  current
    DESCRIPTION
        "Generated when a SONET/SDH path alarm condition is cleared.
         It is generated only when the type of alarm being cleared is enabled
         in tmnxSonetPathReportAlarm."
    ::= { tmnxPortNotification 7 }

 tmnxEqPortSFPInserted NOTIFICATION-TYPE
    OBJECTS {
        tmnxPortNotifyPortId
    }
    STATUS  current
    DESCRIPTION
        "Generated when an SFF is inserted in the port."
    ::= { tmnxPortNotification 8 }

 tmnxEqPortSFPRemoved NOTIFICATION-TYPE
    OBJECTS {
        tmnxPortNotifyPortId
    }
    STATUS  current
    DESCRIPTION
        "Generated when an SFF is removed from the port."
    ::= { tmnxPortNotification 9 }

 tmnxEqPortWrongSFP NOTIFICATION-TYPE
    OBJECTS {
        tmnxPortNotifyPortId
    }
    STATUS  obsolete
    DESCRIPTION
        "Generated when a wrong type of SFF optics module
         is plugged into a 1 Gig MDA, SONET MDA, or 100FX MDA.

         Because of the large variety of SFFs now supported and
         their different encoding schemes for compliance bits, the
         check for wrong SFF has been removed. As a result,
         tmnxEqPortWrongSFP notification is no longer generated.

         However, wrong SFF can be inferred from port statistics."
    ::= { tmnxPortNotification 10 }

tmnxEqPortSFPCorrupted  NOTIFICATION-TYPE
    OBJECTS {
        tmnxPortNotifyPortId
    }
    STATUS  obsolete
    DESCRIPTION
        "Generated when SFF information stored in the EPROM
         on the SFF is corrupt. This notification was made
         obsolete for revision 6.0 on Alcatel-Lucent SROS series
         systems; it was replaced by tmnxEqPortSFPStatusFailure."
    ::= { tmnxPortNotification 11 }

 tmnxPortNotifyBerSdTca NOTIFICATION-TYPE
    OBJECTS {
        tmnxPortNotifyPortId,
        tmnxSonetBerSdThreshold
    }
    STATUS  obsolete
    DESCRIPTION
        "Generated when a SONET/SDH port's signal degradation bit error
         rate is greater than the configured error rate threshold.

         This notification was made obsolete in the 2.1 release."
        ::= { tmnxPortNotification 12 }

 tmnxPortNotifyBerSfTca NOTIFICATION-TYPE
    OBJECTS {
        tmnxPortNotifyPortId,
        tmnxSonetBerSfThreshold
    }
    STATUS  obsolete
    DESCRIPTION
        "Generated when a SONET/SDH port's signal failure bit error
         rate is greater than the configured error rate threshold.

         This notification was made obsolete in the 2.1 release."
    ::= { tmnxPortNotification 13 }

tmnxEqPortError NOTIFICATION-TYPE
    OBJECTS {
        tmnxPortNotifyPortId,
        tmnxPortNotifyError
    }
    STATUS  current
    DESCRIPTION
        "Generated when an error listed in tmnxPortNotifyError
         is detected on the port."
    ::= { tmnxPortNotification 14 }

 tmnxEqPortDS3Alarm   NOTIFICATION-TYPE
    OBJECTS {
        tmnxPortNotifyPortId,
        tmnxPortNotifyDS3AlarmReason
    }
    STATUS  current
    DESCRIPTION
        "Generated when a DS3 interface alarm condition is detected.
         It is generated only when the type of alarm being raised is enabled
         in tmnxDS3ChannelReportAlarm."
    ::= { tmnxPortNotification 15 }

 tmnxEqPortDS3AlarmClear      NOTIFICATION-TYPE
    OBJECTS {
        tmnxPortNotifyPortId,
        tmnxPortNotifyDS3AlarmReason
    }
    STATUS  current
    DESCRIPTION
        "Generated when a DS3 interface alarm condition is cleared.
         It is generated only when the type of alarm being cleared is enabled
         in tmnxDS3ChannelReportAlarm."
    ::= { tmnxPortNotification 16 }

 tmnxEqPortDS1Alarm   NOTIFICATION-TYPE
    OBJECTS {
        tmnxPortNotifyPortId,
        tmnxPortNotifyDS1AlarmReason
    }
    STATUS  current
    DESCRIPTION
        "Generated when a DS1 interface alarm condition is detected.
         It is generated only when the type of alarm being raised is enabled
         in tmnxDS1ReportAlarm."
    ::= { tmnxPortNotification 17 }

 tmnxEqPortDS1AlarmClear      NOTIFICATION-TYPE
    OBJECTS {
        tmnxPortNotifyPortId,
        tmnxPortNotifyDS1AlarmReason
    }
    STATUS  current
    DESCRIPTION
        "Generated when a DS1 interface alarm condition is cleared.
         It is generated only when the type of alarm being cleared is enabled
         in tmnxDS1ReportAlarm."
    ::= { tmnxPortNotification 18 }

 tmnxEqPortBndlYellowDiffExceeded   NOTIFICATION-TYPE
    OBJECTS {
        tmnxPortNotifyPortId,
        tmnxBundleYellowDiffDelay
    }
    STATUS  current
    DESCRIPTION
        "Generated when the differential delay of a port in the bundle
         exceeds the configured value in tmnxBundleYellowDiffDelay."
    ::= { tmnxPortNotification 19 }

 tmnxEqPortBndlRedDiffExceeded   NOTIFICATION-TYPE
    OBJECTS {
        tmnxPortNotifyPortId,
        tmnxBundleRedDiffDelay
    }
    STATUS  current
    DESCRIPTION
        "Generated when the differential delay of a port in the bundle
         exceeds the configured value in tmnxBundleRedDiffDelay."
    ::= { tmnxPortNotification 20 }

 tmnxEqPortBndlBadEndPtDiscr  NOTIFICATION-TYPE
    OBJECTS {
        tmnxBundleMemberDownReason
    }
    STATUS  current
    DESCRIPTION
        "Generated when the port detected mismatched peer endpoint
         discriminator for the bundle."
    ::= { tmnxPortNotification 21 }

 tmnxEqPortEtherAlarm     NOTIFICATION-TYPE
    OBJECTS {
        tmnxPortNotifyPortId,
        tmnxPortNotifyEtherAlarmReason
    }
    STATUS  current
    DESCRIPTION
        "tmnxEqPortEtherAlarm is generated when a ethernet port alarm
         condition is detected. It is generated only when the type of
         alarm being raised is enabled in tmnxPortEtherReportAlarm."
    ::= { tmnxPortNotification 22 }

 tmnxEqPortEtherAlarmClear        NOTIFICATION-TYPE
    OBJECTS {
        tmnxPortNotifyPortId,
        tmnxPortNotifyEtherAlarmReason
    }
    STATUS  current
    DESCRIPTION
        "tmnxEqPortEtherAlarmClear is generated when a ethernet port alarm
         condition is cleared. It is generated only when the type of alarm
         being cleared is enabled in tmnxPortEtherReportAlarm."
    ::= { tmnxPortNotification 23 }

 tmnxDS1E1LoopbackStarted        NOTIFICATION-TYPE
    OBJECTS {
        tmnxPortNotifyPortId,
        tmnxDS1Loopback
    }
    STATUS          current
    DESCRIPTION
        "The tmnxDS1E1LoopbackStarted notification is generated when a
         loopback is provisioned on a DS1/E1 port."
    ::= { tmnxPortNotification 24 }

 tmnxDS1E1LoopbackStopped NOTIFICATION-TYPE
    OBJECTS {
        tmnxPortNotifyPortId,
        tmnxDS1Loopback
    }
    STATUS          current
    DESCRIPTION
        "The tmnxDS1E1LoopbackStopped notification is generated when a
         loopback is removed on a DS1/E1 port. The value of
         tmnxSonetLoopback specifies the type of loopback that was
         configured and has now been removed."
    ::= { tmnxPortNotification 25 }

 tmnxDS3E3LoopbackStarted NOTIFICATION-TYPE
    OBJECTS {
        tmnxPortNotifyPortId,
        tmnxDS3ChannelLoopback
    }
    STATUS          current
    DESCRIPTION
        "The tmnxDS3E3LoopbackStarted notification is generated when a
         loopback is provisioned on a DS3/E3 port."
    ::= { tmnxPortNotification 26 }

 tmnxDS3E3LoopbackStopped NOTIFICATION-TYPE
    OBJECTS {
        tmnxPortNotifyPortId,
        tmnxDS3ChannelLoopback
    }
    STATUS          current
    DESCRIPTION
        "The tmnxDS3E3LoopbackStopped notification is generated when a
         loopback is removed on a DS3/E3 port. The value of
         tmnxDS3ChannelLoopback specifies the type of loopback that was
         configured and has now been removed."
    ::= { tmnxPortNotification 27 }

 tmnxSonetSDHLoopbackStarted NOTIFICATION-TYPE
    OBJECTS {
        tmnxPortNotifyPortId,
        tmnxSonetLoopback
    }
    STATUS          current
    DESCRIPTION
        "The tmnxSonetSDHLoopbackStarted notification is generated when a
         loopback is provisioned on a Sonet-SDH port."
    ::= { tmnxPortNotification 28 }

 tmnxSonetSDHLoopbackStopped NOTIFICATION-TYPE
    OBJECTS {
        tmnxPortNotifyPortId,
        tmnxSonetLoopback
    }
    STATUS          current
    DESCRIPTION
        "The tmnxSonetSDHLoopbackStopped notification is generated when a
         loopback test is removed on a Sonet-SDH port. The value of
         tmnxDS1Loopback specifies the type of loopback that was
         configured and has now been removed."
    ::= { tmnxPortNotification 29 }

--
--  Down-when-looped Alarm
--
 tmnxEqPortEtherLoopDetected  NOTIFICATION-TYPE
    OBJECTS {
        tmnxPortNotifyPortId
    }
    STATUS  current
    DESCRIPTION
        "The tmnxEqPortEtherLoopDetected notification is genereated when
         down-when-looped detects an Ethernet port is receiving PDUs that
         it transmitted and tmnxPortEtherDownWhenLoopedEnabled is set to
         'true'."
    ::= { tmnxPortNotification 30 }

 tmnxEqPortEtherLoopCleared  NOTIFICATION-TYPE
    OBJECTS {
        tmnxPortNotifyPortId
    }
    STATUS  current
    DESCRIPTION
        "The tmnxEqPortEtherLoopCleared notification is generated when
         down-when-looped detects an Ethernet port has stopped receiving
         PDUs that it transmitted and tmnxPortEtherDownWhenLoopedEnabled
         is set to 'true'.  Setting tmnxPortEtherDownWhenLoopedEnabled to
         'false' will also cause this notification to be generated if
         tmnxEqPortEtherLoopDetected had previously been raised."
    ::= { tmnxPortNotification 31 }

 tmnxEqPortSpeedCfgNotCompatible  NOTIFICATION-TYPE
    OBJECTS {
        tmnxPortNotifyPortId,
        tmnxPortEtherSpeed,
        tmnxMdaNotifyType
    }
    STATUS  current
    DESCRIPTION
        "Generated when a configured speed on an MDA port is not
         compatible with the MDA type.

         [EFFECT] Though services can still be created, if the tmnxMdaNotifyType
         is the same as the tmnxMDAEquippedType then the MDA will fail to
         operate as configured and will be in a failed state.

         [RECOVERY] Change the configuration to reflect the capabilities of the
         MDA port, or switch out/re-provision the MDA for one that is
         compatible."
    ::= { tmnxPortNotification 32 }

 tmnxEqPortDuplexCfgNotCompatible  NOTIFICATION-TYPE
    OBJECTS {
        tmnxPortNotifyPortId,
        tmnxPortEtherDuplex,
        tmnxMdaNotifyType
    }
    STATUS  current
    DESCRIPTION
        "Generated when a configured duplex on an MDA port is not
         compatible with the MDA type.

         [EFFECT] Though services can still be created, if the tmnxMdaNotifyType
         is the same as the tmnxMDAEquippedType then the MDA will fail to
         operate as configured and will be in a failed state.

         [RECOVERY] Change the configuration to reflect the capabilities of the
         MDA port, or switch out/re-provision the MDA for one that is
         compatible."
    ::= { tmnxPortNotification 33 }

 tmnxEqPortIngressRateCfgNotCompatible  NOTIFICATION-TYPE
    OBJECTS {
        tmnxPortNotifyPortId,
        tmnxMdaNotifyType
    }
    STATUS  current
    DESCRIPTION
        "Generated when a configured ingress rate on an MDA port is not
         compatible with the MDA type.

         [EFFECT] Though services can still be created, if the tmnxMdaNotifyType
         is the same as the tmnxMDAEquippedType then the MDA will fail to
         operate as configured and will be in a failed state.

         [RECOVERY] Change the configuration to reflect the capabilities of the
         MDA port, or switch out/re-provision the MDA for one that is
         compatible."
    ::= { tmnxPortNotification 34 }

tmnxEqDigitalDiagMonitorFailure NOTIFICATION-TYPE
    OBJECTS {
        tmnxPortNotifyPortId,
        tmnxDDMFailedObject,
        tmnxDDMLaneIdOrModule
    }
    STATUS  current
    DESCRIPTION
        "Generated when an SFF that supports Digital Diagnostic
         Monitoring (DDM) enters a failed state."
    ::= { tmnxPortNotification 35 }

tmnxEqPortSFPStatusFailure NOTIFICATION-TYPE
    OBJECTS {
        tmnxPortNotifyPortId,
        tmnxPortSFPStatus
    }
    STATUS  current
    DESCRIPTION
        "[CAUSE] The tmnxEqPortSFPStatusFailure notification is generated
         when the tmnxPortSFPStatus of an SFF results in a value other than
         'not-equipped (0)', or 'operational (1)'. tmnxEqPortSFPStatusFailure
         obsoleted tmnxEqPortSFPCorrupted for revision 6.0 on Alcatel-Lucent
         SROS series systems.

         [EFFECT] The SFF device is not operational and the associated port
         can not be used. The SFF and port will not recover without operator
         intervention.

         [RECOVERY] Remove and re-insert the SFF device. If the problem
         persists then replace the SFF device."
    ::= { tmnxPortNotification 36 }

tmnxDSXClockSyncStateChange NOTIFICATION-TYPE
    OBJECTS {
        tmnxPortNotifyPortId,
        tmnxDSXClockSyncStateObject
    }
    STATUS  current
    DESCRIPTION
        "Generated when the tmnxDS3ChannelClockSyncState changes for a DS3 or
         DS1 channel with adaptive or differentical clock source."
    ::= { tmnxPortNotification 37 }

--
--  Quality of Service Alarm
--
tmnxQosServiceDegraded     NOTIFICATION-TYPE
    OBJECTS {
        tmnxChassisNotifyChassisId,
        tmnxPortNotifyPortId
    }
    STATUS  obsolete
    DESCRIPTION
        "Generated when the port is unable to provided the specified
         quality of service level."
    ::= { tmnxPortNotification 3 }

--
--  Functional Alarm
--

tmnxPortUnsupportedFunction NOTIFICATION-TYPE
    OBJECTS {
        tmnxPortNotifyPortId,
        tmnxPortNotifyDescription
    }
    STATUS  current
    DESCRIPTION
        "Generated when a functionality is required from this port that it
         cannot support.

         The object tmnxPortNotifyDescription explains what function is
         affected."
    ::= { tmnxPortNotification 38 }

tmnxBundleMemberMlfrLoopback     NOTIFICATION-TYPE
    OBJECTS {
        tmnxBundleMemberMlfrDownReason
    }
    STATUS  current
    DESCRIPTION
        "Generated when a Multilink Frame-Relay Bundle Member enters or leaves
         the 'loopback (3)' state."
    ::= { tmnxPortNotification 39 }

tmnxEqPortWaveTrackerAlarm              NOTIFICATION-TYPE
    OBJECTS {
        tmnxPortNotifyWTAlarmReason,
        tmnxWaveTrackerAlarmState
    }
    STATUS  current
    DESCRIPTION
        "The tmnxEqPortWaveTrackerAlarm notification indicates that a
         Wave Tracker interface has experienced either a raising or clearing
         of an alarm as indicated by the value of tmnxPortNotifyWTAlarmReason."
    ::= { tmnxPortNotification 40 }

tPortAccEgrQGrpHostMatchFailure         NOTIFICATION-TYPE
    OBJECTS {
        tmnxPortNotifyPortId,
        tmnxHostMatchNotifyIntDestId,
        tmnxHostMatchNotifyOrgString,
        tmnxHostMatchNotifySubIdent
    }
    STATUS  current
    DESCRIPTION
        "The tPortAccEgrQGrpHostMatchFailure notification indicates that a
         host match lookup failed to resolve a specific port egress 
         queue-group. In such case the default policer-output-queue is used."
    ::= { tmnxPortNotification 41 }

tPortEgrVPortHostMatchFailure NOTIFICATION-TYPE
    OBJECTS {
        tmnxPortNotifyPortId,
        tmnxHostMatchNotifyIntDestId,
        tmnxHostMatchNotifyOrgString,
        tmnxHostMatchNotifySubIdent
    }
    STATUS  current
    DESCRIPTION
            "The tPortEgrVPortHostMatchFailure notification indicates that a
             host match lookup failed to resolve a specific port egress 
             virtual port."
    ::= { tmnxPortNotification 42 }

tmnxEqDigitalDiagMonitorClear   NOTIFICATION-TYPE
    OBJECTS {
        tmnxPortNotifyPortId,
        tmnxDDMFailedObject,
        tmnxDDMLaneIdOrModule
    }
    STATUS  current
    DESCRIPTION
        "Generated when an SFF that supports Digital Diagnostic
         Monitoring (DDM) clears a failed state."
    ::= { tmnxPortNotification 43 }

tmnxEqPortOpticalAmpAlarm               NOTIFICATION-TYPE
    OBJECTS {
        tmnxOpticalPortAmpAlarmState
    }
    STATUS  current
    DESCRIPTION
        "The tmnxEqPortOpticalAmpAlarm notification indicates that an
         Optical Amplifier interface has experienced either a raising
         or clearing of an alarm as indicated by the value of
         tmnxOpticalPortAmpAlarmState."
    ::= { tmnxPortNotification 44 }

tmnxEqPortOpticalTdcmAlarm              NOTIFICATION-TYPE
    OBJECTS {
        tmnxOpticalPortTdcmAlarmState
    }
    STATUS  current
    DESCRIPTION
        "The tmnxEqPortOpticalTdcmAlarm notification indicates that an
         Optical Tdcm interface has experienced either a raising
         or clearing of an alarm as indicated by the value of
         tmnxOpticalPortTdcmAlarmState."
    ::= { tmnxPortNotification 45 }

tmnxEqSonetClockSrcNotCompatible  NOTIFICATION-TYPE
    OBJECTS {
        tmnxSonetClockSource,
        tmnxMdaNotifyType
    }
    STATUS  current
    DESCRIPTION
        "Notification tmnxEqSonetClockSrcNotCompatible is generated when a
         configured SONET/SDH clock source on an MDA port is not compatible
         with the MDA type.

         [EFFECT] Though services can still be created, if the tmnxMdaNotifyType
         is the same as the tmnxMDAEquippedType then the MDA will fail to
         operate as configured and will be in a failed state.

         [RECOVERY] Change the configuration to reflect the capabilities of the
         MDA port, or switch out/re-provision the MDA for one that is
         compatible."
    ::= { tmnxPortNotification 46 }

tmnxEqSonetSfThreshNotCompatible  NOTIFICATION-TYPE
    OBJECTS {
        tmnxSonetBerSfThreshold,
        tmnxMdaNotifyType
    }
    STATUS  current
    DESCRIPTION
        "Notification tmnxEqSonetSfThreshNotCompatible is generated when a
         configured SONET/SDH Signal Fail (SF) threshold on an MDA port is not
         compatible with the MDA type.

         [EFFECT] Though services can still be created, if the tmnxMdaNotifyType
         is the same as the tmnxMDAEquippedType then the MDA will fail to
         operate as configured and will be in a failed state.

         [RECOVERY] Change the configuration to reflect the capabilities of the
         MDA port, or switch out/re-provision the MDA for one that is
         compatible."
    ::= { tmnxPortNotification 47 }

tmnxEqSonetFramingNotCompatible  NOTIFICATION-TYPE
    OBJECTS {
        tmnxSonetFraming,
        tmnxMdaNotifyType
    }
    STATUS  current
    DESCRIPTION
        "Notification tmnxEqSonetFramingNotCompatible is generated when a
         configured SONET/SDH framing on an MDA port is not compatible with
         the MDA type.

         [EFFECT] Though services can still be created, if the tmnxMdaNotifyType
         is the same as the tmnxMDAEquippedType then the MDA will fail to
         operate as configured and will be in a failed state.

         [RECOVERY] Change the configuration to reflect the capabilities of the
         MDA port, or switch out/re-provision the MDA for one that is
         compatible."
    ::= { tmnxPortNotification 48 }

tmnxResvCbsPoolThreshGreen  NOTIFICATION-TYPE
    OBJECTS {
        tmnxObjType,
        tmnxObjPortId,
        tmnxObjMdaId,
        tmnxObjAppType,
        tmnxObjAppPool,
        tmnxObjNamedPoolPolicy,
        tmnxObjAppResvSize,
        tmnxObjAppSumOfQResvSize,
        tmnxObjAppResvCbsOld,
        tmnxObjAppResvCbsNew,
        tmnxObjAppResvSizeOld
    }
    STATUS  current
    DESCRIPTION
        "The notification tmnxResvCbsPoolThreshGreen is generated when a
         reserved-CBS of an object (MDA or port) returns to within defined
         thresholds.

         [EFFECT] Reserved CBS of the object has returned to within normal
         parameters.

         [RECOVERY] None required."
    ::= { tmnxPortNotification 49 }

tmnxResvCbsPoolThreshAmber  NOTIFICATION-TYPE
    OBJECTS {
        tmnxObjType,
        tmnxObjPortId,
        tmnxObjMdaId,
        tmnxObjAppType,
        tmnxObjAppPool,
        tmnxObjNamedPoolPolicy,
        tmnxObjAppResvSize,
        tmnxObjAppSumOfQResvSize,
        tmnxObjAppResvCbsOld,
        tmnxObjAppResvCbsNew,
        tmnxObjAppResvSizeOld
    }
    STATUS  current
    DESCRIPTION
        "The notification tmnxResvCbsPoolThreshAmber is generated when a
         reserved-CBS of an object (MDA or port) has crossed threshold value
         specified by tmnxObjectAppAmbrAlrmThresh or tQ1NamedPoolAmbrAlrmThresh.

         [EFFECT] This is warning event but the traffic is not yet affected.

         [RECOVERY] The value of tmnxObjectAppResvCbs
         or TIMETRA-QOS-MIB::tQ1NamedPoolReservedCbs may need to be adjusted."
    ::= { tmnxPortNotification 50 }

tmnxResvCbsPoolThreshRed  NOTIFICATION-TYPE
    OBJECTS {
        tmnxObjType,
        tmnxObjPortId,
        tmnxObjMdaId,
        tmnxObjAppType,
        tmnxObjAppPool,
        tmnxObjNamedPoolPolicy,
        tmnxObjAppResvSize,
        tmnxObjAppSumOfQResvSize,
        tmnxObjAppResvCbsOld,
        tmnxObjAppResvCbsNew,
        tmnxObjAppResvSizeOld
    }
    STATUS  current
    DESCRIPTION
        "The notification tmnxResvCbsPoolThreshAmber is generated when a
         reserved-CBS of an object (MDA or port) has crossed threshold value
         specified by tmnxObjectAppRedAlrmThresh or tQ1NamedPoolRedAlrmThresh.

         [EFFECT] This is a critical event and the traffic may be affected.

         [RECOVERY] The value of tmnxObjectAppResvCbs
         or TIMETRA-QOS-MIB::tQ1NamedPoolReservedCbs may need to be adjusted."
    ::= { tmnxPortNotification 51 }

tmnxEqPortEtherCrcAlarm          NOTIFICATION-TYPE
    OBJECTS {
        tmnxPortNotifyPortId,
        tmnxPortNotifyEtherCrcThreshold,
        tmnxPortNotifyEtherCrcMultiplier,
        tmnxPortNotifyEtherCrcAlarmValue
    }
    STATUS      current
    DESCRIPTION
        "tmnxEqPortEtherCrcAlarm is generated when an Ethernet port CRC alarm
         condition is detected. It is generated only when the type of alarm
         being raised is enabled on the port.

         [EFFECT] On a signal failure (SF) fault, the port is taken out of
         service until the CRC alarm condition is cleared.

         [RECOVERY] tmnxEqPortEtherCrcAlarm is cleared by taking the port out of
         service (eg. shutdown, card/mda reset, physical link loss), or
         changing/disabling the associated threshold/multiplier values.

         Signal Degradation is self clearing and will clear once the error rate
         drops below 1/10th of the configured rate."
    ::= { tmnxPortNotification 52 }

tmnxEqPortEtherCrcAlarmClear     NOTIFICATION-TYPE
    OBJECTS {
        tmnxPortNotifyPortId,
        tmnxPortNotifyEtherCrcThreshold,
        tmnxPortNotifyEtherCrcMultiplier,
        tmnxPortNotifyEtherCrcAlarmValue
    }
    STATUS      current
    DESCRIPTION
        "tmnxEqPortEtherCrcAlarmClear is generated when an Ethernet port CRC
         alarm condition is cleared or disabled."
    ::= { tmnxPortNotification 53 }

tmnxEqPortEtherInternalAlarm     NOTIFICATION-TYPE
    OBJECTS {
        tmnxPortNotifyPortId
    }
    STATUS      current
    DESCRIPTION
        "tmnxEqPortEtherInternalAlarm is generated when an Ethernet port
         experiences excessive internal MAC tx errors.  It is generated only
         when tmnxPortEtherDownOnInternalError is enabled on the port.

         [EFFECT] A port experiencing excessive internal MAC tx errors will
         take the port out of service while the alarm condition is in affect.

         [RECOVERY] tmnxEqPortEtherInternalAlarm is cleared by taking the port
         out of service (eg. shutdown, card/mda reset, physical link loss), or
         setting tmnxPortEtherDownOnInternalError to the value 'false'."
    ::= { tmnxPortNotification 54 }

tmnxEqPortEtherInternalAlarmClr  NOTIFICATION-TYPE
    OBJECTS {
        tmnxPortNotifyPortId
    }
    STATUS      current
    DESCRIPTION
        "tmnxEqPortEtherInternalAlarmClr is generated when an Ethernet port no
         longer experiences excessive internal MAC tx errors."
    ::= { tmnxPortNotification 55 }

tmnxEqCohOptPortAlarm            NOTIFICATION-TYPE
    OBJECTS {
        tmnxCohOptPortAlarmState,
        tmnxCohOptPortDefectPoints
    }
    STATUS  current
    DESCRIPTION
        "The tmnxEqCohOptPortAlarm notification indicates that a coherent
         optical port has experienced either a raising or a clearing of an
         alarm as indicated by the value of tmnxCohOptPortAlarmState. Further
         details can be obtained from the value of tmnxCohOptPortDefectPoints."
    ::= { tmnxPortNotification 56 }

tmnxEqPortEtherSymMonAlarm       NOTIFICATION-TYPE
    OBJECTS {
        tmnxPortNotifyPortId,
        tmnxPortNotifyEtherSymThreshold,
        tmnxPortNotifyEtherSymMultiplier,
        tmnxPortNotifyEtherSymAlarmValue
    }
    STATUS      current
    DESCRIPTION
        "tmnxEqPortEtherSymMonAlarm is generated when an Ethernet port Symbol
         alarm condition is detected. It is generated only when the type of
         alarm being raised is enabled on the port.

         [EFFECT] On a signal failure (SF) fault, the port is taken out of
         service until the Symbol alarm condition is cleared.

         [RECOVERY] tmnxEqPortEtherSymMonAlarm is cleared by taking the port out
         of service (eg. shutdown, card/mda reset, physical link loss), or
         changing/disabling the associated threshold/multiplier values.

         Signal Degradation is self clearing and will clear once the error rate
         drops below 1/10th of the configured rate."
    ::= { tmnxPortNotification 57 }

tmnxEqPortEtherSymMonAlarmClear  NOTIFICATION-TYPE
    OBJECTS {
        tmnxPortNotifyPortId,
        tmnxPortNotifyEtherSymThreshold,
        tmnxPortNotifyEtherSymMultiplier,
        tmnxPortNotifyEtherSymAlarmValue
    }
    STATUS      current
    DESCRIPTION
        "tmnxEqPortEtherSymMonAlarmClear is generated when an Ethernet port
         Symbol alarm condition is cleared or disabled."
    ::= { tmnxPortNotification 58 }

--%%%%%%%%%%%%%%%%%%%%%%%%%%%%%%%%%%%%%%%%%%%%%%%%%%%%%%%%%%%%%%%%%%%%%
--
--      The compliance specifications.
--

tmnxPortCompliances     OBJECT IDENTIFIER ::= { tmnxPortConformance 1 }
tmnxPortGroups            OBJECT IDENTIFIER ::= { tmnxPortConformance 2 }

tmnxPortComp7750        OBJECT IDENTIFIER ::= { tmnxPortCompliances 3 }
--  tmnxPortComp7750V3v0  OBJECT IDENTIFIER ::= { tmnxPortComp7750 1}

tmnxPortComp7450        OBJECT IDENTIFIER ::= { tmnxPortCompliances 4 }
--  tmnxPortComp7450V3v0  OBJECT IDENTIFIER ::= { tmnxPortComp7450 1 }

tmnxPortComp7710        OBJECT IDENTIFIER ::= { tmnxPortCompliances 5 }
--  tmnxPortComp7710V3v0  OBJECT IDENTIFIER ::= { tmnxPortComp7710 1 }

tmnxPortDCCompliances       OBJECT IDENTIFIER ::= { tmnxPortConformance 3 }
tmnxPortDCGroups            OBJECT IDENTIFIER ::= { tmnxPortConformance 4 }

-- tmnxPortCompliance  MODULE-COMPLIANCE
--    ::= { tmnxPortCompliances 1 }

-- tmnxPortR2r1Compliance  MODULE-COMPLIANCE
--    ::= { tmnxPortCompliances 2 }

-- tmnxPortComp7750V3v0  MODULE-COMPLIANCE
--    ::= { tmnxPortComp7750 1 }

tmnxPortComp7750V4v0  MODULE-COMPLIANCE
    STATUS  obsolete
    DESCRIPTION
            "The compliance statement for revision 4.0 of TIMETRA-PORT-MIB on
             the Alcatel-Lucent SROS series systems.

             tmnxMlImaBundleGroup was added as of R4."
    MODULE  -- this module
        MANDATORY-GROUPS {
            tmnxPortGroupV4v0,
            tmnxPortEthernetV3v0Group,
            tmnxPortSonetV3v0Group,
            tmnxPortTDMGroupV4v0,
            tmnxPortFRGroup,
            tmnxQosAppObjsGroup,
            -- tmnxPortTestGroup,
            tmnxPortNotificationGroupV3v0,
            tmnxPortIngrMdaQosStatR2r1Group,
            tmnxPortATMGroupV4v0,
            tmnxPortStatsR2r1Group,
            tmnxCiscoHDLCGroup,
            tmnxScalarPortV3v0Group,
            tmnxMlBundleGroupV4v0,
            tmnxMlImaBundleGroup
        }
    ::= { tmnxPortComp7750 2 }

tmnxPortComp7750V5v0  MODULE-COMPLIANCE
    STATUS  obsolete
    DESCRIPTION
            "The compliance statement for revision 5.0 of TIMETRA-PORT-MIB on
             the Alcatel-Lucent SROS series systems."
    MODULE  -- this module
        MANDATORY-GROUPS {
            tmnxPortGroupV5v0,
            tmnxPortSonetV3v0Group,
            tmnxPortTDMGroupV5v0,
            tmnxPortFRGroup,
            tmnxQosAppObjsGroup,
            -- tmnxPortTestGroup,
            tmnxPortNotificationGroupV5v0,
            tmnxPortIngrMdaQosStatR2r1Group,
            tmnxPortATMGroupV4v0,
            tmnxPortStatsR2r1Group,
            tmnxCiscoHDLCGroup,
            tmnxScalarPortV3v0Group,
            tmnxMlBundleGroupV5v0,
            tmnxMlImaBundleGroup,
            tmnxPortSchedV5v0Group,
            tmnxPortEthernetV5v0Group
        }
    ::= { tmnxPortComp7750 3 }

tmnxPortComp7750V6v0  MODULE-COMPLIANCE
    STATUS  obsolete
    DESCRIPTION
            "The compliance statement for revision 6.0 of TIMETRA-PORT-MIB on
             the Alcatel-Lucent SROS series systems."
    MODULE  -- this module
        MANDATORY-GROUPS {
            tmnxPortGroupV6v0,
            tmnxPortSonetV3v0Group,
            tmnxPortTDMGroupV6v0,
            tmnxPortFRGroup,
            tmnxQosAppObjsGroup,
            -- tmnxPortTestGroup,
            tmnxPortNotificationGroupV6v0,
            tmnxPortIngrMdaQosStatR2r1Group,
            tmnxPortATMGroupV4v0,
            tmnxPortStatsR2r1Group,
            tmnxCiscoHDLCGroup,
            tmnxScalarPortV3v0Group,
            tmnxMlBundleGroupV6v0,
            tmnxMlImaBundleGroup,
            tmnxPortSchedV5v0Group,
            tmnxPortEthernetV6v0Group,
            tmnxPortCemGroupV6v0,
            tmnxMcMlpppBundleGroup,
            tmnxMlpppBundleGroup,
            tmnxHsmdaGroupV6v0,
            tmnxDigitalDiagMonitorGroup
        }
    ::= { tmnxPortComp7750 4 }

tmnxPortComp7750V6v1  MODULE-COMPLIANCE
    STATUS  obsolete
    DESCRIPTION
            "The compliance statement for revision 6.1 of TIMETRA-PORT-MIB on
             the Alcatel-Lucent SROS series systems."
    MODULE  -- this module
        MANDATORY-GROUPS {
            tmnxPortGroupV6v0,
            tmnxPortSonetV3v0Group,
            tmnxPortTDMGroupV6v0,
            tmnxPortTDME1GroupV6v1,
            tmnxPortFRGroup,
            tmnxQosAppObjsGroup,
            -- tmnxPortTestGroup,
            tmnxPortNotificationGroupV6v0,
            tmnxPortIngrMdaQosStatR2r1Group,
            tmnxPortATMGroupV4v0,
            tmnxPortStatsR2r1Group,
            tmnxCiscoHDLCGroup,
            tmnxScalarPortV3v0Group,
            tmnxMlBundleGroupV6v0,
            tmnxMlImaBundleGroup,
            tmnxPortSchedV5v0Group,
            tmnxPortEthernetV6v1Group,
            tmnxPortCemGroupV6v0,
            tmnxMcMlpppBundleGroup,
            tmnxMlpppBundleGroup,
            tmnxHsmdaGroupV6v0,
            tmnxNamedPoolGroupV6v0,
            tmnxDigitalDiagMonitorGroup
        }
    ::= { tmnxPortComp7750 5 }

tmnxPortComp7750V7v0  MODULE-COMPLIANCE
    STATUS  obsolete
    DESCRIPTION
            "The compliance statement for revision 7.0 of TIMETRA-PORT-MIB on
             the Alcatel-Lucent SROS series systems."
    MODULE  -- this module
        MANDATORY-GROUPS {
            tmnxPortGroupV7v0,
            tmnxPortSonetV3v0Group,
            tmnxPortTDMGroupV7v0,
            tmnxPortTDME1GroupV6v1,
            tmnxPortFRGroup,
            tmnxQosAppObjsGroup,
            tmnxPortTestGroup,
            tmnxPortNotificationGroupV7v0,
            tmnxPortIngrMdaQosStatR2r1Group,
            tmnxPortATMGroupV7v0,
            tmnxPortStatsR2r1Group,
            tmnxCiscoHDLCGroup,
            tmnxScalarPortV3v0Group,
            tmnxMlBundleGroupV6v0,
            tmnxMlImaBundleGroup,
            tmnxPortSchedV5v0Group,
            tmnxPortEthernetV7v0Group,
            tmnxPortCemGroupV6v0,
            tmnxMcMlpppBundleGroup,
            tmnxMlpppBundleGroup,
            tmnxHsmdaGroupV6v0,
            tmnxNamedPoolGroupV6v0,
            tmnxDigitalDiagMonitorGroup,
            tmnxPortQV7v0Group,
            tmnxPortQStatV7v0Group,
            tmnxMcMfrBundleGroup,
            tmnxFrIntfGroup,
            tmnxFrf12IntfGroup,
            tmnxPortSchedStatsGroup
        }
    ::= { tmnxPortComp7750 6 }

tmnxPortComp7750V8v0  MODULE-COMPLIANCE
    STATUS  obsolete
    DESCRIPTION
            "The compliance statement for revision 8.0 of TIMETRA-PORT-MIB on
             the Alcatel-Lucent SROS series systems."
    MODULE  -- this module
        MANDATORY-GROUPS {
            tmnxPortGroupV7v0,
            tmnxPortSonetV3v0Group,
            tmnxPortTDMGroupV7v0,
            tmnxPortTDME1GroupV6v1,
            tmnxPortFRGroup,
            tmnxQosAppObjsGroup,
            tmnxPortTestGroup,
            tmnxPortNotificationGroupV8v0,
            tmnxPortIngrMdaQosStatR2r1Group,
            tmnxPortATMGroupV7v0,
            tmnxPortStatsR2r1Group,
            tmnxCiscoHDLCGroup,
            tmnxScalarPortV3v0Group,
            tmnxMlBundleGroupV6v0,
            tmnxMlImaBundleGroup,
            tmnxPortSchedV5v0Group,
            tmnxPortEthernetV7v0Group,
            tmnxPortCemGroupV6v0,
            tmnxMcMlpppBundleGroup,
            tmnxMlpppBundleGroup,
            tmnxHsmdaGroupV6v0,
            tmnxNamedPoolGroupV6v0,
            tmnxDigitalDiagMonitorGroup,
            tmnxPortQV8v0Group,
            tmnxPortQStatV7v0Group,
            tmnxMcMfrBundleGroup,
            tmnxFrIntfGroup,
            tmnxFrf12IntfGroup,
            tmnxWaveTrackerGroup,
            tmnxPortDwdmGroup,
            tmnxPortGroupV8v0,
            tmnxPortCEMGroupV8v0,
            tmnxPortSchedStatsGroup,
            tmnxPortVPortGroup,
            tmnxMlpppBundleGroupV7v0,
            tmnxOpticalPortGroup,
            tmnxPortNotificationGroupV8v9
        }
    ::= { tmnxPortComp7750 7 }

tmnxPortComp7750V9v0  MODULE-COMPLIANCE
    STATUS  obsolete
    DESCRIPTION
            "The compliance statement for revision 9.0 of TIMETRA-PORT-MIB on
             the Alcatel-Lucent SROS series systems.

             This MODULE-COMPLIANCE was made obsolete in favor of
             tmnxPortComplianceV9v0."
    MODULE  -- this module
        MANDATORY-GROUPS {
            tmnxPortGroupV7v0,
            tmnxPortSonetV3v0Group,
            tmnxPortTDMGroupV7v0,
            tmnxPortTDME1GroupV6v1,
            tmnxPortFRGroup,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxCiscoHDLCGroup,
            tmnxScalarPortV3v0Group,
            tmnxMlBundleGroupV6v0,
            tmnxMlImaBundleGroup,
            tmnxPortSchedV5v0Group,
            tmnxPortEthernetV7v0Group,
            tmnxPortCemGroupV6v0,
            tmnxMcMlpppBundleGroup,
            tmnxMlpppBundleGroup,
            tmnxHsmdaGroupV6v0,
            tmnxNamedPoolGroupV6v0,
            tmnxDigitalDiagMonitorGroup,
            tmnxPortQV8v0Group,
            tmnxPortQStatV7v0Group,
            tmnxMcMfrBundleGroup,
            tmnxFrIntfGroup,
            tmnxFrf12IntfGroup,
            tmnxWaveTrackerGroup,
            tmnxPortDwdmGroup,
            tmnxPortGroupV8v0,
            tmnxPortCEMGroupV8v0,
            tmnxPortSchedStatsGroup,
            tmnxPortVPortV9v0Group,
            tmnxMlpppBundleGroupV7v0,
            tmnxOpticalPortGroup,
            tmnxPortATMGroupV9v0,
            tmnxPortEgrExpShaperV9v0Group,
            tmnxPortObjAppV9v0Group,
            tmnxOpticalPortGroupV9v0,
            tmnxPortNotificationGroupV8v9,
            tmnxPortEgrVPortStatsV9v0Group
        }
    ::= { tmnxPortComp7750 8 }

        -- tmnxPortComp7450V3v0  MODULE-COMPLIANCE
--    ::= { tmnxPortComp7450 1 }

tmnxPortComp7450V4v0  MODULE-COMPLIANCE
    STATUS  obsolete
    DESCRIPTION
            "The compliance statement for revision 4.0 of TIMETRA-PORT-MIB on
             the Alcatel-Lucent 7450 SR series systems."
    MODULE  -- this module
        MANDATORY-GROUPS {
            tmnxPortGroupV4v0,
            tmnxPortEthernetV3v0Group,
            tmnxPortSonetV3v0Group,
            -- tmnxPortTDMGroupV4v0,
            tmnxPortFRGroup,
            tmnxQosAppObjsGroup,
            -- tmnxPortTestGroup,
            tmnxPortNotificationGroupV3v0,
            tmnxPortIngrMdaQosStatR2r1Group,
            tmnxPortStatsR2r1Group,
            tmnxScalarPortV3v0Group
            -- tmnxPortATMGroupV4v0,         No ATM on 7450
            -- tmnxCiscoHDLCGroup,           No Cisco HDLC on 7450
            -- tmnxMlBundleGroupV4v0         No ML Bundles on 7450
            -- tmnxMlImaBundleGroup          No IMA Bundles on 7450
        }
    ::= { tmnxPortComp7450 2 }

tmnxPortComp7450V5v0  MODULE-COMPLIANCE
    STATUS  obsolete
    DESCRIPTION
            "The compliance statement for revision 5.0 of TIMETRA-PORT-MIB on
             the Alcatel-Lucent 7450 SR series systems."
    MODULE  -- this module
        MANDATORY-GROUPS {
            tmnxPortGroupV5v0,
            tmnxPortSonetV3v0Group,
            --tmnxPortTDMGroupV5v0,         No TDM interfaces
            tmnxPortFRGroup,
            tmnxQosAppObjsGroup,
            -- tmnxPortTestGroup,
            tmnxPortNotificationGroupV5v0,
            tmnxPortIngrMdaQosStatR2r1Group,
            tmnxPortStatsR2r1Group,
            tmnxScalarPortV3v0Group,
            -- tmnxPortATMGroupV4v0,         No ATM on 7450
            -- tmnxCiscoHDLCGroup,           No Cisco HDLC on 7450
            -- tmnxMlBundleGroupV5v0         No ML Bundles on 7450
            -- tmnxMlImaBundleGroup          No IMA Bundles on 7450
            -- tmnxPortSchedV5v0Group,
            tmnxPortEthernetV5v0Group
        }
    ::= { tmnxPortComp7450 3 }

tmnxPortComp7450V6v0  MODULE-COMPLIANCE
    STATUS  obsolete
    DESCRIPTION
            "The compliance statement for revision 6.0 of TIMETRA-PORT-MIB on
             the Alcatel-Lucent 7450 SR series systems."
    MODULE  -- this module
        MANDATORY-GROUPS {
            tmnxPortGroupV6v0,
            tmnxPortSonetV3v0Group,
            -- tmnxPortTDMGroupV6v0,         No TDM interfaces
            -- tmnxPortTDME1GroupV6v1,
            tmnxPortFRGroup,
            tmnxQosAppObjsGroup,
            -- tmnxPortTestGroup,
            tmnxPortNotificationGroupV6v0,
            tmnxPortIngrMdaQosStatR2r1Group,
            tmnxPortStatsR2r1Group,
            tmnxScalarPortV3v0Group,
            -- tmnxPortATMGroupV4v0,         No ATM on 7450
            -- tmnxCiscoHDLCGroup,           No Cisco HDLC on 7450
            -- tmnxMlBundleGroupV5v0         No ML Bundles on 7450
            -- tmnxMlImaBundleGroup          No IMA Bundles on 7450
            -- tmnxPortSchedV5v0Group,
            tmnxPortEthernetV6v0Group,
            -- tmnxPortCemGroupV6v0          No CEM on 7450
            -- tmnxMcMlpppBundleGroup        No Multiclass MLPPP Bundles on 7450
            -- tmnxMlpppBundleGroup          No MLPPP Bundles on 7450
            tmnxHsmdaGroupV6v0,
            tmnxDigitalDiagMonitorGroup
        }
    ::= { tmnxPortComp7450 4 }

tmnxPortComp7450V6v1  MODULE-COMPLIANCE
    STATUS  obsolete
    DESCRIPTION
            "The compliance statement for revision 6.1 of TIMETRA-PORT-MIB on
             the Alcatel-Lucent 7450 SR series systems."
    MODULE  -- this module
        MANDATORY-GROUPS {
            tmnxPortGroupV6v0,
            tmnxPortSonetV3v0Group,
            -- tmnxPortTDMGroupV6v0,         No TDM interfaces
            -- tmnxPortTDME1GroupV6v1,
            tmnxPortFRGroup,
            tmnxQosAppObjsGroup,
            -- tmnxPortTestGroup,
            tmnxPortNotificationGroupV6v0,
            tmnxPortIngrMdaQosStatR2r1Group,
            tmnxPortStatsR2r1Group,
            tmnxScalarPortV3v0Group,
            -- tmnxPortATMGroupV4v0,         No ATM on 7450
            -- tmnxCiscoHDLCGroup,           No Cisco HDLC on 7450
            -- tmnxMlBundleGroupV5v0         No ML Bundles on 7450
            -- tmnxMlImaBundleGroup          No IMA Bundles on 7450
            -- tmnxPortSchedV5v0Group,
            tmnxPortEthernetV6v1Group,
            -- tmnxPortCemGroupV6v0          No CEM on 7450
            -- tmnxMcMlpppBundleGroup        No Multiclass MLPPP Bundles on 7450
            -- tmnxMlpppBundleGroup          No MLPPP Bundles on 7450
            tmnxHsmdaGroupV6v0,
            tmnxNamedPoolGroupV6v0,
            tmnxDigitalDiagMonitorGroup
        }
    ::= { tmnxPortComp7450 5 }

tmnxPortComp7450V7v0  MODULE-COMPLIANCE
    STATUS  obsolete
    DESCRIPTION
            "The compliance statement for revision 7.0 of TIMETRA-PORT-MIB on
             the Alcatel-Lucent 7450 SR series systems."
    MODULE  -- this module
        MANDATORY-GROUPS {
            tmnxPortGroupV7v0,
            tmnxPortSonetV3v0Group,
            -- tmnxPortTDMGroupV6v0,         No TDM interfaces
            -- tmnxPortTDME1GroupV6v1,
            tmnxPortFRGroup,
            tmnxQosAppObjsGroup,
            tmnxPortTestGroup,
            tmnxPortNotificationGroupV7v0,
            tmnxPortIngrMdaQosStatR2r1Group,
            tmnxPortStatsR2r1Group,
            tmnxScalarPortV3v0Group,
            -- tmnxPortATMGroupV7v0,         No ATM on 7450
            -- tmnxCiscoHDLCGroup,           No Cisco HDLC on 7450
            -- tmnxMlBundleGroupV5v0         No ML Bundles on 7450
            -- tmnxMlImaBundleGroup          No IMA Bundles on 7450
            -- tmnxPortSchedV5v0Group,
            tmnxPortEthernetV7v0Group,
            -- tmnxPortCemGroupV6v0          No CEM on 7450
            -- tmnxMcMlpppBundleGroup        No Multiclass MLPPP Bundles on 7450
            -- tmnxMlpppBundleGroup          No MLPPP Bundles on 7450
            tmnxHsmdaGroupV6v0,
            tmnxNamedPoolGroupV6v0,
            tmnxDigitalDiagMonitorGroup,
            tmnxPortQV7v0Group,
            tmnxPortQStatV7v0Group,
            tmnxPortSchedStatsGroup
        }
    ::= { tmnxPortComp7450 6 }

tmnxPortComp7450V8v0  MODULE-COMPLIANCE
    STATUS  obsolete
    DESCRIPTION
            "The compliance statement for revision 8.0 of TIMETRA-PORT-MIB on
             the Alcatel-Lucent 7450 SR series systems."
    MODULE  -- this module
        MANDATORY-GROUPS {
            tmnxPortGroupV7v0,
            tmnxPortSonetV3v0Group,
            -- tmnxPortTDMGroupV6v0,         No TDM interfaces
            -- tmnxPortTDME1GroupV6v1,
            tmnxPortFRGroup,
            tmnxQosAppObjsGroup,
            tmnxPortTestGroup,
            tmnxPortNotificationGroupV8v0,
            tmnxPortIngrMdaQosStatR2r1Group,
            tmnxPortStatsR2r1Group,
            tmnxScalarPortV3v0Group,
            -- tmnxPortATMGroupV7v0,         No ATM on 7450
            -- tmnxCiscoHDLCGroup,           No Cisco HDLC on 7450
            -- tmnxMlBundleGroupV5v0         No ML Bundles on 7450
            -- tmnxMlImaBundleGroup          No IMA Bundles on 7450
            -- tmnxPortSchedV5v0Group,
            tmnxPortEthernetV7v0Group,
            -- tmnxPortCemGroupV6v0          No CEM on 7450
            -- tmnxMcMlpppBundleGroup        No Multiclass MLPPP Bundles on 7450
            -- tmnxMlpppBundleGroup          No MLPPP Bundles on 7450
            tmnxHsmdaGroupV6v0,
            tmnxNamedPoolGroupV6v0,
            tmnxDigitalDiagMonitorGroup,
            tmnxPortQV8v0Group,
            tmnxPortQStatV7v0Group,
            tmnxWaveTrackerGroup,
            tmnxPortDwdmGroup,
            tmnxPortGroupV8v0,
            tmnxPortCEMGroupV8v0,
            tmnxPortSchedStatsGroup,
            tmnxMlpppBundleGroupV7v0,
            tmnxOpticalPortGroup,
            tmnxPortNotificationGroupV8v9
        }
    ::= { tmnxPortComp7450 7 }

tmnxPortComp7710V3v0  MODULE-COMPLIANCE
    STATUS  obsolete
    DESCRIPTION
            "The compliance statement for revision 3.0 of TIMETRA-PORT-MIB."
    MODULE  -- this module
        MANDATORY-GROUPS {
            tmnxPortV3v0Group,
            tmnxPortEthernetV3v0Group,
            tmnxPortSonetV3v0Group,
            tmnxPortTDMV3v0Group,
            tmnxPortFRGroup,
            tmnxQosAppObjsGroup,
            tmnxPortTestGroup,
            tmnxPortNotificationGroupR2r1,
            tmnxPortIngrMdaQosStatR2r1Group,
            tmnxPortATMV3v0Group,
            tmnxPortStatsR2r1Group,
            tmnxCiscoHDLCGroup,
            tmnxScalarPortV3v0Group,
            tmnxMlBundleV3v0Group,
            tmnx7710PortTDMGroupV3v0
        }
    ::= { tmnxPortComp7710 1 }

tmnxPortComp7710V5v0  MODULE-COMPLIANCE
    STATUS  obsolete
    DESCRIPTION
            "The compliance statement for revision 5.0 of TIMETRA-PORT-MIB."
    MODULE  -- this module
        MANDATORY-GROUPS {
            tmnxPortGroupV5v0,
            tmnxPortEthernetV5v0Group,
            tmnxPortSonetV3v0Group,
            tmnxPortTDMGroupV5v0,
            tmnxPortFRGroup,
            tmnxQosAppObjsGroup,
            -- tmnxPortTestGroup,
            tmnxPortNotificationGroupV5v0,
            tmnxPortIngrMdaQosStatR2r1Group,
            tmnxPortATMGroupV4v0,
            tmnxPortStatsR2r1Group,
            tmnxCiscoHDLCGroup,
            tmnxScalarPortV3v0Group,
            tmnxMlBundleGroupV5v0,
            tmnxPortSchedV5v0Group,
            tmnx7710PortTDMGroupV5v0
        }
    ::= { tmnxPortComp7710 2 }

tmnxPortComp7710V6v0  MODULE-COMPLIANCE
    STATUS  obsolete
    DESCRIPTION
            "The compliance statement for revision 6.0 of TIMETRA-PORT-MIB."
    MODULE  -- this module
        MANDATORY-GROUPS {
            tmnxPortGroupV6v0,
            tmnxPortEthernetV6v0Group,
            tmnxPortSonetV3v0Group,
            tmnxPortTDMGroupV6v0,
            tmnxPortFRGroup,
            tmnxQosAppObjsGroup,
            -- tmnxPortTestGroup,
            tmnxPortNotificationGroupV6v0,
            tmnxPortIngrMdaQosStatR2r1Group,
            tmnxPortATMGroupV4v0,
            tmnxPortStatsR2r1Group,
            tmnxCiscoHDLCGroup,
            tmnxScalarPortV3v0Group,
            tmnxMlBundleGroupV6v0,
            tmnxPortSchedV5v0Group,
            tmnx7710PortTDMGroupV5v0,
            tmnxPortCemGroupV6v0,
            tmnxMcMlpppBundleGroup,
            tmnxMlpppBundleGroup,
            -- tmnxHsmdaGroupV6v0,
            tmnxDigitalDiagMonitorGroup
        }
    ::= { tmnxPortComp7710 3 }

tmnxPortComp7710V6v1  MODULE-COMPLIANCE
    STATUS  obsolete
    DESCRIPTION
            "The compliance statement for revision 6.1 of TIMETRA-PORT-MIB."
    MODULE  -- this module
        MANDATORY-GROUPS {
            tmnxPortGroupV6v0,
            tmnxPortEthernetV6v1Group,
            tmnxPortSonetV3v0Group,
            tmnxPortTDMGroupV6v0,
            tmnxPortTDME1GroupV6v1,
            tmnxPortFRGroup,
            tmnxQosAppObjsGroup,
            -- tmnxPortTestGroup,
            tmnxPortNotificationGroupV6v0,
            tmnxPortIngrMdaQosStatR2r1Group,
            tmnxPortATMGroupV4v0,
            tmnxPortStatsR2r1Group,
            tmnxCiscoHDLCGroup,
            tmnxScalarPortV3v0Group,
            tmnxMlBundleGroupV6v0,
            tmnxPortSchedV5v0Group,
            tmnx7710PortTDMGroupV5v0,
            tmnxPortCemGroupV6v0,
            tmnxMcMlpppBundleGroup,
            tmnxMlpppBundleGroup,
            -- tmnxHsmdaGroupV6v0,
            -- tmnxNamedPoolGroupV6v0
            tmnxDigitalDiagMonitorGroup
        }
    ::= { tmnxPortComp7710 4 }

tmnxPortComp7710V7v0  MODULE-COMPLIANCE
    STATUS  obsolete
    DESCRIPTION
            "The compliance statement for revision 7.0 of TIMETRA-PORT-MIB."
    MODULE  -- this module
        MANDATORY-GROUPS {
            tmnxPortGroupV7v0,
            tmnxPortEthernetV7v0Group,
            tmnxPortSonetV3v0Group,
            tmnxPortTDMGroupV7v0,
            tmnxPortTDME1GroupV6v1,
            tmnxPortFRGroup,
            tmnxQosAppObjsGroup,
            tmnxPortTestGroup,
            tmnxPortNotificationGroupV7v0,
            tmnxPortIngrMdaQosStatR2r1Group,
            tmnxPortATMGroupV7v0,
            tmnxPortStatsR2r1Group,
            tmnxCiscoHDLCGroup,
            tmnxScalarPortV3v0Group,
            tmnxMlBundleGroupV6v0,
            tmnxPortSchedV5v0Group,
            tmnx7710PortTDMGroupV5v0,
            tmnxPortCemGroupV6v0,
            tmnxMcMlpppBundleGroup,
            tmnxMlpppBundleGroup,
            -- tmnxHsmdaGroupV6v0,
            -- tmnxNamedPoolGroupV6v0
            tmnxDigitalDiagMonitorGroup,
            tmnxPortQV7v0Group,
            tmnxPortQStatV7v0Group,
            tmnxPortSchedStatsGroup
        }
    ::= { tmnxPortComp7710 5 }

tmnxPortComp7710V8v0  MODULE-COMPLIANCE
    STATUS  obsolete
    DESCRIPTION
            "The compliance statement for revision 8.0 of TIMETRA-PORT-MIB."
    MODULE  -- this module
        MANDATORY-GROUPS {
            tmnxPortGroupV7v0,
            tmnxPortEthernetV7v0Group,
            tmnxPortSonetV3v0Group,
            tmnxPortTDMGroupV7v0,
            tmnxPortTDME1GroupV6v1,
            tmnxPortFRGroup,
            tmnxQosAppObjsGroup,
            tmnxPortTestGroup,
            tmnxPortNotificationGroupV8v0,
            tmnxPortIngrMdaQosStatR2r1Group,
            tmnxPortATMGroupV7v0,
            tmnxPortStatsR2r1Group,
            tmnxCiscoHDLCGroup,
            tmnxScalarPortV3v0Group,
            tmnxMlBundleGroupV6v0,
            tmnxPortSchedV5v0Group,
            tmnx7710PortTDMGroupV5v0,
            tmnxPortCemGroupV6v0,
            tmnxMcMlpppBundleGroup,
            tmnxMlpppBundleGroup,
            -- tmnxHsmdaGroupV6v0,
            -- tmnxNamedPoolGroupV6v0
            tmnxDigitalDiagMonitorGroup,
            tmnxPortQV8v0Group,
            tmnxPortQStatV7v0Group,
            tmnxWaveTrackerGroup,
            tmnxPortDwdmGroup,
            tmnxPortGroupV8v0,
            tmnxPortCEMGroupV8v0,
            tmnxPortSchedStatsGroup,
            tmnxMlpppBundleGroupV7v0,
            tmnxOpticalPortGroup,
            tmnxPortNotificationGroupV8v9
        }
    ::= { tmnxPortComp7710 6 }

-- MODULE-COMPLIANCE statements for the SROS series systems.
tmnxPortComplianceV9v0  MODULE-COMPLIANCE
    STATUS  obsolete
    DESCRIPTION
            "The compliance statement for revision 9.0 of TIMETRA-PORT-MIB on
             the Alcatel-Lucent SROS series systems."
    MODULE  -- this module
        MANDATORY-GROUPS {
            tmnxPortGroupV7v0,
            tmnxPortSonetV3v0Group,
            tmnxPortTDMGroupV7v0,
            tmnxPortTDME1GroupV6v1,
            tmnxPortFRGroup,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxCiscoHDLCGroup,
            tmnxScalarPortV3v0Group,
            tmnxMlBundleGroupV6v0,
            tmnxMlImaBundleGroup,
            tmnxPortSchedV5v0Group,
            tmnxPortEthernetV7v0Group,
            tmnxPortCemGroupV6v0,
            tmnxMcMlpppBundleGroup,
            tmnxMlpppBundleGroup,
            tmnxHsmdaGroupV6v0,
            tmnxNamedPoolGroupV6v0,
            tmnxDigitalDiagMonitorGroup,
            tmnxPortQV8v0Group,
            tmnx7710PortTDMGroupV5v0,
            tmnxPortQStatV7v0Group,
            tmnxMcMfrBundleGroup,
            tmnxFrIntfGroup,
            tmnxFrf12IntfGroup,
            tmnxWaveTrackerGroup,
            tmnxPortDwdmGroup,
            tmnxPortGroupV8v0,
            tmnxPortCEMGroupV8v0,
            tmnxPortSchedStatsGroup,
            tmnxPortVPortV9v0Group,
            tmnxMlpppBundleGroupV7v0,
            tmnxOpticalPortGroup,
            tmnxPortATMGroupV9v0,
            tmnxPortEgrExpShaperV9v0Group,
            tmnxPortObjAppV9v0Group,
            tmnxOpticalPortGroupV9v0,
            tmnxPortNotificationGroupV8v9,
            tmnxPortEgrVPortStatsV9v0Group,
            tmnxPortEtherV9v0Group,
            tmnxPortNotificationV9v0Group,
            tmnxPortV9v0Group
        }
    ::= { tmnxPortCompliances 6 }

tmnxPortComplianceV10v0  MODULE-COMPLIANCE
    STATUS  obsolete
    DESCRIPTION
            "The compliance statement for revision 10.0 of TIMETRA-PORT-MIB on
             the Alcatel-Lucent SROS series systems."
    MODULE  -- this module
        MANDATORY-GROUPS {
            tmnxPortGroupV7v0,
            tmnxPortSonetV3v0Group,
            tmnxPortTDMGroupV7v0,
            tmnxPortTDME1GroupV6v1,
            tmnxPortFRGroup,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxCiscoHDLCGroup,
            tmnxScalarPortV3v0Group,
            tmnxMlBundleGroupV6v0,
            tmnxMlImaBundleGroup,
            tmnxPortSchedV5v0Group,
            tmnxPortEthernetV7v0Group,
            tmnxPortEthernetV10v0Group,
            tmnxPortCemGroupV6v0,
            tmnxMcMlpppBundleGroup,
            tmnxMlpppBundleGroup,
            tmnxHsmdaGroupV10v0,
            tmnxNamedPoolGroupV6v0,
            tmnxDigitalDiagMonitorGroup,
            tmnxDDMLaneGroupV10v0,
            tmnxPortQV8v0Group,
            tmnx7710PortTDMGroupV5v0,
            tmnxPortQStatV7v0Group,
            tmnxMcMfrBundleGroup,
            tmnxFrIntfGroup,
            tmnxFrf12IntfGroup,
            tmnxWaveTrackerGroup,
            tmnxPortDwdmGroup,
            tmnxPortGroupV8v0,
            tmnxPortCEMGroupV8v0,
            tmnxPortSchedStatsGroup,
            tmnxPortVPortV9v0Group,
            tmnxMlpppBundleGroupV7v0,
            tmnxOpticalPortGroup,
            tmnxPortATMGroupV9v0,
            tmnxPortEgrExpShaperV9v0Group,
            tmnxPortObjAppV9v0Group,
            tmnxOpticalPortGroupV9v0,
            tmnxPortNotificationGroupV8v9,
            tmnxPortEgrVPortStatsV9v0Group,
            tmnxPortEtherV9v0Group,
            tmnxPortNotificationV9v0Group,
            tmnxPortV9v0Group,
            tmnxPortNetEgrV10v0Group,
            tmnxPortPlcyGroup,
            tmnxPwPortV10v0Group,
            tmnxPortLoadBalGroupV10v0,
            tmnxPortEtherPhysStatsGroup
        }
    ::= { tmnxPortCompliances 7 }

tmnxPortComplianceV11v0  MODULE-COMPLIANCE
    STATUS  obsolete
    DESCRIPTION
            "The compliance statement for revision 11.0 of TIMETRA-PORT-MIB on
             the Alcatel-Lucent SROS series systems."
    MODULE  -- this module
        MANDATORY-GROUPS {
            tmnxPortGroupV7v0,
            tmnxPortSonetV3v0Group,
            tmnxPortTDMGroupV7v0,
            tmnxPortTDME1GroupV6v1,
            tmnxPortFRGroup,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxCiscoHDLCGroup,
            tmnxScalarPortV3v0Group,
            tmnxScalarPortV11v0Group,
            tmnxMlBundleGroupV6v0,
            tmnxMlImaBundleGroup,
            tmnxPortSchedV5v0Group,
            tmnxPortEthernetV7v0Group,
            tmnxPortEthernetV10v0Group,
            tmnxPortCemGroupV6v0,
            tmnxMcMlpppBundleGroup,
            tmnxMlpppBundleGroup,
            tmnxHsmdaGroupV10v0,
            tmnxNamedPoolGroupV6v0,
            tmnxDigitalDiagMonitorGroup,
            tmnxDDMLaneGroupV10v0,
            tmnxPortQV8v0Group,
            tmnx7710PortTDMGroupV5v0,
            tmnxPortQStatV7v0Group,
            tmnxMcMfrBundleGroup,
            tmnxFrIntfGroup,
            tmnxFrf12IntfGroup,
            tmnxWaveTrackerGroup,
            tmnxPortDwdmGroup,
            tmnxPortGroupV8v0,
            tmnxPortCEMGroupV8v0,
            tmnxPortSchedStatsGroup,
            tmnxPortVPortV9v0Group,
            tmnxPortVPortV11v0Group,
            tmnxMlpppBundleGroupV7v0,
            tmnxOpticalPortGroup,
            tmnxPortATMGroupV9v0,
            tmnxPortEgrExpShaperV9v0Group,
            tmnxPortObjAppV9v0Group,
            tmnxOpticalPortGroupV9v0,
            tmnxPortNotificationGroupV8v9,
            tmnxPortEgrVPortStatsV9v0Group,
            tmnxPortEtherV9v0Group,
            tmnxPortNotificationV9v0Group,
            tmnxPortV9v0Group,
            tmnxPortNetEgrV10v0Group,
            tmnxPortPlcyGroup,
            tmnxPwPortV10v0Group,
            tmnxPortLoadBalGroupV10v0,
            tmnxPortEgrQGrpV11v0Group,
            tmnxPortEtherPhysStatsGroup,
            tmnxWaveTrackerV11v0Group,
            tmnxPortEgrQGrpV11v0Group,
            tmnxCohOptPortGroup,
            tmnxCohOptPortStatsGroup,
            tmnxPortNotificationV11v0Group,
            tmnxPortEgrHsmdaStatV11v0Group,
            tmnxPortEgrHsmdaOverV11v0Group,
            tmnxPortEthernetV11v0Group
        }
    ::= { tmnxPortCompliances 8 }


tmnxPortComplianceV12v0  MODULE-COMPLIANCE
    STATUS  current
    DESCRIPTION
            "The compliance statement for revision 12.0 of TIMETRA-PORT-MIB on
             the Alcatel-Lucent SROS series systems."
    MODULE  -- this module
        MANDATORY-GROUPS {
            tmnxDS3V12v0Group,
            tmnxPortGroupV7v0,
            tmnxPortSonetV3v0Group,
            tmnxPortTDMGroupV7v0,
            tmnxPortTDME1GroupV6v1,
            tmnxPortFRGroup,
            tmnxQosAppObjsGroup,
            tmnxPortTestGroup,
            tmnxPortNotificationGroupV8v0,
            tmnxPortNotificationGroupV9v4,
            tmnxPortIngrMdaQosStatR2r1Group,
            tmnxPortATMGroupV7v0,
            tmnxPortStatsR2r1Group,
            tmnxCiscoHDLCGroup,
            tmnxScalarPortV3v0Group,
            tmnxScalarPortV11v0Group,
            tmnxMlBundleGroupV6v0,
            tmnxMlImaBundleGroup,
            tmnxPortSchedV5v0Group,
            tmnxPortEthernetV7v0Group,
            tmnxPortEthernetV10v0Group,
            tmnxPortCemGroupV6v0,
            tmnxMcMlpppBundleGroup,
            tmnxMlpppBundleGroup,
            tmnxHsmdaGroupV10v0,
            tmnxNamedPoolGroupV6v0,
            tmnxDigitalDiagMonitorGroup,
            tmnxDDMLaneGroupV10v0,
            tmnxPortQV8v0Group,
            tmnx7710PortTDMGroupV5v0,
            tmnxPortQStatV7v0Group,
            tmnxMcMfrBundleGroup,
            tmnxFrIntfGroup,
            tmnxFrf12IntfGroup,
            tmnxWaveTrackerGroup,
            tmnxPortDwdmGroup,
            tmnxPortGroupV8v0,
            tmnxPortCEMGroupV8v0,
            tmnxPortSchedStatsGroup,
            tmnxPortVPortV9v0Group,
            tmnxPortVPortV11v0Group,
            tmnxPortVPortV12v0Group,
            tmnxPortParentLocV12v0Group,
            tmnxMlpppBundleGroupV7v0,
            tmnxOpticalPortGroup,
            tmnxPortATMGroupV9v0,
            tmnxPortEgrExpShaperV9v0Group,
            tmnxPortObjAppV9v0Group,
            tmnxOpticalPortGroupV9v0,
            tmnxPortNotificationGroupV8v9,
            tmnxPortEgrVPortStatsV9v0Group,
            tmnxPortEtherV9v0Group,
            tmnxPortNotificationV9v0Group,
            tmnxPortV9v0Group,
            tmnxPortNetEgrV10v0Group,
            tmnxPortPlcyGroup,
            tmnxPwPortV10v0Group,
            tmnxPortLoadBalGroupV10v0,
            tmnxPortEgrQGrpV11v0Group,
            tmnxPortEtherPhysStatsGroup,
            tmnxPortEtherSymMonGroupV12v0,
            tmnxPrtEthSmMnNotifyObjsGrpV12v0,
            tmnxPortEthSymMonNotifyGrpV12v0,
            tmnxWaveTrackerV11v0Group,
            tmnxPortEgrQGrpV11v0Group,
            tmnxCohOptPortGroup,
            tmnxCohOptPortStatsGroup,
            tmnxPortNotificationV11v0Group,
            tmnxPortEgrHsmdaStatV11v0Group,
            tmnxPortEgrHsmdaOverV11v0Group,
            tmnxPortEthernetV11v0Group,
            tmnxCohOptPortV11v0Group,
            tmnxDot1xPaePortGroup,
            tmnxPortAggRateV12v0Group,
            tmnxPortSchedPlcyV12v0Group
        }
    ::= { tmnxPortCompliances 9 }

-- units of conformance

-- tmnxPortGroup   OBJECT-GROUP
--    ::= { tmnxPortGroups 1 }

-- tmnxPortEthernetGroup       OBJECT-GROUP
--    ::= { tmnxPortGroups 2 }

-- tmnxPortSONETGroup      OBJECT-GROUP
--    ::= { tmnxPortGroups 3 }

-- tmnxPortTDMGroup    OBJECT-GROUP
--    ::= { tmnxPortGroups 4 }

tmnxPortFRGroup     OBJECT-GROUP
    OBJECTS {   tmnxFRDlcmiMode,
                tmnxFRDlcmiN392Dce,
                tmnxFRDlcmiN393Dce,
                tmnxFRDlcmiT392Dce,
                tmnxFRDlcmiTxStatusEnqMsgs,
                tmnxFRDlcmiRxStatusEnqMsgs,
                tmnxFRDlcmiStatusEnqMsgTimeouts,
                tmnxFRDlcmiTxStatusMsgs,
                tmnxFRDlcmiRxStatusMsgs,
                tmnxFRDlcmiStatusMsgTimeouts,
                tmnxFRDlcmiDiscardedMsgs,
                tmnxFRDlcmiInvRxSeqNumMsgs
            }
    STATUS      current
    DESCRIPTION
        "The group of objects supporting management of Frame Relay DLCMI
         on Alcatel-Lucent SROS series systems."
    ::= { tmnxPortGroups 5 }

tmnxQosAppObjsGroup     OBJECT-GROUP
    OBJECTS {   tmnxObjectAppPoolRowStatus,
                tmnxObjectAppResvCbs,
                tmnxObjectAppSlopePolicy,
                tmnxObjectAppPoolSize
            }
    STATUS      current
    DESCRIPTION
        "The group of objects supporting management of Qos associations of
         the buffer pools to mdas, ports, channels and bundles on
         Alcatel-Lucent SROS series systems."
    ::= { tmnxPortGroups 6 }

tmnxPortTestGroup       OBJECT-GROUP
    OBJECTS {   tmnxPortTestState,
                tmnxPortTestMode,
                tmnxPortTestParameter,
                tmnxPortTestLastResult,
                tmnxPortTestStartTime,
                tmnxPortTestEndTime,
                tmnxPortTestDuration,
                tmnxPortTestAction
            }
    STATUS      current
    DESCRIPTION
        "The group of objects supporting management of port testing
         on Alcatel-Lucent SROS series system."
    ::= { tmnxPortGroups 7 }

-- tmnxPortNotifyObjsGroup   OBJECT-GROUP
--    ::= { tmnxPortGroups 8 }

-- tmnxPortNotificationGroup NOTIFICATION-GROUP
--    ::= { tmnxPortGroups 9 }

-- tmnxPortATMGroup     OBJECT-GROUP
--    ::= { tmnxPortGroups 10 }

tmnxPortObsoleteGroup    OBJECT-GROUP
    OBJECTS {
                tmnxDS1IdleCycleFlags,
                tmnxSonetPathType,
                tmnxPortFCStatsIngFwdInProfPkts,
                tmnxPortFCStatsIngFwdOutProfPkts,
                tmnxPortFCStatsIngFwdInProfOcts,
                tmnxPortFCStatsIngFwdOutProfOcts,
                tmnxPortFCStatsIngDroInProfPkts,
                tmnxPortFCStatsIngDroOutProfPkts,
                tmnxPortFCStatsIngDroInProfOcts,
                tmnxPortFCStatsIngDroOutProfOcts,
                tmnxPortFCStatsEgrFwdInProfPkts,
                tmnxPortFCStatsEgrFwdOutProfPkts,
                tmnxPortFCStatsEgrFwdInProfOcts,
                tmnxPortFCStatsEgrFwdOutProfOcts,
                tmnxPortFCStatsEgrDroInProfPkts,
                tmnxPortFCStatsEgrDroOutProfPkts,
                tmnxPortFCStatsEgrDroInProfOcts,
                tmnxPortFCStatsEgrDroOutProfOcts
            }
    STATUS      current
    DESCRIPTION
        "The group of objects in TIMETRA-PORT-MIB which are obsoleted."
    ::= { tmnxPortGroups 11 }

-- tmnxPortR2r1Group   OBJECT-GROUP
--    ::= { tmnxPortGroups 12 }

-- tmnxPortEthernetR2r1Group       OBJECT-GROUP
--    ::= { tmnxPortGroups 13 }

tmnxPortIngrMdaQosStatR2r1Group OBJECT-GROUP
    OBJECTS {
             tmnxPortIngrMdaQos00StatDropPkts,
             tmnxPortIngrMdaQos00StatDropOcts,
             tmnxPortIngrMdaQos01StatDropPkts,
             tmnxPortIngrMdaQos01StatDropOcts,
             tmnxPortIngrMdaQos02StatDropPkts,
             tmnxPortIngrMdaQos02StatDropOcts,
             tmnxPortIngrMdaQos03StatDropPkts,
             tmnxPortIngrMdaQos03StatDropOcts,
             tmnxPortIngrMdaQos04StatDropPkts,
             tmnxPortIngrMdaQos04StatDropOcts,
             tmnxPortIngrMdaQos05StatDropPkts,
             tmnxPortIngrMdaQos05StatDropOcts,
             tmnxPortIngrMdaQos06StatDropPkts,
             tmnxPortIngrMdaQos06StatDropOcts,
             tmnxPortIngrMdaQos07StatDropPkts,
             tmnxPortIngrMdaQos07StatDropOcts,
             tmnxPortIngrMdaQos08StatDropPkts,
             tmnxPortIngrMdaQos08StatDropOcts,
             tmnxPortIngrMdaQos09StatDropPkts,
             tmnxPortIngrMdaQos09StatDropOcts,
             tmnxPortIngrMdaQos10StatDropPkts,
             tmnxPortIngrMdaQos10StatDropOcts,
             tmnxPortIngrMdaQos11StatDropPkts,
             tmnxPortIngrMdaQos11StatDropOcts,
             tmnxPortIngrMdaQos12StatDropPkts,
             tmnxPortIngrMdaQos12StatDropOcts,
             tmnxPortIngrMdaQos13StatDropPkts,
             tmnxPortIngrMdaQos13StatDropOcts,
             tmnxPortIngrMdaQos14StatDropPkts,
             tmnxPortIngrMdaQos14StatDropOcts,
             tmnxPortIngrMdaQos15StatDropPkts,
             tmnxPortIngrMdaQos15StatDropOcts
            }
    STATUS        current
    DESCRIPTION
        "The group of objects that describe the MDA QoS discard
         statistics for an ethernet port located on an oversubscribed MDA
         for revision 2.1 on Alcatel-Lucent SROS series systems."
    ::= { tmnxPortGroups 14 }

-- tmnxPortSONETR2r1Group      OBJECT-GROUP
--    ::= { tmnxPortGroups 15 }

tmnxPortStatsR2r1Group      OBJECT-GROUP
    OBJECTS {
                tmnxPortNetIngressFwdInProfPkts,
                tmnxPortNetIngressFwdOutProfPkts,
                tmnxPortNetIngressFwdInProfOcts,
                tmnxPortNetIngressFwdOutProfOcts,
                tmnxPortNetIngressDroInProfPkts,
                tmnxPortNetIngressDroOutProfPkts,
                tmnxPortNetIngressDroInProfOcts,
                tmnxPortNetIngressDroOutProfOcts,
                tmnxPortNetEgressFwdInProfPkts,
                tmnxPortNetEgressFwdOutProfPkts,
                tmnxPortNetEgressFwdInProfOcts,
                tmnxPortNetEgressFwdOutProfOcts,
                tmnxPortNetEgressDroInProfPkts,
                tmnxPortNetEgressDroOutProfPkts,
                tmnxPortNetEgressDroInProfOcts,
                tmnxPortNetEgressDroOutProfOcts
            }
    STATUS      current
    DESCRIPTION
        "The group of objects supporting port statistics
         for revision 2.1 on Alcatel-Lucent SROS series systems."
    ::= { tmnxPortGroups 16 }

tmnxPortNotificationGroupR2r1 NOTIFICATION-GROUP
    NOTIFICATIONS   {   tmnxEqPortSonetAlarm,
                        tmnxEqPortSonetAlarmClear,
                        tmnxEqPortSonetPathAlarm,
                        tmnxEqPortSonetPathAlarmClear,
                        tmnxEqPortSFPInserted,
                        tmnxEqPortSFPRemoved,
                        tmnxEqPortSFPCorrupted,
                        tmnxEqPortError,
                        tmnxEqPortDS3Alarm,
                        tmnxEqPortDS3AlarmClear,
                        tmnxEqPortDS1Alarm,
                        tmnxEqPortDS1AlarmClear,
                        tmnxEqPortBndlYellowDiffExceeded,
                        tmnxEqPortBndlRedDiffExceeded,
                        tmnxEqPortBndlBadEndPtDiscr,
                        tmnxEqPortEtherAlarm,
                        tmnxEqPortEtherAlarmClear
                    }
    STATUS        obsolete
    DESCRIPTION
        "The group of notifications supporting the management of physical
         ports for revision 2.1 on Alcatel-Lucent SROS series systems."
    ::= { tmnxPortGroups 17 }

tmnxPortNotifyObjsGroupR2r1   OBJECT-GROUP
    OBJECTS {   tmnxPortNotifyPortId,
                tmnxPortNotifySonetAlarmReason,
                tmnxPortNotifySonetPathAlarmReason,
                tmnxPortNotifyError,
                tmnxPortNotifyDS3AlarmReason,
                tmnxPortNotifyDS1AlarmReason,
                tmnxPortNotifyBundleId,
                tmnxPortNotifyEtherAlarmReason
            }
    STATUS        current
    DESCRIPTION
        "The group of objects supporting physical port notifications
          for revision 2.1 on Alcatel-Lucent SROS series systems."
    ::= { tmnxPortGroups 18 }

-- tmnxPortTDMGroupR2r1    OBJECT-GROUP
--    ::= { tmnxPortGroups 19 }

tmnxPortNotifyObsoleteGroup NOTIFICATION-GROUP
    NOTIFICATIONS   {   tmnxEqOobPortFailure,
                        tmnxEqPortFailure,
                        tmnxQosServiceDegraded,
                        tmnxPortNotifyBerSdTca,
                        tmnxPortNotifyBerSfTca,
                        tmnxEqPortWrongSFP,
                        tmnxEqPortSFPCorrupted
                    }
    STATUS        current
    DESCRIPTION
        "The group of notifications supporting the management of physical
         ports made obsolete for revision 2.1 on Alcatel-Lucent SROS series
         systems. tmnxEqPortSFPCorrupted was made obsolete for revision 6.0
         on Alcatel-Lucent SROS series systems."
    ::= { tmnxPortGroups 20 }

tmnxPortSonetV3v0Group      OBJECT-GROUP
    OBJECTS {   tmnxSonetSpeed,
                tmnxSonetClockSource,
                tmnxSonetFraming,
                tmnxSonetReportAlarm,
                tmnxSonetBerSdThreshold,
                tmnxSonetBerSfThreshold,
                tmnxSonetLoopback,
                tmnxSonetReportAlarmStatus,
                tmnxSonetSectionTraceMode,
                tmnxSonetJ0String,
                tmnxSonetMonS1Byte,
                tmnxSonetMonJ0String,
                tmnxSonetMonK1Byte,
                tmnxSonetMonK2Byte,
                tmnxSonetSingleFiber,
                tmnxSonetHoldTimeUp,
                tmnxSonetHoldTimeDown,
                tmnxSonetPathRowStatus,
                tmnxSonetPathLastChangeTime,
                tmnxSonetPathMTU,
                tmnxSonetPathScramble,
                tmnxSonetPathC2Byte,
                tmnxSonetPathJ1String,
                tmnxSonetPathCRC,
                tmnxSonetPathOperMTU,
                tmnxSonetPathOperMRU,
                tmnxSonetPathReportAlarm,
                tmnxSonetPathAcctPolicyId,
                tmnxSonetPathCollectStats,
                tmnxSonetPathReportAlarmStatus,
                tmnxSonetPathMonC2Byte,
                tmnxSonetPathMonJ1String,
                tmnxSonetPathChildType,
                tmnxSonetGroupType,
                tmnxSonetGroupParentPortID,
                tmnxSonetGroupChildType,
                tmnxSonetGroupName
            }
    STATUS      current
    DESCRIPTION
        "The group of objects supporting management of SONET type ports
         for revision 3.0 on Alcatel-Lucent SROS series systems."
    ::= { tmnxPortGroups 21 }

tmnxPortTDMV3v0Group    OBJECT-GROUP
    OBJECTS {   tmnxDS3Buildout,
                tmnxDS3Type,
                tmnxDS3LastChangeTime,
                tmnxDS3ChannelRowStatus,
                tmnxDS3ChannelType,
                tmnxDS3ChannelFraming,
                tmnxDS3ChannelClockSource,
                tmnxDS3ChannelChannelized,
                tmnxDS3ChannelSubrateCSUMode,
                tmnxDS3ChannelSubrate,
                tmnxDS3ChannelIdleCycleFlags,
                tmnxDS3ChannelLoopback,
                tmnxDS3ChannelBitErrorInsertionRate,
                tmnxDS3ChannelBERTPattern,
                tmnxDS3ChannelBERTDuration,
                tmnxDS3ChannelMDLEicString,
                tmnxDS3ChannelMDLLicString,
                tmnxDS3ChannelMDLFicString,
                tmnxDS3ChannelMDLUnitString,
                tmnxDS3ChannelMDLPfiString,
                tmnxDS3ChannelMDLPortString,
                tmnxDS3ChannelMDLGenString,
                tmnxDS3ChannelMDLMessageType,
                tmnxDS3ChannelFEACLoopRespond,
                tmnxDS3ChannelCRC,
                tmnxDS3ChannelMTU,
                tmnxDS3ChannelOperMTU,
                tmnxDS3ChannelReportAlarm,
                tmnxDS3ChannelReportAlarmStatus,
                tmnxDS3ChannelLastChangeTime,
                tmnxDS3ChannelInFEACLoop,
                tmnxDS3ChannelMDLMonPortString,
                tmnxDS3ChannelMDLMonGenString,
                tmnxDS3ChannelBERTOperStatus,
                tmnxDS3ChannelBERTSynched,
                tmnxDS3ChannelBERTErrors,
                tmnxDS3ChannelBERTTotalBits,
                tmnxDS1RowStatus,
                tmnxDS1Type,
                tmnxDS1Framing,
                tmnxDS1Loopback,
                tmnxDS1InvertData,
                tmnxDS1BitErrorInsertionRate,
                tmnxDS1BERTPattern,
                tmnxDS1BERTDuration,
                tmnxDS1ReportAlarm,
                tmnxDS1ReportAlarmStatus,
                tmnxDS1LastChangeTime,
                tmnxDS1ClockSource,
                tmnxDS1BERTOperStatus,
                tmnxDS1BERTSynched,
                tmnxDS1BERTErrors,
                tmnxDS1BERTTotalBits,
                tmnxDS1RemoteLoopRespond,
                tmnxDS1InRemoteLoop,
                tmnxDS0ChanGroupRowStatus,
                tmnxDS0ChanGroupTimeSlots,
                tmnxDS0ChanGroupSpeed,
                tmnxDS0ChanGroupCRC,
                tmnxDS0ChanGroupMTU,
                tmnxDS0ChanGroupOperMTU,
                tmnxDS0ChanGroupLastChangeTime,
                tmnxDS0ChanGroupIdleCycleFlags
            }
    STATUS      obsolete
    DESCRIPTION
        "The group of objects supporting management of TDM type ports
         for revision 3.0 on the Alcatel-Lucent SROS series systems."
    ::= { tmnxPortGroups 22 }

tmnxPortATMV3v0Group     OBJECT-GROUP
    OBJECTS {
                tmnxATMIntfCellFormat,
                tmnxATMIntfMinVpValue
            }
    STATUS      obsolete
    DESCRIPTION
        "The group of objects supporting management of ATM interfaces
         for version 3.0 on Alcatel-Lucent SROS series systems."
    ::= { tmnxPortGroups 23 }

tmnxScalarPortV3v0Group         OBJECT-GROUP
    OBJECTS { tmnxL4LoadBalancing }
    STATUS      current
    DESCRIPTION
        "The group of objects supporting management for general port
         settings for revision 3.0 on Alcatel-Lucent SROS series systems."
    ::= { tmnxPortGroups 24 }

tmnxPortV3v0Group   OBJECT-GROUP
    OBJECTS {   tmnxPortTableLastChange,
                tmnxPortLastChangeTime,
                tmnxPortType,
                tmnxPortClass,
                tmnxPortDescription,
                tmnxPortName,
                tmnxPortAlias,
                tmnxPortUserAssignedMac,
                tmnxPortMacAddress,
                tmnxPortHwMacAddress,
                tmnxPortMode,
                tmnxPortEncapType,
                tmnxPortLagId,
                tmnxPortHoldTimeUp,
                tmnxPortHoldTimeDown,
                tmnxPortUpProtocols,
                tmnxPortConnectorType,
                tmnxPortTransceiverType,
                tmnxPortTransceiverCode,
                tmnxPortTransceiverLaserWaveLen,
                tmnxPortTransceiverDiagCapable,
                tmnxPortTransceiverModelNumber,
                tmnxPortSFPConnectorCode,
                tmnxPortSFPVendorOUI,
                tmnxPortSFPVendorManufactureDate,
                tmnxPortSFPMedia,
                tmnxPortSFPEquipped,
                tmnxPortSFPVendorSerialNum,
                tmnxPortSFPVendorPartNum,
                tmnxPortEquipped,
                tmnxPortLinkStatus,
                tmnxPortAdminStatus,
                tmnxPortOperStatus,
                tmnxPortState,
                tmnxPortPrevState,
                tmnxPortNumAlarms,
                tmnxPortAlarmState,
                tmnxPortLastAlarmEvent,
                tmnxPortClearAlarms,
                tmnxPortLastStateChanged,
                tmnxPortNumChannels,
                tmnxPortNetworkEgrQueues,
                tmnxPortIsLeaf,
                tmnxPortChanType,
                tmnxPortParentPortID,
                tmnxPortLoadBalanceAlgorithm,
                tmnxPortTypeName,
                tmnxPortTypeDescription,
                tmnxPortTypeStatus,
                tmnxPortConnectTypeName,
                tmnxPortConnectTypeDescription,
                tmnxPortConnectTypeStatus,
                tmnxChannelPortID,
                tmnxPortOpticalCompliance,
                tmnxL4LoadBalancing
            }
    STATUS        obsolete
    DESCRIPTION
        "The group of objects supporting management of physical port
         capabilities for revision 3.0 on Alcatel-Lucent SROS series systems."
    ::= { tmnxPortGroups 25 }

tmnxCiscoHDLCGroup      OBJECT-GROUP
    OBJECTS {   tmnxCiscoHDLCKeepAliveInt,
                tmnxCiscoHDLCUpCount,
                tmnxCiscoHDLCDownCount,
                tmnxCiscoHDLCOperState,
                tmnxCiscoHDLCDiscardStatInPkts,
                tmnxCiscoHDLCDiscardStatOutPkts,
                tmnxCiscoHDLCStatInPkts,
                tmnxCiscoHDLCStatOutPkts,
                tmnxCiscoHDLCStatInOctets,
                tmnxCiscoHDLCStatOutOctets
           }
    STATUS     current
    DESCRIPTION
        "The group of objects supporting Cisco HDLC encapsulation on 
         Alcatel-Lucent SROS series systems."
    ::= { tmnxPortGroups 26 }

tmnxMlBundleV3v0Group    OBJECT-GROUP
    OBJECTS {   tmnxBundleRowStatus,
                tmnxBundleType,
                tmnxBundleMinimumLinks,
                tmnxBundleNumLinks,
                tmnxBundleNumActiveLinks,
                tmnxBundleMRRU,
                tmnxBundleOperMRRU,
                tmnxBundlePeerMRRU,
                tmnxBundleOperMTU,
                tmnxBundleRedDiffDelay,
                tmnxBundleRedDiffDelayAction,
                tmnxBundleYellowDiffDelay,
                tmnxBundleShortSequence,
                tmnxBundleLastChangeTime,
                tmnxBundleFragmentThreshold,
                tmnxBundleUpTime,
                tmnxBundleMemberRowStatus,
                tmnxBundleMemberActive,
                tmnxBundleMemberDownReason,
                tmnxBundleMemberUpTime,
                tmnxBundleInputDiscards,
                tmnxBundlePrimaryMemberPortID,
                tmnxBundleLFI,
                tmnxPortBundleNumber
            }
    STATUS      obsolete
    DESCRIPTION
        "The group of objects supporting management MLBUNDLES
         for revision 3.0 on the Alcatel-Lucent SROS series systems."
    ::= { tmnxPortGroups 27 }

tmnxObsoleteGroupV3v0    OBJECT-GROUP
    OBJECTS {   tmnxSonetAps,
                tmnxSonetApsAdminStatus,
                tmnxSonetApsOperStatus,
                tmnxSonetApsAuthKey,
                tmnxSonetApsNeighborAddr,
                tmnxSonetApsAdvertiseInterval,
                tmnxSonetApsAdvertiseTimeLeft,
                tmnxSonetApsHoldTime,
                tmnxSonetApsHoldTimeLeft
            }
    STATUS      current
    DESCRIPTION
        "The group of objects obsoleted in the 7x50 SR series 3.0 release"
    ::= { tmnxPortGroups 28 }

tmnxPortEthernetV3v0Group       OBJECT-GROUP
    OBJECTS {  tmnxPortEtherMTU,
                tmnxPortEtherDuplex,
                tmnxPortEtherSpeed,
                tmnxPortEtherAutoNegotiate,
                tmnxPortEtherOperDuplex,
                tmnxPortEtherOperSpeed,
                tmnxPortEtherAcctPolicyId,
                tmnxPortEtherCollectStats,
                tmnxPortEtherMDIMDIX,
                tmnxPortEtherXGigMode,
                tmnxPortEtherEgressRate,
                tmnxPortEtherDot1qEtype,
                tmnxPortEtherQinqEtype,
                tmnxPortEtherIngressRate,
                tmnxPortEtherReportAlarm,
                tmnxPortEtherReportAlarmStatus,
                tmnxPortEtherPkts1519toMax,
                tmnxPortEtherHCOverPkts1519toMax,
                tmnxPortEtherHCPkts1519toMax
            }
    STATUS      obsolete
    DESCRIPTION
        "The group of objects supporting management of Ethernet ports
         for revision 3.0 on Alcatel-Lucent SROS series systems."
    ::= { tmnxPortGroups 29 }

tmnxPortTDMGroupV4v0    OBJECT-GROUP
    OBJECTS {   tmnxDS3Buildout,
                tmnxDS3Type,
                tmnxDS3LastChangeTime,
                tmnxDS3ChannelRowStatus,
                tmnxDS3ChannelType,
                tmnxDS3ChannelFraming,
                tmnxDS3ChannelClockSource,
                tmnxDS3ChannelChannelized,
                tmnxDS3ChannelSubrateCSUMode,
                tmnxDS3ChannelSubrate,
                tmnxDS3ChannelIdleCycleFlags,
                tmnxDS3ChannelLoopback,
                tmnxDS3ChannelBitErrorInsertionRate,
                tmnxDS3ChannelBERTPattern,
                tmnxDS3ChannelBERTDuration,
                tmnxDS3ChannelMDLEicString,
                tmnxDS3ChannelMDLLicString,
                tmnxDS3ChannelMDLFicString,
                tmnxDS3ChannelMDLUnitString,
                tmnxDS3ChannelMDLPfiString,
                tmnxDS3ChannelMDLPortString,
                tmnxDS3ChannelMDLGenString,
                tmnxDS3ChannelMDLMessageType,
                tmnxDS3ChannelFEACLoopRespond,
                tmnxDS3ChannelCRC,
                tmnxDS3ChannelMTU,
                tmnxDS3ChannelOperMTU,
                tmnxDS3ChannelReportAlarm,
                tmnxDS3ChannelReportAlarmStatus,
                tmnxDS3ChannelLastChangeTime,
                tmnxDS3ChannelInFEACLoop,
                tmnxDS3ChannelMDLMonPortString,
                tmnxDS3ChannelMDLMonGenString,
                tmnxDS3ChannelBERTOperStatus,
                tmnxDS3ChannelBERTSynched,
                tmnxDS3ChannelBERTErrors,
                tmnxDS3ChannelBERTTotalBits,
                tmnxDS3ChannelScramble,
                tmnxDS1RowStatus,
                tmnxDS1Type,
                tmnxDS1Framing,
                tmnxDS1Loopback,
                tmnxDS1InvertData,
                tmnxDS1BitErrorInsertionRate,
                tmnxDS1BERTPattern,
                tmnxDS1BERTDuration,
                tmnxDS1ReportAlarm,
                tmnxDS1ReportAlarmStatus,
                tmnxDS1LastChangeTime,
                tmnxDS1ClockSource,
                tmnxDS1BERTOperStatus,
                tmnxDS1BERTSynched,
                tmnxDS1BERTErrors,
                tmnxDS1BERTTotalBits,
                tmnxDS1RemoteLoopRespond,
                tmnxDS1InRemoteLoop,
                tmnxDS0ChanGroupRowStatus,
                tmnxDS0ChanGroupTimeSlots,
                tmnxDS0ChanGroupSpeed,
                tmnxDS0ChanGroupCRC,
                tmnxDS0ChanGroupMTU,
                tmnxDS0ChanGroupOperMTU,
                tmnxDS0ChanGroupLastChangeTime,
                tmnxDS0ChanGroupIdleCycleFlags,
                tmnxDS0ChanGroupScramble
            }
    STATUS      obsolete
    DESCRIPTION
        "The group of objects supporting management of TDM type ports
         for version 4.0 on the Alcatel-Lucent SROS series systems."
    ::= { tmnxPortGroups 30 }

tmnxPortATMGroupV4v0     OBJECT-GROUP
    OBJECTS {
                tmnxATMIntfCellFormat,
                tmnxATMIntfMinVpValue,
                tmnxATMIntfMapping
            }
    STATUS      obsolete
    DESCRIPTION
        "The group of objects supporting management of ATM interfaces
         for version 4.0 on Alcatel-Lucent SROS series systems."
    ::= { tmnxPortGroups 31 }

tmnxMlBundleGroupV4v0    OBJECT-GROUP
    OBJECTS {   tmnxBundleRowStatus,
                tmnxBundleType,
                tmnxBundleMinimumLinks,
                tmnxBundleNumLinks,
                tmnxBundleNumActiveLinks,
                tmnxBundleMRRU,
                tmnxBundleOperMRRU,
                tmnxBundlePeerMRRU,
                tmnxBundleOperMTU,
                tmnxBundleRedDiffDelay,
                tmnxBundleRedDiffDelayAction,
                tmnxBundleYellowDiffDelay,
                tmnxBundleShortSequence,
                tmnxBundleLastChangeTime,
                tmnxBundleFragmentThreshold,
                tmnxBundleUpTime,
                tmnxBundleMemberRowStatus,
                tmnxBundleMemberActive,
                tmnxBundleMemberDownReason,
                tmnxBundleMemberUpTime,
                tmnxBundleInputDiscards,
                tmnxBundlePrimaryMemberPortID,
                tmnxBundleLFI,
                tmnxPortBundleNumber
            }
    STATUS      obsolete
    DESCRIPTION
        "The group of objects supporting management MLBUNDLES
         for revision 4.0 on the Alcatel-Lucent SROS series systems."
    ::= { tmnxPortGroups 32 }

tmnxMlImaBundleGroup    OBJECT-GROUP
    OBJECTS {
                tmnxBundleImaGrpLnkActTimer,
                tmnxBundleImaGrpLnkDeactTimer,
                tmnxBundleImaGrpSymmetryMode,
                tmnxBundleImaGrpTxId,
                tmnxBundleImaGrpRxId,
                tmnxBundleImaGrpTxRefLnk,
                tmnxBundleImaGrpRxRefLnk,
                tmnxBundleImaGrpSmNeState,
                tmnxBundleImaGrpSmFeState,
                tmnxBundleImaGrpSmFailState,
                tmnxBundleImaGrpSmDownSecs,
                tmnxBundleImaGrpSmOperSecs,
                tmnxBundleImaGrpAvailTxCR,
                tmnxBundleImaGrpAvailRxCR,
                tmnxBundleImaGrpNeFails,
                tmnxBundleImaGrpFeFails,
                tmnxBundleImaGrpTxIcpCells,
                tmnxBundleImaGrpRxIcpCells,
                tmnxBundleImaGrpErrorIcpCells,
                tmnxBundleImaGrpLostRxIcpCells,
                tmnxBundleImaGrpTxOamLablVal,
                tmnxBundleImaGrpRxOamLablVal,
                tmnxBundleImaGrpAlphaValue,
                tmnxBundleImaGrpBetaValue,
                tmnxBundleImaGrpGammaValue,
                tmnxBundleImaGrpNeClockMode,
                tmnxBundleImaGrpFeClockMode,
                tmnxBundleImaGrpVersion,
                tmnxBundleImaGrpMaxConfBw,
                tmnxBundleImaGrpTestState,
                tmnxBundleImaGrpTestMember,
                tmnxBundleImaGrpTestPattern,
                tmnxBundleImaGrpDiffDelayMaxObs,
                tmnxBundleImaGrpLeastDelayLink,
                tmnxBundleMemberImaNeTxState,
                tmnxBundleMemberImaNeRxState,
                tmnxBundleMemberImaFeTxState,
                tmnxBundleMemberImaFeRxState,
                tmnxBundleMemberImaNeRxFailState,
                tmnxBundleMemberImaFeRxFailState,
                tmnxBundleMemberImaTxLid,
                tmnxBundleMemberImaRxLid,
                tmnxBundleMemberImaViolations,
                tmnxBundleMemberImaNeSevErrSecs,
                tmnxBundleMemberImaFeSevErrSecs,
                tmnxBundleMemberImaNeUnavailSecs,
                tmnxBundleMemberImaFeUnavailSecs,
                tmnxBundleMemberImaNeTxUnuseSecs,
                tmnxBundleMemberImaNeRxUnuseSecs,
                tmnxBundleMemberImaFeTxUnuseSecs,
                tmnxBundleMemberImaFeRxUnuseSecs,
                tmnxBundleMemberImaNeTxNumFails,
                tmnxBundleMemberImaNeRxNumFails,
                tmnxBundleMemberImaFeTxNumFails,
                tmnxBundleMemberImaFeRxNumFails,
                tmnxBundleMemberImaTxIcpCells,
                tmnxBundleMemberImaRxIcpCells,
                tmnxBundleMemberImaErrorIcpCells,
                tmnxBundleMemberImaLstRxIcpCells,
                tmnxBundleMemberImaOifAnomalies,
                tmnxBundleMemberImaRxTestState,
                tmnxBundleMemberImaRxTestPattern,
                tmnxBundleMemberImaRelDelay
            }
    STATUS      current
    DESCRIPTION
        "The group of objects supporting management of Ima Groups
         and Members on the Alcatel-Lucent SROS series systems."
    ::= { tmnxPortGroups 33 }

tmnx7710PortTDMGroupV3v0   OBJECT-GROUP
    OBJECTS {
                tmnxDS3ChannelAcctPolicyId,
                tmnxDS3ChannelCollectStats,
                tmnxDS1PortBuildout,
                tmnxDS1PortLastChangeTime,
                tmnxDS1PortType,
                tmnxDS1PortLineLength,
                tmnxDS1PortLbo,
                tmnxDS1PortDbGain,
                tmnxDS1InsertSingleBitError,
                tmnxDS0ChanGroupAcctPolicyId,
                tmnxDS0ChanGroupCollectStats
           }
    STATUS     obsolete
    DESCRIPTION
        "The group of objects supporting management of TDM type ports
         specific to the Alcatel-Lucent 7710 SR series systems for revision 3.0."
    ::= { tmnxPortGroups 34 }

tmnxPortGroupV4v0   OBJECT-GROUP
    OBJECTS {   tmnxPortTableLastChange,
                tmnxPortLastChangeTime,
                tmnxPortType,
                tmnxPortClass,
                tmnxPortDescription,
                tmnxPortName,
                tmnxPortAlias,
                tmnxPortUserAssignedMac,
                tmnxPortMacAddress,
                tmnxPortHwMacAddress,
                tmnxPortMode,
                tmnxPortEncapType,
                tmnxPortLagId,
                tmnxPortHoldTimeUp,
                tmnxPortHoldTimeDown,
                tmnxPortUpProtocols,
                tmnxPortConnectorType,
                tmnxPortTransceiverType,
                tmnxPortTransceiverCode,
                tmnxPortTransceiverLaserWaveLen,
                tmnxPortTransceiverDiagCapable,
                tmnxPortTransceiverModelNumber,
                tmnxPortSFPConnectorCode,
                tmnxPortSFPVendorOUI,
                tmnxPortSFPVendorManufactureDate,
                tmnxPortSFPMedia,
                tmnxPortSFPEquipped,
                tmnxPortSFPVendorSerialNum,
                tmnxPortSFPVendorPartNum,
                tmnxPortEquipped,
                tmnxPortLinkStatus,
                tmnxPortAdminStatus,
                tmnxPortOperStatus,
                tmnxPortState,
                tmnxPortPrevState,
                tmnxPortNumAlarms,
                tmnxPortAlarmState,
                tmnxPortLastAlarmEvent,
                tmnxPortClearAlarms,
                tmnxPortLastStateChanged,
                tmnxPortNumChannels,
                tmnxPortNetworkEgrQueues,
                tmnxPortIsLeaf,
                tmnxPortChanType,
                tmnxPortParentPortID,
                tmnxPortLoadBalanceAlgorithm,
                tmnxPortTypeName,
                tmnxPortTypeDescription,
                tmnxPortTypeStatus,
                tmnxPortConnectTypeName,
                tmnxPortConnectTypeDescription,
                tmnxPortConnectTypeStatus,
                tmnxChannelPortID,
                tmnxPortOpticalCompliance,
                tmnxL4LoadBalancing
            }
    STATUS        obsolete
    DESCRIPTION
        "The group of objects supporting management of physical port
         capabilities for revision 4.0 on Alcatel-Lucent SROS series systems."
    ::= { tmnxPortGroups 35 }

tmnxObsoleteGroupV5v0    OBJECT-GROUP
    OBJECTS {
                tmnxPortTransceiverCode
            }
    STATUS      current
    DESCRIPTION
        "The group of objects obsoleted in the 7x50 SR series 5.0 release"
    ::= { tmnxPortGroups 36 }

tmnxPortSchedV5v0Group  OBJECT-GROUP
    OBJECTS {
                tmnxPortEgrPortSchedPlcy,
                tmnxPortSchedOverrideRowStatus,
                tmnxPortSchedOverrideSchedName,
                tmnxPortSchedOverrideLastChanged,
                tmnxPortSchedOverrideMaxRate,
                tmnxPortSchedOverrideLvl1PIR,
                tmnxPortSchedOverrideLvl1CIR,
                tmnxPortSchedOverrideLvl2PIR,
                tmnxPortSchedOverrideLvl2CIR,
                tmnxPortSchedOverrideLvl3PIR,
                tmnxPortSchedOverrideLvl3CIR,
                tmnxPortSchedOverrideLvl4PIR,
                tmnxPortSchedOverrideLvl4CIR,
                tmnxPortSchedOverrideLvl5PIR,
                tmnxPortSchedOverrideLvl5CIR,
                tmnxPortSchedOverrideLvl6PIR,
                tmnxPortSchedOverrideLvl6CIR,
                tmnxPortSchedOverrideLvl7PIR,
                tmnxPortSchedOverrideLvl7CIR,
                tmnxPortSchedOverrideLvl8PIR,
                tmnxPortSchedOverrideLvl8CIR,
                tmnxPortSchedOverrideFlags
            }
    STATUS        current
    DESCRIPTION
        "The group of objects supporting management of physical port
         virtual scheduler capabilities for revision 5.0 on Alcatel-Lucent
         SROS series systems."
    ::= { tmnxPortGroups 37 }

tmnxPortEthernetV5v0Group       OBJECT-GROUP
    OBJECTS {  tmnxPortEtherMTU,
                tmnxPortEtherDuplex,
                tmnxPortEtherSpeed,
                tmnxPortEtherAutoNegotiate,
                tmnxPortEtherOperDuplex,
                tmnxPortEtherOperSpeed,
                tmnxPortEtherAcctPolicyId,
                tmnxPortEtherCollectStats,
                tmnxPortEtherMDIMDIX,
                tmnxPortEtherXGigMode,
                tmnxPortEtherEgressRate,
                tmnxPortEtherDot1qEtype,
                tmnxPortEtherQinqEtype,
                tmnxPortEtherIngressRate,
                tmnxPortEtherReportAlarm,
                tmnxPortEtherReportAlarmStatus,
                tmnxPortEtherPkts1519toMax,
                tmnxPortEtherHCOverPkts1519toMax,
                tmnxPortEtherHCPkts1519toMax,
                tmnxPortEtherLacpTunnel
            }
    STATUS      obsolete
    DESCRIPTION
        "The group of objects supporting management of Ethernet ports
         for revision 5.0 on Alcatel-Lucent SROS series systems."
    ::= { tmnxPortGroups 38 }

tmnxPortGroupV5v0   OBJECT-GROUP
    OBJECTS {   tmnxPortTableLastChange,
                tmnxPortLastChangeTime,
                tmnxPortType,
                tmnxPortClass,
                tmnxPortDescription,
                tmnxPortName,
                tmnxPortAlias,
                tmnxPortUserAssignedMac,
                tmnxPortMacAddress,
                tmnxPortHwMacAddress,
                tmnxPortMode,
                tmnxPortEncapType,
                tmnxPortLagId,
                tmnxPortHoldTimeUp,
                tmnxPortHoldTimeDown,
                tmnxPortUpProtocols,
                tmnxPortConnectorType,
                tmnxPortTransceiverType,
                tmnxPortTransceiverCode,
                tmnxPortTransceiverLaserWaveLen,
                tmnxPortTransceiverDiagCapable,
                tmnxPortTransceiverModelNumber,
                tmnxPortSFPConnectorCode,
                tmnxPortSFPVendorOUI,
                tmnxPortSFPVendorManufactureDate,
                tmnxPortSFPMedia,
                tmnxPortSFPEquipped,
                tmnxPortSFPVendorSerialNum,
                tmnxPortSFPVendorPartNum,
                tmnxPortEquipped,
                tmnxPortLinkStatus,
                tmnxPortAdminStatus,
                tmnxPortOperStatus,
                tmnxPortState,
                tmnxPortPrevState,
                tmnxPortNumAlarms,
                tmnxPortAlarmState,
                tmnxPortLastAlarmEvent,
                tmnxPortClearAlarms,
                tmnxPortLastStateChanged,
                tmnxPortNumChannels,
                tmnxPortNetworkEgrQueues,
                tmnxPortIsLeaf,
                tmnxPortChanType,
                tmnxPortParentPortID,
                tmnxPortLoadBalanceAlgorithm,
                tmnxPortTypeName,
                tmnxPortTypeDescription,
                tmnxPortTypeStatus,
                tmnxPortConnectTypeName,
                tmnxPortConnectTypeDescription,
                tmnxPortConnectTypeStatus,
                tmnxChannelPortID,
                tmnxPortOpticalCompliance,
                tmnxL4LoadBalancing,
                tmnxPortLastClearedTime
            }
    STATUS        obsolete
    DESCRIPTION
        "The group of objects supporting management of physical port
         capabilities for revision 5.0 on Alcatel-Lucent SROS series systems."
    ::= { tmnxPortGroups 39 }

tmnxMlBundleGroupV5v0    OBJECT-GROUP
    OBJECTS {   tmnxBundleRowStatus,
                tmnxBundleType,
                tmnxBundleMinimumLinks,
                tmnxBundleNumLinks,
                tmnxBundleNumActiveLinks,
                tmnxBundleMRRU,
                tmnxBundleOperMRRU,
                tmnxBundlePeerMRRU,
                tmnxBundleOperMTU,
                tmnxBundleRedDiffDelay,
                tmnxBundleRedDiffDelayAction,
                tmnxBundleYellowDiffDelay,
                tmnxBundleShortSequence,
                tmnxBundleLastChangeTime,
                tmnxBundleFragmentThreshold,
                tmnxBundleUpTime,
                tmnxBundleMemberRowStatus,
                tmnxBundleMemberActive,
                tmnxBundleMemberDownReason,
                tmnxBundleMemberUpTime,
                tmnxBundleInputDiscards,
                tmnxBundlePrimaryMemberPortID,
                tmnxBundleLFI,
                tmnxPortBundleNumber,
                tmnxBundleProtectedType,
                tmnxBundleParentBundle,
                tmnxBPGrpAssocWorkingBundleID,
                tmnxBPGrpAssocProtectBundleID,
                tmnxBPGrpAssocActiveBundleID
            }
    STATUS      obsolete
    DESCRIPTION
        "The group of objects supporting management MLBUNDLES
         for revision 5.0 on the Alcatel-Lucent SROS series systems."
    ::= { tmnxPortGroups 40 }

tmnxPortNotificationGroupV5v0 NOTIFICATION-GROUP
    NOTIFICATIONS   {   tmnxEqPortSonetAlarm,
                        tmnxEqPortSonetAlarmClear,
                        tmnxEqPortSonetPathAlarm,
                        tmnxEqPortSonetPathAlarmClear,
                        tmnxEqPortSFPInserted,
                        tmnxEqPortSFPRemoved,
                        tmnxEqPortSFPCorrupted,
                        tmnxEqPortError,
                        tmnxEqPortDS3Alarm,
                        tmnxEqPortDS3AlarmClear,
                        tmnxEqPortDS1Alarm,
                        tmnxEqPortDS1AlarmClear,
                        tmnxEqPortBndlYellowDiffExceeded,
                        tmnxEqPortBndlRedDiffExceeded,
                        tmnxEqPortBndlBadEndPtDiscr,
                        tmnxEqPortEtherAlarm,
                        tmnxEqPortEtherAlarmClear,
                        tmnxDS1E1LoopbackStarted,
                        tmnxDS1E1LoopbackStopped,
                        tmnxDS3E3LoopbackStarted,
                        tmnxDS3E3LoopbackStopped,
                        tmnxSonetSDHLoopbackStarted,
                        tmnxSonetSDHLoopbackStopped,
                        tmnxEqPortSpeedCfgNotCompatible,
                        tmnxEqPortDuplexCfgNotCompatible,
                        tmnxEqPortIngressRateCfgNotCompatible
                    }
    STATUS        obsolete
    DESCRIPTION
        "The group of notifications supporting the management of physical
         ports for revision 5.0 on Alcatel-Lucent SROS series systems."
    ::= { tmnxPortGroups 41 }

tmnxPortTDMGroupV5v0    OBJECT-GROUP
    OBJECTS {   tmnxDS3ChannelAcctPolicyId,
                tmnxDS3ChannelCollectStats,
                tmnxDS3Buildout,
                tmnxDS3Type,
                tmnxDS3LastChangeTime,
                tmnxDS3ChannelRowStatus,
                tmnxDS3ChannelType,
                tmnxDS3ChannelFraming,
                tmnxDS3ChannelClockSource,
                tmnxDS3ChannelChannelized,
                tmnxDS3ChannelSubrateCSUMode,
                tmnxDS3ChannelSubrate,
                tmnxDS3ChannelIdleCycleFlags,
                tmnxDS3ChannelLoopback,
                tmnxDS3ChannelBitErrorInsertionRate,
                tmnxDS3ChannelBERTPattern,
                tmnxDS3ChannelBERTDuration,
                tmnxDS3ChannelMDLEicString,
                tmnxDS3ChannelMDLLicString,
                tmnxDS3ChannelMDLFicString,
                tmnxDS3ChannelMDLUnitString,
                tmnxDS3ChannelMDLPfiString,
                tmnxDS3ChannelMDLPortString,
                tmnxDS3ChannelMDLGenString,
                tmnxDS3ChannelMDLMessageType,
                tmnxDS3ChannelFEACLoopRespond,
                tmnxDS3ChannelCRC,
                tmnxDS3ChannelMTU,
                tmnxDS3ChannelOperMTU,
                tmnxDS3ChannelReportAlarm,
                tmnxDS3ChannelReportAlarmStatus,
                tmnxDS3ChannelLastChangeTime,
                tmnxDS3ChannelInFEACLoop,
                tmnxDS3ChannelMDLMonPortString,
                tmnxDS3ChannelMDLMonGenString,
                tmnxDS3ChannelBERTOperStatus,
                tmnxDS3ChannelBERTSynched,
                tmnxDS3ChannelBERTErrors,
                tmnxDS3ChannelBERTTotalBits,
                tmnxDS3ChannelScramble,
                tmnxDS1RowStatus,
                tmnxDS1Type,
                tmnxDS1Framing,
                tmnxDS1Loopback,
                tmnxDS1InvertData,
                tmnxDS1BitErrorInsertionRate,
                tmnxDS1BERTPattern,
                tmnxDS1BERTDuration,
                tmnxDS1ReportAlarm,
                tmnxDS1ReportAlarmStatus,
                tmnxDS1LastChangeTime,
                tmnxDS1ClockSource,
                tmnxDS1BERTOperStatus,
                tmnxDS1BERTSynched,
                tmnxDS1BERTErrors,
                tmnxDS1BERTTotalBits,
                tmnxDS1RemoteLoopRespond,
                tmnxDS1InRemoteLoop,
                tmnxDS0ChanGroupRowStatus,
                tmnxDS0ChanGroupTimeSlots,
                tmnxDS0ChanGroupSpeed,
                tmnxDS0ChanGroupCRC,
                tmnxDS0ChanGroupMTU,
                tmnxDS0ChanGroupOperMTU,
                tmnxDS0ChanGroupLastChangeTime,
                tmnxDS0ChanGroupIdleCycleFlags,
                tmnxDS0ChanGroupScramble
            }
    STATUS      obsolete
    DESCRIPTION
        "The group of objects supporting management of TDM type ports
         for version 5.0 on the Alcatel-Lucent SROS series systems."
    ::= { tmnxPortGroups 42 }

tmnx7710PortTDMGroupV5v0   OBJECT-GROUP
    OBJECTS {
                tmnxDS1PortBuildout,
                tmnxDS1PortLastChangeTime,
                tmnxDS1PortType,
                tmnxDS1PortLineLength,
                tmnxDS1PortLbo,
                tmnxDS1PortDbGain,
                tmnxDS1InsertSingleBitError,
                tmnxDS0ChanGroupAcctPolicyId,
                tmnxDS0ChanGroupCollectStats
            }
    STATUS     current
    DESCRIPTION
        "The group of objects supporting management of TDM type ports
         specific to the revision 5.0 on Alcatel-Lucent 7710 SR series systems."
    ::= { tmnxPortGroups 43 }

tmnxPortCemGroupV6v0   OBJECT-GROUP
    OBJECTS {
                tmnxDS3ChannelClockSyncState,
                tmnxDS3ChannelClockMasterPortId,
                tmnxDS1SignalMode,
                tmnxDS1ClockSyncState,
                tmnxDS1ClockMasterPortId,
                tmnxDS0ChanGroupPayloadFillType,
                tmnxDS0ChanGroupPayloadPattern,
                tmnxDS0ChanGroupSignalFillType,
                tmnxDS0ChanGroupSignalPattern
            }
    STATUS     current
    DESCRIPTION
        "The group of objects supporting management of CEM encapsulation TDM
         type ports specific to the Alcatel-Lucent 7750 and 7710 SR series 
         systems for revision 6.0."
    ::= { tmnxPortGroups 44 }

tmnxMcMlpppBundleGroup    OBJECT-GROUP
    OBJECTS {   tmnxBundleMlpppClassCount,
                tmnxBundleMlpppIngQoSProfId,
                tmnxBundleMlpppEgrQoSProfId,
                tmnxMcMlpppStatsIngressOct,
                tmnxMcMlpppStatsIngressPkt,
                tmnxMcMlpppStatsIngressErrPkt,
                tmnxMcMlpppStatsEgressOct,
                tmnxMcMlpppStatsEgressPkt,
                tmnxMcMlpppStatsEgressErrPkt
            }
    STATUS      current
    DESCRIPTION
        "The group of objects supporting management of MClass MLPPP BUNDLES
         for revision 6.0 on the Alcatel-Lucent SROS series systems."
    ::= { tmnxPortGroups 45 }

tmnxPortNotificationGroupV6v0 NOTIFICATION-GROUP
    NOTIFICATIONS   {   tmnxEqPortSonetAlarm,
                        tmnxEqPortSonetAlarmClear,
                        tmnxEqPortSonetPathAlarm,
                        tmnxEqPortSonetPathAlarmClear,
                        tmnxEqPortSFPInserted,
                        tmnxEqPortSFPRemoved,
                        tmnxEqPortError,
                        tmnxEqPortDS3Alarm,
                        tmnxEqPortDS3AlarmClear,
                        tmnxEqPortDS1Alarm,
                        tmnxEqPortDS1AlarmClear,
                        tmnxEqPortBndlYellowDiffExceeded,
                        tmnxEqPortBndlRedDiffExceeded,
                        tmnxEqPortBndlBadEndPtDiscr,
                        tmnxEqPortEtherAlarm,
                        tmnxEqPortEtherAlarmClear,
                        tmnxDS1E1LoopbackStarted,
                        tmnxDS1E1LoopbackStopped,
                        tmnxDS3E3LoopbackStarted,
                        tmnxDS3E3LoopbackStopped,
                        tmnxSonetSDHLoopbackStarted,
                        tmnxSonetSDHLoopbackStopped,
                        tmnxEqPortEtherLoopDetected,
                        tmnxEqPortEtherLoopCleared,
                        tmnxEqPortSpeedCfgNotCompatible,
                        tmnxEqPortDuplexCfgNotCompatible,
                        tmnxEqPortIngressRateCfgNotCompatible,
                        tmnxEqDigitalDiagMonitorFailure,
                        tmnxEqPortSFPStatusFailure,
                        tmnxDSXClockSyncStateChange
                    }
    STATUS        obsolete
    DESCRIPTION
        "The group of notifications supporting the management of physical
         ports for revision 6.0 on Alcatel-Lucent SROS series systems."
    ::= { tmnxPortGroups 46 }

tmnxPortEthernetV6v0Group       OBJECT-GROUP
    OBJECTS {  tmnxPortEtherMTU,
                tmnxPortEtherDuplex,
                tmnxPortEtherSpeed,
                tmnxPortEtherAutoNegotiate,
                tmnxPortEtherOperDuplex,
                tmnxPortEtherOperSpeed,
                tmnxPortEtherAcctPolicyId,
                tmnxPortEtherCollectStats,
                tmnxPortEtherMDIMDIX,
                tmnxPortEtherXGigMode,
                tmnxPortEtherEgressRate,
                tmnxPortEtherDot1qEtype,
                tmnxPortEtherQinqEtype,
                tmnxPortEtherIngressRate,
                tmnxPortEtherReportAlarm,
                tmnxPortEtherReportAlarmStatus,
                tmnxPortEtherPkts1519toMax,
                tmnxPortEtherHCOverPkts1519toMax,
                tmnxPortEtherHCPkts1519toMax,
                tmnxPortEtherLacpTunnel,
                tmnxPortEtherDownWhenLoopedEnabled,
                tmnxPortEtherDownWhenLoopedKeepAlive,
                tmnxPortEtherDownWhenLoopedRetry,
                tmnxPortEtherDownWhenLoopedState,
                tmnxPortEtherPBBEtype,
                tmnxPortEtherReasonDownFlags
            }
    STATUS      obsolete
    DESCRIPTION
        "The group of objects supporting management of Ethernet ports
         for revision 6.0 on Alcatel-Lucent SROS series systems."
    ::= { tmnxPortGroups 47 }

tmnxMlBundleGroupV6v0    OBJECT-GROUP
    OBJECTS {   tmnxBundleRowStatus,
                tmnxBundleType,
                tmnxBundleMinimumLinks,
                tmnxBundleNumLinks,
                tmnxBundleNumActiveLinks,
                tmnxBundleRedDiffDelay,
                tmnxBundleRedDiffDelayAction,
                tmnxBundleLastChangeTime,
                tmnxBundleFragmentThreshold,
                tmnxBundleUpTime,
                tmnxBundleMemberRowStatus,
                tmnxBundleMemberActive,
                tmnxBundleMemberDownReason,
                tmnxBundleMemberUpTime,
                tmnxBundleInputDiscards,
                tmnxBundlePrimaryMemberPortID,
                tmnxPortBundleNumber,
                tmnxBundleProtectedType,
                tmnxBundleParentBundle,
                tmnxBPGrpAssocWorkingBundleID,
                tmnxBPGrpAssocProtectBundleID,
                tmnxBPGrpAssocActiveBundleID
            }
    STATUS      current
    DESCRIPTION
        "The group of objects supporting management MLBUNDLES
         for revision 6.0 on the Alcatel-Lucent SROS series systems."
    ::= { tmnxPortGroups 48 }

tmnxMlpppBundleGroup    OBJECT-GROUP
    OBJECTS {
                tmnxBundleMlpppEndpointID,
                tmnxBundleMlpppEndpointIDClass,
                tmnxBundleYellowDiffDelay,
                tmnxBundleShortSequence,
                tmnxBundleMRRU,
                tmnxBundleOperMRRU,
                tmnxBundlePeerMRRU,
                tmnxBundleOperMTU,
                tmnxBundleLFI,
                tmnxBundleMlpppMagicNumber
            }
    STATUS      current
    DESCRIPTION
        "The group of objects supporting management of MLPPP Bundles
         on the Alcatel-Lucent SROS series systems."
    ::= { tmnxPortGroups 49 }

tmnxPortNotificationGroupV3v0 NOTIFICATION-GROUP
    NOTIFICATIONS   {   tmnxEqPortSonetAlarm,
                        tmnxEqPortSonetAlarmClear,
                        tmnxEqPortSonetPathAlarm,
                        tmnxEqPortSonetPathAlarmClear,
                        tmnxEqPortSFPInserted,
                        tmnxEqPortSFPRemoved,
                        tmnxEqPortSFPCorrupted,
                        tmnxEqPortError,
                        tmnxEqPortDS3Alarm,
                        tmnxEqPortDS3AlarmClear,
                        tmnxEqPortDS1Alarm,
                        tmnxEqPortDS1AlarmClear,
                        tmnxEqPortBndlYellowDiffExceeded,
                        tmnxEqPortBndlRedDiffExceeded,
                        tmnxEqPortBndlBadEndPtDiscr,
                        tmnxEqPortEtherAlarm,
                        tmnxEqPortEtherAlarmClear,
                        tmnxEqPortSpeedCfgNotCompatible,
                        tmnxEqPortDuplexCfgNotCompatible,
                        tmnxEqPortIngressRateCfgNotCompatible
                    }
    STATUS        obsolete
    DESCRIPTION
        "The group of notifications supporting the management of physical
         ports for revision 3.0 on Alcatel-Lucent SROS series systems."
    ::= { tmnxPortGroups 50 }


tmnxHsmdaGroupV6v0 OBJECT-GROUP
    OBJECTS   {
                  tmnxPortEgrHsmdaSchedPlcy,
                  tmnxHsmdaPortSchOvrTblLastChngd,
                  tmnxHsmdaPortSchOvrRowStatus,
                  tmnxHsmdaPortSchOvrLastChanged,
                  tmnxHsmdaPortSchOvrMaxRate,
                  tmnxHsmdaPortSchOvrGrp1Rate,
                  tmnxHsmdaPortSchOvrGrp2Rate,
                  tmnxHsmdaPortSchOvrClass1Rate,
                  tmnxHsmdaPortSchOvrClass1WtInGp,
                  tmnxHsmdaPortSchOvrClass2Rate,
                  tmnxHsmdaPortSchOvrClass2WtInGp,
                  tmnxHsmdaPortSchOvrClass3Rate,
                  tmnxHsmdaPortSchOvrClass3WtInGp,
                  tmnxHsmdaPortSchOvrClass4Rate,
                  tmnxHsmdaPortSchOvrClass4WtInGp,
                  tmnxHsmdaPortSchOvrClass5Rate,
                  tmnxHsmdaPortSchOvrClass5WtInGp,
                  tmnxHsmdaPortSchOvrClass6Rate,
                  tmnxHsmdaPortSchOvrClass6WtInGp,
                  tmnxHsmdaPortSchOvrClass7Rate,
                  tmnxHsmdaPortSchOvrClass7WtInGp,
                  tmnxHsmdaPortSchOvrClass8Rate,
                  tmnxHsmdaPortSchOvrClass8WtInGp,
                  tmnxPortEgrShaperTblLastChanged,
                  tmnxPortEgrShaperRowStatus,
                  tmnxPortEgrShaperLastChanged,
                  tmnxPortEgrShaperRate
              }
    STATUS        obsolete
    DESCRIPTION
        "The group of objects supporting the management of HSMDA
         ports for revision 6.0 on Alcatel-Lucent SROS series systems."
    ::= { tmnxPortGroups 51 }

tmnxPortTDMGroupV6v0    OBJECT-GROUP
    OBJECTS {   tmnxDS3ChannelAcctPolicyId,
                tmnxDS3ChannelCollectStats,
                tmnxDS3Buildout,
                tmnxDS3Type,
                tmnxDS3LastChangeTime,
                tmnxDS3ChannelRowStatus,
                tmnxDS3ChannelType,
                tmnxDS3ChannelFraming,
                tmnxDS3ChannelClockSource,
                tmnxDS3ChannelChannelized,
                tmnxDS3ChannelSubrateCSUMode,
                tmnxDS3ChannelSubrate,
                tmnxDS3ChannelIdleCycleFlags,
                tmnxDS3ChannelLoopback,
                tmnxDS3ChannelBitErrorInsertionRate,
                tmnxDS3ChannelBERTPattern,
                tmnxDS3ChannelBERTDuration,
                tmnxDS3ChannelMDLEicString,
                tmnxDS3ChannelMDLLicString,
                tmnxDS3ChannelMDLFicString,
                tmnxDS3ChannelMDLUnitString,
                tmnxDS3ChannelMDLPfiString,
                tmnxDS3ChannelMDLPortString,
                tmnxDS3ChannelMDLGenString,
                tmnxDS3ChannelMDLMessageType,
                tmnxDS3ChannelFEACLoopRespond,
                tmnxDS3ChannelCRC,
                tmnxDS3ChannelMTU,
                tmnxDS3ChannelOperMTU,
                tmnxDS3ChannelReportAlarm,
                tmnxDS3ChannelReportAlarmStatus,
                tmnxDS3ChannelLastChangeTime,
                tmnxDS3ChannelInFEACLoop,
                tmnxDS3ChannelMDLMonPortString,
                tmnxDS3ChannelMDLMonGenString,
                tmnxDS3ChannelBERTOperStatus,
                tmnxDS3ChannelBERTSynched,
                tmnxDS3ChannelBERTErrors,
                tmnxDS3ChannelBERTTotalBits,
                tmnxDS3ChannelScramble,
                tmnxDS1RowStatus,
                tmnxDS1Type,
                tmnxDS1Framing,
                tmnxDS1Loopback,
                tmnxDS1InvertData,
                tmnxDS1BitErrorInsertionRate,
                tmnxDS1BERTPattern,
                tmnxDS1BERTDuration,
                tmnxDS1ReportAlarm,
                tmnxDS1ReportAlarmStatus,
                tmnxDS1LastChangeTime,
                tmnxDS1ClockSource,
                tmnxDS1BERTOperStatus,
                tmnxDS1BERTSynched,
                tmnxDS1BERTErrors,
                tmnxDS1BERTTotalBits,
                tmnxDS1RemoteLoopRespond,
                tmnxDS1InRemoteLoop,
                tmnxDS1BerSdThreshold,
                tmnxDS1BerSfThreshold,
                tmnxDS0ChanGroupRowStatus,
                tmnxDS0ChanGroupTimeSlots,
                tmnxDS0ChanGroupSpeed,
                tmnxDS0ChanGroupCRC,
                tmnxDS0ChanGroupMTU,
                tmnxDS0ChanGroupOperMTU,
                tmnxDS0ChanGroupLastChangeTime,
                tmnxDS0ChanGroupIdleCycleFlags,
                tmnxDS0ChanGroupScramble
            }
    STATUS      obsolete
    DESCRIPTION
        "The group of objects supporting management of TDM type ports
         for version 6.0 on the Alcatel-Lucent SROS series systems."
    ::= { tmnxPortGroups 52 }

tmnxDigitalDiagMonitorGroup OBJECT-GROUP
    OBJECTS   {
                  tmnxDDMTemperature,
                  tmnxDDMTempLowWarning,
                  tmnxDDMTempLowAlarm,
                  tmnxDDMTempHiWarning,
                  tmnxDDMTempHiAlarm,
                  tmnxDDMSupplyVoltage,
                  tmnxDDMSupplyVoltageLowWarning,
                  tmnxDDMSupplyVoltageLowAlarm,
                  tmnxDDMSupplyVoltageHiWarning,
                  tmnxDDMSupplyVoltageHiAlarm,
                  tmnxDDMTxBiasCurrent,
                  tmnxDDMTxBiasCurrentLowWarning,
                  tmnxDDMTxBiasCurrentLowAlarm,
                  tmnxDDMTxBiasCurrentHiWarning,
                  tmnxDDMTxBiasCurrentHiAlarm,
                  tmnxDDMTxOutputPower,
                  tmnxDDMTxOutputPowerLowWarning,
                  tmnxDDMTxOutputPowerLowAlarm,
                  tmnxDDMTxOutputPowerHiWarning,
                  tmnxDDMTxOutputPowerHiAlarm,
                  tmnxDDMRxOpticalPower,
                  tmnxDDMRxOpticalPowerLowWarning,
                  tmnxDDMRxOpticalPowerLowAlarm,
                  tmnxDDMRxOpticalPowerHiWarning,
                  tmnxDDMRxOpticalPowerHiAlarm,
                  tmnxDDMRxOpticalPowerType,
                  tmnxDDMAux1,
                  tmnxDDMAux1LowWarning,
                  tmnxDDMAux1LowAlarm,
                  tmnxDDMAux1HiWarning,
                  tmnxDDMAux1HiAlarm,
                  tmnxDDMAux1Type,
                  tmnxDDMAux2,
                  tmnxDDMAux2LowWarning,
                  tmnxDDMAux2LowAlarm,
                  tmnxDDMAux2HiWarning,
                  tmnxDDMAux2HiAlarm,
                  tmnxDDMAux2Type,
                  tmnxDDMFailedThresholds,
                  tmnxDDMExternallyCalibrated,
                  tmnxDDMExtCalRxPower4,
                  tmnxDDMExtCalRxPower3,
                  tmnxDDMExtCalRxPower2,
                  tmnxDDMExtCalRxPower1,
                  tmnxDDMExtCalRxPower0,
                  tmnxDDMExtCalTxLaserBiasSlope,
                  tmnxDDMExtCalTxLaserBiasOffset,
                  tmnxDDMExtCalTxPowerSlope,
                  tmnxDDMExtCalTxPowerOffset,
                  tmnxDDMExtCalTemperatureSlope,
                  tmnxDDMExtCalTemperatureOffset,
                  tmnxDDMExtCalVoltageSlope,
                  tmnxDDMExtCalVoltageOffset
              }
    STATUS        current
    DESCRIPTION
        "The group of objects supporting the management of
         Digital Diagnostic Monitoring SFFs for revision 6.0 on
         Alcatel-Lucent SROS series systems."
    ::= { tmnxPortGroups 53 }

tmnxPortGroupV6v0   OBJECT-GROUP
    OBJECTS {   tmnxPortTableLastChange,
                tmnxPortLastChangeTime,
                tmnxPortType,
                tmnxPortClass,
                tmnxPortDescription,
                tmnxPortName,
                tmnxPortAlias,
                tmnxPortUserAssignedMac,
                tmnxPortMacAddress,
                tmnxPortHwMacAddress,
                tmnxPortMode,
                tmnxPortEncapType,
                tmnxPortLagId,
                tmnxPortHoldTimeUp,
                tmnxPortHoldTimeDown,
                tmnxPortUpProtocols,
                tmnxPortConnectorType,
                tmnxPortTransceiverType,
                tmnxPortTransceiverLaserWaveLen,
                tmnxPortTransceiverDiagCapable,
                tmnxPortTransceiverModelNumber,
                tmnxPortSFPConnectorCode,
                tmnxPortSFPVendorOUI,
                tmnxPortSFPVendorManufactureDate,
                tmnxPortSFPMedia,
                tmnxPortSFPEquipped,
                tmnxPortSFPVendorSerialNum,
                tmnxPortSFPVendorPartNum,
                tmnxPortEquipped,
                tmnxPortLinkStatus,
                tmnxPortAdminStatus,
                tmnxPortOperStatus,
                tmnxPortState,
                tmnxPortPrevState,
                tmnxPortNumAlarms,
                tmnxPortAlarmState,
                tmnxPortLastAlarmEvent,
                tmnxPortClearAlarms,
                tmnxPortLastStateChanged,
                tmnxPortNumChannels,
                tmnxPortNetworkEgrQueues,
                tmnxPortIsLeaf,
                tmnxPortChanType,
                tmnxPortParentPortID,
                tmnxPortLoadBalanceAlgorithm,
                tmnxPortTypeName,
                tmnxPortTypeDescription,
                tmnxPortTypeStatus,
                tmnxPortConnectTypeName,
                tmnxPortConnectTypeDescription,
                tmnxPortConnectTypeStatus,
                tmnxChannelPortID,
                tmnxPortOpticalCompliance,
                tmnxL4LoadBalancing,
                tmnxPortLastClearedTime,
                tmnxPortDDMEventSuppression,
                tmnxPortSFPStatus,
                tmnxPortReasonDownFlags
            }
    STATUS        obsolete
    DESCRIPTION
        "The group of objects supporting management of physical port
         capabilities for revision 6.0 on Alcatel-Lucent SROS series systems."
    ::= { tmnxPortGroups 54 }

tmnxNamedPoolGroupV6v0 OBJECT-GROUP
    OBJECTS {
                tmnxPortIngNamedPoolPlcy,
                tmnxPortEgrNamedPoolPlcy,
                tmnxPortIngPoolPercentRate,
                tmnxPortEgrPoolPercentRate
            }
    STATUS        current
    DESCRIPTION
        "The group of objects supporting the Named Pool feature
         for revision 6.0 on Alcatel-Lucent SROS series systems."
    ::= { tmnxPortGroups 55 }

tmnxPortEthernetV6v1Group       OBJECT-GROUP
    OBJECTS {   tmnxPortEtherMTU,
                tmnxPortEtherDuplex,
                tmnxPortEtherSpeed,
                tmnxPortEtherAutoNegotiate,
                tmnxPortEtherOperDuplex,
                tmnxPortEtherOperSpeed,
                tmnxPortEtherAcctPolicyId,
                tmnxPortEtherCollectStats,
                tmnxPortEtherMDIMDIX,
                tmnxPortEtherXGigMode,
                tmnxPortEtherEgressRate,
                tmnxPortEtherDot1qEtype,
                tmnxPortEtherQinqEtype,
                tmnxPortEtherIngressRate,
                tmnxPortEtherReportAlarm,
                tmnxPortEtherReportAlarmStatus,
                tmnxPortEtherPkts1519toMax,
                tmnxPortEtherHCOverPkts1519toMax,
                tmnxPortEtherHCPkts1519toMax,
                tmnxPortEtherLacpTunnel,
                tmnxPortEtherDownWhenLoopedEnabled,
                tmnxPortEtherDownWhenLoopedKeepAlive,
                tmnxPortEtherDownWhenLoopedRetry,
                tmnxPortEtherDownWhenLoopedState,
                tmnxPortEtherPBBEtype,
                tmnxPortEtherReasonDownFlags,
                tmnxPortEtherSingleFiber
            }
    STATUS      obsolete
    DESCRIPTION
        "The group of objects supporting management of Ethernet ports
         for revision 6.1 on Alcatel-Lucent SROS series systems."
    ::= { tmnxPortGroups 56 }

tmnxPortNotifyObjsGroupV6v0     OBJECT-GROUP
    OBJECTS {
                tmnxDDMFailedObject,
                tmnxDSXClockSyncStateObject
            }
    STATUS        current
    DESCRIPTION
        "The group of objects supporting physical port notifications
         for revision 6.0 on Alcatel-Lucent SROS series systems."
    ::= { tmnxPortGroups 57 }

tmnxPortQV7v0Group       OBJECT-GROUP
    OBJECTS {
        tPortAccEgrQGrpAggRateLimit,
        tPortAccEgrQGrpLastChgd,
        tPortAccEgrQGrpRowStatus,
        tPortAccEgrQGrpSchedPol,
        tPortAccEgrQGrpAcctgPolId,
        tPortAccEgrQGrpCollectStats,
        tPortAccEgrQGrpFrameBaseActg,
        tPortAccEgrQGrpTableLastChgd,
        tPortAccEgrQOverLastChanged,
        tPortAccEgrQOverRowStatus,
        tPortAccEgrQOverTableLastChgd,
        tPortAccEgrQOverAdminCIR,
        tPortAccEgrQOverAdminPIR,
        tPortAccEgrQOverCBS,
        tPortAccEgrQOverHiPrioOnly,
        tPortAccEgrQOverMBS,
        tPortAccIngQGrpLastChgd,
        tPortAccIngQGrpRowStatus,
        tPortAccIngQGrpSchedPol,
        tPortAccIngQGrpAcctgPolId,
        tPortAccIngQGrpCollectStats,
        tPortAccIngQGrpTableLastChgd,
        tPortAccIngQOverLastChanged,
        tPortAccIngQOverRowStatus,
        tPortAccIngQOverTableLastChgd,
        tPortAccIngQOverAdminCIR,
        tPortAccIngQOverAdminPIR,
        tPortAccIngQOverCBS,
        tPortAccIngQOverHiPrioOnly,
        tPortAccIngQOverMBS,
        tPortNetEgrQGrpAcctgPolId,
        tPortNetEgrQGrpAggRateLimit,
        tPortNetEgrQGrpCollectStats,
        tPortNetEgrQGrpFrameBaseActg,
        tPortNetEgrQGrpLastChgd,
        tPortNetEgrQGrpRowStatus,
        tPortNetEgrQGrpSchedPol,
        tPortNetEgrQGrpTableLastChgd,
        tPortNetEgrQOverAdminCIR,
        tPortNetEgrQOverAdminPIR,
        tPortNetEgrQOverCBS,
        tPortNetEgrQOverHiPrioOnly,
        tPortNetEgrQOverLastChanged,
        tPortNetEgrQOverMBS,
        tPortNetEgrQOverRowStatus,
        tPortNetEgrQOverTableLastChgd,
        tPortAccEgrQOverCIRAdaptation,
        tPortAccEgrQOverPIRAdaptation,
        tPortAccIngQOverCIRAdaptation,
        tPortAccIngQOverPIRAdaptation,
        tPortNetEgrQOverCIRAdaptation,
        tPortNetEgrQOverPIRAdaptation,
        tPortAccIngQGrpDescr,
        tPortAccEgrQGrpDescr,
        tPortNetEgrQGrpDescr
    }
    STATUS      obsolete
    DESCRIPTION
        "The group of objects supporting management of Ethernet ports
         for revision 7.0 on Alcatel-Lucent SROS series systems."
    ::= { tmnxPortGroups 58 }

tmnxMcMfrBundleGroup    OBJECT-GROUP
    OBJECTS {
        tmnxBundleMlfrBundleId,
        tmnxBundleMlfrIngQoSProfId,
        tmnxBundleMlfrEgrQoSProfId,
        tmnxBundleMlfrHelloTimer,
        tmnxBundleMlfrHelloRetryCount,
        tmnxBundleMlfrAckTimer,
        tmnxBundleMlfrLastChanged,
        tmnxBundleMemberMlfrDownReason
            }
    STATUS      current
    DESCRIPTION
        "The group of objects supporting management of MClass Mlfr Bundles
         for revision 7.0 on the Alcatel-Lucent SROS series systems."
    ::= { tmnxPortGroups 59 }

tmnxFrIntfGroup    OBJECT-GROUP
    OBJECTS {
        tmnxFrIntfFrf12Mode,
        tmnxFrIntfLinkId,
        tmnxFrIntfLastChanged
            }
    STATUS      current
    DESCRIPTION
        "The group of objects supporting management of Frame-Relay
         Interfaces for revision 7.0 on the Alcatel-Lucent SROS series systems."
    ::= { tmnxPortGroups 60 }

tmnxFrf12IntfGroup    OBJECT-GROUP
    OBJECTS {
        tmnxFrf12IntfFragmentThreshold,
        tmnxFrf12IntfEgrQoSProfId,
        tmnxFrf12IntfLastChanged
            }
    STATUS      current
    DESCRIPTION
        "The group of objects supporting management of Frame-Relay Frf12
         Interfaces for revision 7.0 on the Alcatel-Lucent SROS series systems."
    ::= { tmnxPortGroups 61 }

tmnxPortQStatV7v0Group       OBJECT-GROUP
    OBJECTS {
       tmnxPortEgrQosQStatDpdInProfOcts,
       tmnxPortEgrQosQStatDpdInProfPkts,
       tmnxPortEgrQosQStatDpdOutProfOcts,
       tmnxPortEgrQosQStatDpdOutProfPkts,
       tmnxPortEgrQosQStatFwdInProfOcts,
       tmnxPortEgrQosQStatFwdInProfPkts,
       tmnxPortEgrQosQStatFwdOutProfOcts,
       tmnxPortEgrQosQStatFwdOutProfPkts,
       tmnxPortIngQosQStatDpdHiPrioOcts,
       tmnxPortIngQosQStatDpdHiPrioPkts,
       tmnxPortIngQosQStatDpdLoPrioOcts,
       tmnxPortIngQosQStatDpdLoPrioPkts,
       tmnxPortIngQosQStatFwdInProfOcts,
       tmnxPortIngQosQStatFwdInProfPkts,
       tmnxPortIngQosQStatFwdOutProfOcts,
       tmnxPortIngQosQStatFwdOutProfPkts,
       tmnxPortIngQosQStatOffHiPrioOcts,
       tmnxPortIngQosQStatOffHiPrioPkts,
       tmnxPortIngQosQStatOffLoPrioOcts,
       tmnxPortIngQosQStatOffLoPrioPkts,
       tmnxPortIngQosQStatUncolOctsOff,
       tmnxPortIngQosQStatUncolPktsOff,
       tmnxPortNetEgrQDroInProfOcts,
       tmnxPortNetEgrQDroInProfPkts,
       tmnxPortNetEgrQDroOutProfOcts,
       tmnxPortNetEgrQDroOutProfPkts,
       tmnxPortNetEgrQFwdInProfOcts,
       tmnxPortNetEgrQFwdInProfPkts,
       tmnxPortNetEgrQFwdOutProfOcts,
       tmnxPortNetEgrQFwdOutProfPkts
    }
    STATUS      current
    DESCRIPTION
        "The group of objects supporting management of ethernet port
         queue group statistics on the Alcatel-Lucent SROS series systems."
    ::= { tmnxPortGroups 62 }

tmnxPortEthernetV7v0Group       OBJECT-GROUP
    OBJECTS {   tmnxPortEtherMTU,
                tmnxPortEtherDuplex,
                tmnxPortEtherSpeed,
                tmnxPortEtherAutoNegotiate,
                tmnxPortEtherOperDuplex,
                tmnxPortEtherOperSpeed,
                tmnxPortEtherAcctPolicyId,
                tmnxPortEtherCollectStats,
                tmnxPortEtherMDIMDIX,
                tmnxPortEtherXGigMode,
                tmnxPortEtherEgressRate,
                tmnxPortEtherDot1qEtype,
                tmnxPortEtherQinqEtype,
                tmnxPortEtherIngressRate,
                tmnxPortEtherReportAlarm,
                tmnxPortEtherReportAlarmStatus,
                tmnxPortEtherPkts1519toMax,
                tmnxPortEtherHCOverPkts1519toMax,
                tmnxPortEtherHCPkts1519toMax,
                tmnxPortEtherLacpTunnel,
                tmnxPortEtherDownWhenLoopedEnabled,
                tmnxPortEtherDownWhenLoopedKeepAlive,
                tmnxPortEtherDownWhenLoopedRetry,
                tmnxPortEtherDownWhenLoopedState,
                tmnxPortEtherPBBEtype,
                tmnxPortEtherSingleFiber,
                tmnxPortEtherSSM,
                tmnxPortEtherDWLUseBroadcastAddr
            }
    STATUS      current
    DESCRIPTION
        "The group of objects supporting management of Ethernet ports
         for revision 7.0 on Alcatel-Lucent SROS series systems."
    ::= { tmnxPortGroups 63 }

tmnxPortGroupV7v0   OBJECT-GROUP
    OBJECTS {   tmnxPortTableLastChange,
                tmnxPortLastChangeTime,
                tmnxPortType,
                tmnxPortClass,
                tmnxPortDescription,
                tmnxPortName,
                tmnxPortAlias,
                tmnxPortUserAssignedMac,
                tmnxPortMacAddress,
                tmnxPortHwMacAddress,
                tmnxPortMode,
                tmnxPortEncapType,
                tmnxPortLagId,
                tmnxPortHoldTimeUp,
                tmnxPortHoldTimeDown,
                tmnxPortUpProtocols,
                tmnxPortConnectorType,
                tmnxPortTransceiverType,
                tmnxPortTransceiverLaserWaveLen,
                tmnxPortTransceiverDiagCapable,
                tmnxPortTransceiverModelNumber,
                tmnxPortSFPConnectorCode,
                tmnxPortSFPVendorOUI,
                tmnxPortSFPVendorManufactureDate,
                tmnxPortSFPMedia,
                tmnxPortSFPEquipped,
                tmnxPortSFPVendorSerialNum,
                tmnxPortSFPVendorPartNum,
                tmnxPortEquipped,
                tmnxPortLinkStatus,
                tmnxPortAdminStatus,
                tmnxPortOperStatus,
                tmnxPortState,
                tmnxPortPrevState,
                tmnxPortNumAlarms,
                tmnxPortAlarmState,
                tmnxPortLastAlarmEvent,
                tmnxPortClearAlarms,
                tmnxPortLastStateChanged,
                tmnxPortNumChannels,
                tmnxPortNetworkEgrQueues,
                tmnxPortIsLeaf,
                tmnxPortChanType,
                tmnxPortParentPortID,
                tmnxPortLoadBalanceAlgorithm,
                tmnxPortTypeName,
                tmnxPortTypeDescription,
                tmnxPortTypeStatus,
                tmnxPortConnectTypeName,
                tmnxPortConnectTypeDescription,
                tmnxPortConnectTypeStatus,
                tmnxChannelPortID,
                tmnxPortOpticalCompliance,
                tmnxL4LoadBalancing,
                tmnxLsrIpLoadBalancing,
                tmnxPortLastClearedTime,
                tmnxPortDDMEventSuppression,
                tmnxPortSFPStatus,
                tmnxPortReasonDownFlags,
                tmnxPortSSMRxQualityLevel,
                tmnxPortDwdmLaserChannel,
                tmnxPortOtuCapable,
                tmnxSonetSuppressLoOrderAlarm
            }
    STATUS        current
    DESCRIPTION
        "The group of objects supporting management of physical port
         capabilities for revision 7.0 on Alcatel-Lucent SROS series systems."
    ::= { tmnxPortGroups 64 }

tmnxPortNotifyObjsGroupV7v0     OBJECT-GROUP
    OBJECTS {   tmnxPortNotifyDescription
            }
    STATUS        current
    DESCRIPTION
        "The group of objects supporting physical port notifications
         for revision 7.0 on Alcatel 7xxx series systems."
    ::= { tmnxPortGroups 65 }

tmnxPortNotificationGroupV7v0 NOTIFICATION-GROUP
    NOTIFICATIONS   {   tmnxEqPortSonetAlarm,
                        tmnxEqPortSonetAlarmClear,
                        tmnxEqPortSonetPathAlarm,
                        tmnxEqPortSonetPathAlarmClear,
                        tmnxEqPortSFPInserted,
                        tmnxEqPortSFPRemoved,
                        tmnxEqPortError,
                        tmnxEqPortDS3Alarm,
                        tmnxEqPortDS3AlarmClear,
                        tmnxEqPortDS1Alarm,
                        tmnxEqPortDS1AlarmClear,
                        tmnxEqPortBndlYellowDiffExceeded,
                        tmnxEqPortBndlRedDiffExceeded,
                        tmnxEqPortBndlBadEndPtDiscr,
                        tmnxEqPortEtherAlarm,
                        tmnxEqPortEtherAlarmClear,
                        tmnxDS1E1LoopbackStarted,
                        tmnxDS1E1LoopbackStopped,
                        tmnxDS3E3LoopbackStarted,
                        tmnxDS3E3LoopbackStopped,
                        tmnxSonetSDHLoopbackStarted,
                        tmnxSonetSDHLoopbackStopped,
                        tmnxEqPortEtherLoopDetected,
                        tmnxEqPortEtherLoopCleared,
                        tmnxEqPortSpeedCfgNotCompatible,
                        tmnxEqPortDuplexCfgNotCompatible,
                        tmnxEqPortIngressRateCfgNotCompatible,
                        tmnxEqDigitalDiagMonitorFailure,
                        tmnxEqPortSFPStatusFailure,
                        tmnxDSXClockSyncStateChange,
                        tmnxPortUnsupportedFunction,
                        tmnxBundleMemberMlfrLoopback,
                        tmnxEqPortWaveTrackerAlarm
            }
    STATUS        obsolete
    DESCRIPTION
        "The group of notifications supporting the management of physical
         ports for revision 7.0 on Alcatel-Lucent SROS series systems."
    ::= { tmnxPortGroups 66 }

tmnxPortEtherObsoleteV7v0Group  OBJECT-GROUP
    OBJECTS {   tmnxPortEtherReasonDownFlags
            }
    STATUS      current
    DESCRIPTION
        "The objects which were obsoleted for revision 7.0 on Alcatel-Lucent
         SROS series systems."
    ::= { tmnxPortGroups 67 }

tmnxPortTDMGroupV7v0    OBJECT-GROUP
    OBJECTS {   tmnxDS3ChannelAcctPolicyId,
                tmnxDS3ChannelCollectStats,
                tmnxDS3Buildout,
                tmnxDS3Type,
                tmnxDS3LastChangeTime,
                tmnxDS3ChannelRowStatus,
                tmnxDS3ChannelType,
                tmnxDS3ChannelFraming,
                tmnxDS3ChannelClockSource,
                tmnxDS3ChannelChannelized,
                tmnxDS3ChannelSubrateCSUMode,
                tmnxDS3ChannelSubrate,
                tmnxDS3ChannelIdleCycleFlags,
                tmnxDS3ChannelLoopback,
                tmnxDS3ChannelBitErrorInsertionRate,
                tmnxDS3ChannelBERTPattern,
                tmnxDS3ChannelBERTDuration,
                tmnxDS3ChannelMDLEicString,
                tmnxDS3ChannelMDLLicString,
                tmnxDS3ChannelMDLFicString,
                tmnxDS3ChannelMDLUnitString,
                tmnxDS3ChannelMDLPfiString,
                tmnxDS3ChannelMDLPortString,
                tmnxDS3ChannelMDLGenString,
                tmnxDS3ChannelMDLMessageType,
                tmnxDS3ChannelFEACLoopRespond,
                tmnxDS3ChannelCRC,
                tmnxDS3ChannelMTU,
                tmnxDS3ChannelOperMTU,
                tmnxDS3ChannelReportAlarm,
                tmnxDS3ChannelReportAlarmStatus,
                tmnxDS3ChannelLastChangeTime,
                tmnxDS3ChannelInFEACLoop,
                tmnxDS3ChannelMDLMonPortString,
                tmnxDS3ChannelMDLMonGenString,
                tmnxDS3ChannelBERTOperStatus,
                tmnxDS3ChannelBERTSynched,
                tmnxDS3ChannelBERTErrors,
                tmnxDS3ChannelBERTTotalBits,
                tmnxDS3ChannelScramble,
                tmnxDS1RowStatus,
                tmnxDS1Type,
                tmnxDS1Framing,
                tmnxDS1Loopback,
                tmnxDS1InvertData,
                tmnxDS1BitErrorInsertionRate,
                tmnxDS1BERTPattern,
                tmnxDS1BERTDuration,
                tmnxDS1ReportAlarm,
                tmnxDS1ReportAlarmStatus,
                tmnxDS1LastChangeTime,
                tmnxDS1ClockSource,
                tmnxDS1BERTOperStatus,
                tmnxDS1BERTSynched,
                tmnxDS1BERTErrors,
                tmnxDS1BERTTotalBits,
                tmnxDS1RemoteLoopRespond,
                tmnxDS1InRemoteLoop,
                tmnxDS1BerSdThreshold,
                tmnxDS1BerSfThreshold,
                tmnxDS0ChanGroupRowStatus,
                tmnxDS0ChanGroupTimeSlots,
                tmnxDS0ChanGroupSpeed,
                tmnxDS0ChanGroupCRC,
                tmnxDS0ChanGroupMTU,
                tmnxDS0ChanGroupOperMTU,
                tmnxDS0ChanGroupLastChangeTime,
                tmnxDS0ChanGroupIdleCycleFlags,
                tmnxDS0ChanGroupScramble,
                tmnxDS0ChanGroupBerSfLinkDown
            }
    STATUS      current
    DESCRIPTION
        "The group of objects supporting management of TDM type ports
         for version 6.0 on the Alcatel-Lucent SROS series systems."
    ::= { tmnxPortGroups 68 }

tmnxPortTDME1GroupV6v1    OBJECT-GROUP
    OBJECTS {  tmnxDS1NationalUseBits
            }
    STATUS      current
    DESCRIPTION
        "The group of objects supporting management of TDM E1 type ports
         for version 6.1 on the Alcatel-Lucent SROS series systems."
    ::= { tmnxPortGroups 69 }


tmnxPortNotifyObjsGroupV8v0     OBJECT-GROUP
    OBJECTS {   tmnxPortNotifyWTAlarmReason,
                tmnxHostMatchNotifyIntDestId,
                tmnxHostMatchNotifyOrgString,
                tmnxHostMatchNotifySubIdent
            }
    STATUS        current
    DESCRIPTION
        "The group of objects supporting physical port notifications
         for revision 8.0 on Alcatel-Lucent SROS series systems."
    ::= { tmnxPortGroups 70 }

tmnxWaveTrackerGroup             OBJECT-GROUP
    OBJECTS {
                tmnxPortWaveTrackerCapable,
                tmnxWaveTrackerAlarmState,
                tmnxWaveTrackerCfgAlarms,
                tmnxWaveTrackerEncodeEnable,
                tmnxWaveTrackerInUse,
                tmnxWaveTrackerLowerPowerMargin,
                tmnxWaveTrackerMaxAttainablePwr,
                tmnxWaveTrackerMeasuredPower,
                tmnxWaveTrackerMinAttainablePwr,
                tmnxWaveTrackerPowerCtrlEnable,
                tmnxWaveTrackerTargetPower,
                tmnxWaveTrackerTrailName,
                tmnxWaveTrackerUpperPowerMargin,
                tmnxWaveTrackerWaveKey1,
                tmnxWaveTrackerWaveKey2
            }
    STATUS      current
    DESCRIPTION
        "The group of objects supporting management of Wave Tracker
         for version 8.0 on the Alcatel-Lucent SROS series systems."
    ::= { tmnxPortGroups 71 }

tmnxPortGroupV8v0                OBJECT-GROUP
    OBJECTS {
                tmnxPortHybridIngAccessWeight,
                tmnxPortHybridIngNetworkWeight,
                tmnxPortHybridEgrAccessWeight,
                tmnxPortHybridEgrNetworkWeight,
                tmnxPortInterfaceGroupHandlerIdx,
                tmnxPortEtherSSMCodeType,
                tmnxPortEtherSSMTxDus,
                tmnxSonetTxDus,
                tPortAccIngQOverMBSBytes,
                tPortAccEgrQOverMBSBytes,
                tPortNetEgrQOverMBSBytes,
                tPortNetEgrQOverAdminPIRPercent,
                tPortNetEgrQOverAdminCIRPercent,
                tPortNetEgrQOverRateType,
                tPortAccEgrQOverAdminPIRPercent,
                tPortAccEgrQOverAdminCIRPercent,
                tPortAccEgrQOverRateType,
                tPortAccEgrQGrpHMTableLastChgd,
                tPortAccEgrQGrpHMRowStatus,
                tPortAccEgrQGrpHMLastChgd,
                tmnxPortHoldTimeUnits,
                tPortEgrVPortHMRowStatus,
                tPortEgrVPortHMLastChgd,
                tmnxSonetTxS1Byte,
                tmnxPortEtherSSMRxEsmc,
                tmnxPortEtherSSMTxQualityLevel
            }
    STATUS      current
    DESCRIPTION
        "The group of objects added in revision 8.0 Alcatel-Lucent SROS series
         systems for port management."
    ::= { tmnxPortGroups 72 }

tmnxPortDwdmGroup                OBJECT-GROUP
    OBJECTS {
                tmnxPortDwdmLaserChannel,
                tmnxPortDwdmRxDtvAdjustEnable,
                tmnxPortDwdmRxDtvDacPercent
            }
    STATUS      current
    DESCRIPTION
        "The group of objects supporting management of DWDM
         for version 8.0 on the Alcatel-Lucent SROS series systems."
    ::= { tmnxPortGroups 73 }

tmnxPortATMGroupV7v0     OBJECT-GROUP
    OBJECTS {
                tmnxATMIntfCellFormat,
                tmnxATMIntfMinVpValue,
                tmnxATMIntfMapping,
                tmnxATMIntfCustomBufferMode,
                tmnxATMIntfBufferPool,
                tmnxATMIntfVcThreshold
            }
    STATUS      current
    DESCRIPTION
        "The group of objects supporting management of ATM interfaces
         for version 7.0 on Alcatel-Lucent SROS series systems."
    ::= { tmnxPortGroups 74 }

tmnxPortCEMGroupV8v0             OBJECT-GROUP
    OBJECTS {
                tmnxPortCemStatsReportAlarm,
                tmnxPortCemStatsIgrForwardedPkts,
                tmnxPortCemStatsIgrDroppedPkts,
                tmnxPortCemStatsEgrForwardedPkts,
                tmnxPortCemStatsEgrDroppedPkts,
                tmnxPortCemStatsEgrMissingPkts,
                tmnxPortCemStatsEgrPktsReOrder,
                tmnxPortCemStatsEgrJtrBfrURun,
                tmnxPortCemStatsEgrJtrBfrORun,
                tmnxPortCemStatsEgrMisOrderDrop,
                tmnxPortCemStatsEgrMalformedPkts,
                tmnxPortCemStatsEgrLBitDrop,
                tmnxPortCemStatsEgrMultipleDrop,
                tmnxPortCemStatsEgrESs,
                tmnxPortCemStatsEgrSESs,
                tmnxPortCemStatsEgrUASs,
                tmnxPortCemStatsEgrFailureCounts,
                tmnxPortCemStatsEgrURunCounts,
                tmnxPortCemStatsEgrORunCounts,
                tmnxPortCemStatsEgrJtrBfrDepth
            }
    STATUS      current
    DESCRIPTION
        "The group of objects supporting management of Circuit EMulation (CEM)
         interfaces for version 8.0 on Alcatel-Lucent SROS series systems."
    ::= { tmnxPortGroups 75 }

tmnxPortQV8v0Group       OBJECT-GROUP
    OBJECTS {
        tPortAccEgrQGrpAggRateLimit,
        tPortAccEgrQGrpLastChgd,
        tPortAccEgrQGrpRowStatus,
        tPortAccEgrQGrpSchedPol,
        tPortAccEgrQGrpAcctgPolId,
        tPortAccEgrQGrpCollectStats,
        tPortAccEgrQGrpFrameBaseActg,
        tPortAccEgrQGrpTableLastChgd,
        tPortAccEgrQOverLastChanged,
        tPortAccEgrQOverRowStatus,
        tPortAccEgrQOverTableLastChgd,
        tPortAccEgrQOverAdminCIR,
        tPortAccEgrQOverAdminPIR,
        tPortAccEgrQOverCBS,
        tPortAccEgrQOverHiPrioOnly,
        tPortAccIngQGrpLastChgd,
        tPortAccIngQGrpRowStatus,
        tPortAccIngQGrpSchedPol,
        tPortAccIngQGrpAcctgPolId,
        tPortAccIngQGrpCollectStats,
        tPortAccIngQGrpTableLastChgd,
        tPortAccIngQOverLastChanged,
        tPortAccIngQOverRowStatus,
        tPortAccIngQOverTableLastChgd,
        tPortAccIngQOverAdminCIR,
        tPortAccIngQOverAdminPIR,
        tPortAccIngQOverCBS,
        tPortAccIngQOverHiPrioOnly,
        tPortNetEgrQGrpAcctgPolId,
        tPortNetEgrQGrpAggRateLimit,
        tPortNetEgrQGrpCollectStats,
        tPortNetEgrQGrpFrameBaseActg,
        tPortNetEgrQGrpLastChgd,
        tPortNetEgrQGrpRowStatus,
        tPortNetEgrQGrpSchedPol,
        tPortNetEgrQGrpTableLastChgd,
        tPortNetEgrQOverAdminCIR,
        tPortNetEgrQOverAdminPIR,
        tPortNetEgrQOverCBS,
        tPortNetEgrQOverHiPrioOnly,
        tPortNetEgrQOverLastChanged,
        tPortNetEgrQOverRowStatus,
        tPortNetEgrQOverTableLastChgd,
        tPortAccEgrQOverCIRAdaptation,
        tPortAccEgrQOverPIRAdaptation,
        tPortAccIngQOverCIRAdaptation,
        tPortAccIngQOverPIRAdaptation,
        tPortNetEgrQOverCIRAdaptation,
        tPortNetEgrQOverPIRAdaptation,
        tPortAccIngQGrpDescr,
        tPortAccEgrQGrpDescr,
        tPortNetEgrQGrpDescr
    }
    STATUS      current
    DESCRIPTION
        "The group of objects supporting management of Ethernet ports
         for revision 8.0 on Alcatel-Lucent SROS series systems."
    ::= { tmnxPortGroups 76 }

tmnxPortQObsoleteV8v0Group  OBJECT-GROUP
    OBJECTS {   
        tPortAccEgrQOverMBS,
        tPortAccIngQOverMBS,
        tPortNetEgrQOverMBS
    }
    STATUS      current
    DESCRIPTION
        "The objects which were obsoleted for revision 8.0 on Alcatel-Lucent
         SROS series systems."
    ::= { tmnxPortGroups 77 }

tmnxPortNotificationGroupV8v0 NOTIFICATION-GROUP
    NOTIFICATIONS   {   tmnxEqPortSonetAlarm,
                        tmnxEqPortSonetAlarmClear,
                        tmnxEqPortSonetPathAlarm,
                        tmnxEqPortSonetPathAlarmClear,
                        tmnxEqPortSFPInserted,
                        tmnxEqPortSFPRemoved,
                        tmnxEqPortError,
                        tmnxEqPortDS3Alarm,
                        tmnxEqPortDS3AlarmClear,
                        tmnxEqPortDS1Alarm,
                        tmnxEqPortDS1AlarmClear,
                        tmnxEqPortBndlYellowDiffExceeded,
                        tmnxEqPortBndlRedDiffExceeded,
                        tmnxEqPortBndlBadEndPtDiscr,
                        tmnxEqPortEtherAlarm,
                        tmnxEqPortEtherAlarmClear,
                        tmnxDS1E1LoopbackStarted,
                        tmnxDS1E1LoopbackStopped,
                        tmnxDS3E3LoopbackStarted,
                        tmnxDS3E3LoopbackStopped,
                        tmnxSonetSDHLoopbackStarted,
                        tmnxSonetSDHLoopbackStopped,
                        tmnxEqPortEtherLoopDetected,
                        tmnxEqPortEtherLoopCleared,
                        tmnxEqPortSpeedCfgNotCompatible,
                        tmnxEqPortDuplexCfgNotCompatible,
                        tmnxEqPortIngressRateCfgNotCompatible,
                        tmnxEqDigitalDiagMonitorFailure,
                        tmnxEqPortSFPStatusFailure,
                        tmnxDSXClockSyncStateChange,
                        tmnxPortUnsupportedFunction,
                        tmnxBundleMemberMlfrLoopback,
                        tmnxEqPortWaveTrackerAlarm,
                        tPortAccEgrQGrpHostMatchFailure,
                        tPortEgrVPortHostMatchFailure,
                        tmnxEqDigitalDiagMonitorClear,
                        tmnxEqPortOpticalAmpAlarm,
                        tmnxEqPortOpticalTdcmAlarm
            }
    STATUS        current
    DESCRIPTION
        "The group of notifications supporting the management of physical
         ports for revision 8.0 on Alcatel-Lucent SROS series systems."
    ::= { tmnxPortGroups 78 }

tmnxPortSchedStatsGroup       OBJECT-GROUP
    OBJECTS {
        tPortAccEgrSchedStatFwdOcts, 
        tPortAccEgrSchedStatFwdPkts, 
        tPortAccIngSchedStatFwdOcts, 
        tPortAccIngSchedStatFwdPkts, 
        tPortNetEgrSchedStatFwdOcts, 
        tPortNetEgrSchedStatFwdPkts,
        tPortAccEgrSchedStatFwdOctsHi,
        tPortAccEgrSchedStatFwdOctsLo,
        tPortAccEgrSchedStatFwdPktsHi,
        tPortAccEgrSchedStatFwdPktsLo,
        tPortAccIngSchedStatFwdOctsHi,
        tPortAccIngSchedStatFwdOctsLo,
        tPortAccIngSchedStatFwdPktsHi,
        tPortAccIngSchedStatFwdPktsLo,
        tPortNetEgrSchedStatFwdOctsHi,
        tPortNetEgrSchedStatFwdOctsLo,
        tPortNetEgrSchedStatFwdPktsHi,
        tPortNetEgrSchedStatFwdPktsLo
    }
    STATUS        current
    DESCRIPTION
        "The group of objects supporting the scheduler queue-group statistics
        per port for revision 7.0 on Alcatel-Lucent SROS series systems."
    ::= { tmnxPortGroups 79 }

tmnxPortVPortGroup       OBJECT-GROUP
    OBJECTS {
       tPortEgrVPortDescr, 
       tPortEgrVPortLastChanged, 
       tPortEgrVPortRowStatus, 
       tPortEgrVPortSchedPol, 
       tPortEgrVPortTableLastChgd,
       tPortEgrVPortHMTableLastChgd
    }
    STATUS        obsolete
    DESCRIPTION
        "The group of objects supporting the virtual port related objects
        for revision 8.0 on Alcatel-Lucent SROS series systems."
    ::= { tmnxPortGroups 80 }

tmnxMlpppBundleGroupV7v0    OBJECT-GROUP
    OBJECTS {
                tmnxBundleMlpppStatelessApsSwo
            }
    STATUS      current
    DESCRIPTION
        "The group of additional objects supporting management of MLPPP Bundles
         for revision 7.0 on Alcatel-Lucent SROS series systems."
    ::= { tmnxPortGroups 81 }

tmnxOpticalPortGroup          OBJECT-GROUP
    OBJECTS {
                tmnxOpticalPortAmpCfgAlarms,     
                tmnxOpticalPortTdcmCtrlMode,  
                tmnxOpticalPortTdcmManCfgDisp,
                tmnxOpticalPortTdcmCfgRxChan, 
                tmnxOpticalPortTdcmCfgAlarms,    
                tmnxOpticalPortHasRxAmplifier,   
                tmnxOpticalPortHasRxTdcm,        
                tmnxOpticalPortAmpPowerIn,       
                tmnxOpticalPortAmpGain,          
                tmnxOpticalPortAmpPowerOut,      
                tmnxOpticalPortAmpPumpTemp,      
                tmnxOpticalPortAmpModuleTemp,    
                tmnxOpticalPortAmpPumpCurrent,   
                tmnxOpticalPortAmpAlarmState,    
                tmnxOpticalPortAmpSerialNum,  
                tmnxOpticalPortAmpCtrlState,     
                tmnxOpticalPortTdcmPowerIn,      
                tmnxOpticalPortTdcmLoss,         
                tmnxOpticalPortTdcmPowerOut,     
                tmnxOpticalPortTdcmRtd1Temp,     
                tmnxOpticalPortTdcmRtd2Temp,     
                tmnxOpticalPortTdcmRtd3Temp,     
                tmnxOpticalPortTdcmRtd4Temp,     
                tmnxOpticalPortTdcmModuleTemp,   
                tmnxOpticalPortTdcmMinDisp,      
                tmnxOpticalPortTdcmMaxDisp,      
                tmnxOpticalPortTdcmAutoDisp,     
                tmnxOpticalPortTdcmMeasDisp,     
                tmnxOpticalPortTdcmPresRxChan,
                tmnxOpticalPortTdcmAlarmState,   
                tmnxOpticalPortTdcmSerialNum, 
                tmnxOpticalPortTdcmCtrlState,
                tmnxOpticalPortTdcmDispSwpStart,
                tmnxOpticalPortTdcmDispSwpEnd
            }
    STATUS      current
    DESCRIPTION
        "The group of objects supporting management of Optical Port
         for version 8.0 on the Alcatel-Lucent SROS series systems."
    ::= { tmnxPortGroups 82 }

tmnxPortATMGroupV9v0     OBJECT-GROUP
    OBJECTS {
             tmnxPortATMVpShaperTblLastCh,
             tmnxPortATMVpShaperRowStatus,
             tmnxPortATMVpShaperLastMgmtCh,
             tmnxPortATMVpShaperEgrAtd
            }
    STATUS      current
    DESCRIPTION
        "The group of objects supporting management of ATM interfaces
         added in release 9.0 on Alcatel-Lucent SROS series systems."
    ::= { tmnxPortGroups 90 }

tmnxPortVPortV9v0Group       OBJECT-GROUP
    OBJECTS {
       tPortEgrVPortDescr, 
       tPortEgrVPortLastChanged, 
       tPortEgrVPortRowStatus, 
       tPortEgrVPortSchedPol, 
       tPortEgrVPortTableLastChgd,
       tPortEgrVPortHMTableLastChgd,
       tPortEgrVPortAggRateLimit
    }
    STATUS        current
    DESCRIPTION
        "The group of objects supporting the virtual port related objects
        for revision 9.0 on Alcatel-Lucent SROS series systems."
    ::= { tmnxPortGroups 91 }

tmnxPortEgrExpShaperV9v0Group       OBJECT-GROUP
    OBJECTS {
        tmnxPortEgrExpShaperTblLastChngd,
        tmnxPortEgrExpShaperRowStatus,         
        tmnxPortEgrExpShaperRate,
        tmnxPortEgrExpShaperClass1Rate,
        tmnxPortEgrExpShaperClass2Rate,
        tmnxPortEgrExpShaperClass3Rate,
        tmnxPortEgrExpShaperClass4Rate,
        tmnxPortEgrExpShaperClass5Rate,
        tmnxPortEgrExpShaperClass6Rate,
        tmnxPortEgrExpShaperClass7Rate,
        tmnxPortEgrExpShaperClass8Rate,
        tmnxPortEgrExpShaperLastChanged,
        tmnxPortEgrExpShaperClass1Thresh, 
        tmnxPortEgrExpShaperClass2Thresh, 
        tmnxPortEgrExpShaperClass3Thresh, 
        tmnxPortEgrExpShaperClass4Thresh, 
        tmnxPortEgrExpShaperClass5Thresh, 
        tmnxPortEgrExpShaperClass6Thresh, 
        tmnxPortEgrExpShaperClass7Thresh, 
        tmnxPortEgrExpShaperClass8Thresh, 
        tmnxPortEgrExpShaperLoBrstMaxCls, 
        tPortEgrExpShaperCls1StFwdPkts,
        tPortEgrExpShaperCls1StFwdOcts,
        tPortEgrExpShaperCls1StMonOvrOct,
        tPortEgrExpShaperCls2StFwdPkts,
        tPortEgrExpShaperCls2StFwdOcts,
        tPortEgrExpShaperCls2StMonOvrOct,
        tPortEgrExpShaperCls3StFwdPkts,
        tPortEgrExpShaperCls3StFwdOcts,
        tPortEgrExpShaperCls3StMonOvrOct,
        tPortEgrExpShaperCls4StFwdPkts,
        tPortEgrExpShaperCls4StFwdOcts,
        tPortEgrExpShaperCls4StMonOvrOct,
        tPortEgrExpShaperCls5StFwdPkts,
        tPortEgrExpShaperCls5StFwdOcts,
        tPortEgrExpShaperCls5StMonOvrOct,
        tPortEgrExpShaperCls6StFwdPkts,
        tPortEgrExpShaperCls6StFwdOcts,
        tPortEgrExpShaperCls6StMonOvrOct,
        tPortEgrExpShaperCls7StFwdPkts,
        tPortEgrExpShaperCls7StFwdOcts,
        tPortEgrExpShaperCls7StMonOvrOct,
        tPortEgrExpShaperCls8StFwdPkts,
        tPortEgrExpShaperCls8StFwdOcts,
        tPortEgrExpShaperCls8StMonOvrOct,
        tPortEgrExpShaperAggStFwdPkts,
        tPortEgrExpShaperAggStFwdOcts,
        tPortEgrExpShaperAggStMonOvrOct,
        tPortEgrExpShaperStLstClrdTime,
        tPortEgrExpShaperCls1StFwdPktsH,
        tPortEgrExpShaperCls1StFwdPktsL,
        tPortEgrExpShaperCls1StFwdOctsH,
        tPortEgrExpShaperCls1StFwdOctsL,
        tPortEgrExpShaperCls1StMonOvrOL,
        tPortEgrExpShaperCls1StMonOvrOH,
        tPortEgrExpShaperCls2StFwdPktsL,
        tPortEgrExpShaperCls2StFwdPktsH,
        tPortEgrExpShaperCls2StFwdOctsH,
        tPortEgrExpShaperCls2StFwdOctsL,
        tPortEgrExpShaperCls2StMonOvrOL,
        tPortEgrExpShaperCls2StMonOvrOH,
        tPortEgrExpShaperCls3StFwdPktsH,
        tPortEgrExpShaperCls3StFwdPktsL,
        tPortEgrExpShaperCls3StFwdOctsH,
        tPortEgrExpShaperCls3StFwdOctsL,
        tPortEgrExpShaperCls3StMonOvrOL,
        tPortEgrExpShaperCls3StMonOvrOH,
        tPortEgrExpShaperCls4StFwdPktsH,
        tPortEgrExpShaperCls4StFwdPktsL,
        tPortEgrExpShaperCls4StFwdOctsH,
        tPortEgrExpShaperCls4StFwdOctsL,
        tPortEgrExpShaperCls4StMonOvrOL,
        tPortEgrExpShaperCls4StMonOvrOH,
        tPortEgrExpShaperCls5StFwdPktsH,
        tPortEgrExpShaperCls5StFwdPktsL,
        tPortEgrExpShaperCls5StFwdOctsH,
        tPortEgrExpShaperCls5StFwdOctsL,
        tPortEgrExpShaperCls5StMonOvrOL,
        tPortEgrExpShaperCls5StMonOvrOH,
        tPortEgrExpShaperCls6StFwdPktsH,
        tPortEgrExpShaperCls6StFwdPktsL,
        tPortEgrExpShaperCls6StFwdOctsH,
        tPortEgrExpShaperCls6StFwdOctsL,
        tPortEgrExpShaperCls6StMonOvrOL,
        tPortEgrExpShaperCls6StMonOvrOH,
        tPortEgrExpShaperCls7StFwdPktsH,
        tPortEgrExpShaperCls7StFwdPktsL,
        tPortEgrExpShaperCls7StFwdOctsH,
        tPortEgrExpShaperCls7StFwdOctsL,
        tPortEgrExpShaperCls7StMonOvrOL,
        tPortEgrExpShaperCls7StMonOvrOH,
        tPortEgrExpShaperCls8StFwdPktsH,
        tPortEgrExpShaperCls8StFwdPktsL,
        tPortEgrExpShaperCls8StFwdOctsH,
        tPortEgrExpShaperCls8StFwdOctsL,
        tPortEgrExpShaperCls8StMonOvrOL,
        tPortEgrExpShaperCls8StMonOvrOH,
        tPortEgrExpShaperAggStFwdPktsL,
        tPortEgrExpShaperAggStFwdPktsH,
        tPortEgrExpShaperAggStFwdOctsL,
        tPortEgrExpShaperAggStFwdOctsH,
        tPortEgrExpShaperAggStMonOvrOL,
        tPortEgrExpShaperAggStMonOvrOH,
        tmnxPortEgrExpShaperThresh,
        tmnxPortEgrExpShaperLoBurstLimit,
        tmnxPortEgrExpShaperHiBurstInc,
        tmnxPortEgrExpShaperCl1BrstLimit,
        tmnxPortEgrExpShaperCl2BrstLimit,
        tmnxPortEgrExpShaperCl3BrstLimit,
        tmnxPortEgrExpShaperCl4BrstLimit,
        tmnxPortEgrExpShaperCl5BrstLimit,
        tmnxPortEgrExpShaperCl6BrstLimit,
        tmnxPortEgrExpShaperCl7BrstLimit,
        tmnxPortEgrExpShaperCl8BrstLimit
    }
    STATUS        current
    DESCRIPTION
        "The group of objects supporting the egress port expanded shaper related
         objects for revision 9.0 on Alcatel-Lucent SROS series systems."
    ::= { tmnxPortGroups 92 }

tmnxPortNotificationGroupV9v4 NOTIFICATION-GROUP
    NOTIFICATIONS {
        tmnxEqSonetClockSrcNotCompatible,
        tmnxEqSonetSfThreshNotCompatible,
        tmnxEqSonetFramingNotCompatible
    }
    STATUS        current
    DESCRIPTION
        "The group of notifications supporting the management of physical
         ports for release 9.0 R4 on Alcatel-Lucent SROS series systems."
    ::= { tmnxPortGroups 93 }

tmnxPortObjAppV9v0Group OBJECT-GROUP
    OBJECTS {
       tmnxObjectAppResvCbsAmbrAlrmStep,
       tmnxObjectAppResvCbsAmbrAlrmMax,
       tmnxObjectAppAmbrAlrmThresh,
       tmnxObjectAppRedAlrmThresh
    }
    STATUS      current
    DESCRIPTION
        "The group of objects supporting management of Network Named Pool
         policies on Alcatel-Lucent SROS series systems release 9.0."
    ::= { tmnxPortGroups 94 }    

tmnxOpticalPortGroupV9v0         OBJECT-GROUP
    OBJECTS {
        tmnxOpticalPortDwdmChannelMin,
        tmnxOpticalPortDwdmChannelMax,
        tmnxOpticalPortLaserTunability
    }
    STATUS      current
    DESCRIPTION
        "The group of objects supporting the management of optical ports
         added in release 9.0 on Alcatel-Lucent SROS series systems."
    ::= { tmnxPortGroups 95 }

tmnxPortNotifyObjsGroupV8v9     OBJECT-GROUP
    OBJECTS {
        tmnxObjType,
        tmnxObjPortId,
        tmnxObjMdaId,
        tmnxObjAppType,
        tmnxObjAppPool,
        tmnxObjNamedPoolPolicy,
        tmnxObjAppResvSize,
        tmnxObjAppSumOfQResvSize,
        tmnxObjAppResvCbsOld,
        tmnxObjAppResvCbsNew,
        tmnxObjAppResvSizeOld
    }
    STATUS        current
    DESCRIPTION
        "The group of objects supporting physical port notifications
         for revision 8.0R9 on Alcatel-Lucent SROS series systems."
    ::= { tmnxPortGroups 96 }

tmnxPortNotificationGroupV8v9 NOTIFICATION-GROUP
    NOTIFICATIONS {
        tmnxResvCbsPoolThreshGreen,
        tmnxResvCbsPoolThreshAmber,
        tmnxResvCbsPoolThreshRed
    }
    STATUS        current
    DESCRIPTION
        "The group of notifications supporting the management of physical
         ports for release 8.0 R9 on Alcatel-Lucent SROS series systems."
    ::= { tmnxPortGroups 97 }

tmnxPortEgrVPortStatsV9v0Group       OBJECT-GROUP
    OBJECTS {
        tPortEgrVPStLstClrdTime,
        tPortEgrVPStLvlFwdPkt,
        tPortEgrVPStLvlFwdOct,
        tPortEgrVPStLvlDpdPkt,
        tPortEgrVPStLvlDpdOct,
        tPortEgrVPStLvlFwdPktL,
        tPortEgrVPStLvlFwdPktH,
        tPortEgrVPStLvlFwdOctL,
        tPortEgrVPStLvlFwdOctH,
        tPortEgrVPStLvlDpdPktL,
        tPortEgrVPStLvlDpdPktH,
        tPortEgrVPStLvlDpdOctL,
        tPortEgrVPStLvlDpdOctH 
    }
    STATUS        current
    DESCRIPTION
        "The group of objects supporting the virtual port aggregate statistics
         for revision 9.0 on Alcatel-Lucent SROS series systems."
    ::= { tmnxPortGroups 99 }

tmnxPortNotifyObjsV9v0Group OBJECT-GROUP
    OBJECTS {
        tmnxPortNotifyEtherCrcThreshold,
        tmnxPortNotifyEtherCrcMultiplier,
        tmnxPortNotifyEtherCrcAlarmValue
    }
    STATUS        current
    DESCRIPTION
        "The group of notification objects extending port capabilities
         for revision 9.0 on Alcatel-Lucent SROS series systems."
    ::= { tmnxPortGroups 100 }

tmnxPortEtherV9v0Group           OBJECT-GROUP
    OBJECTS {
        tmnxPortEtherCrcMonSdThreshold,
        tmnxPortEtherCrcMonSdTMultiplier,
        tmnxPortEtherCrcMonSfThreshold,
        tmnxPortEtherCrcMonSfTMultiplier,
        tmnxPortEtherCrcMonWindowSize,
        tmnxPortEtherCrcAlarmReason,
        tmnxPortEtherDownOnInternalError
    }
    STATUS        current
    DESCRIPTION
        "The group of objects extending Ethernet port capabilities
         for revision 9.0 on Alcatel-Lucent SROS series systems."
    ::= { tmnxPortGroups 101 }

tmnxPortNotificationV9v0Group    NOTIFICATION-GROUP
    NOTIFICATIONS {
        tmnxEqPortEtherCrcAlarm,
        tmnxEqPortEtherCrcAlarmClear,
        tmnxEqPortEtherInternalAlarm,
        tmnxEqPortEtherInternalAlarmClr
    }
    STATUS        current
    DESCRIPTION
        "The group of notifications extending port capabilities
         for revision 9.0 on Alcatel-Lucent SROS series systems."
    ::= { tmnxPortGroups 102 }

tmnxPortV9v0Group                OBJECT-GROUP
    OBJECTS {
        tmnxPortLinkLengthInfo
    }
    STATUS      current
    DESCRIPTION
        "The group of objects extending port capabilities for
         revision 9.0 on Alcatel-Lucent SROS series systems."
    ::= { tmnxPortGroups 103 }

tmnxPortNetEgrV10v0Group   OBJECT-GROUP
    OBJECTS {
        tPortNetEgrQGrpPlcrCntrlPolicy,
        tPortNetEgrQGrpPStatMode,
        tPortNetEgrQGrpPStOffInProfPkt,
        tPortNetEgrQGrpPStOffInProfPktL,
        tPortNetEgrQGrpPStOffInProfPktH,
        tPortNetEgrQGrpPStFwdInProfPkt,
        tPortNetEgrQGrpPStFwdInProfPktL,
        tPortNetEgrQGrpPStFwdInProfPktH,
        tPortNetEgrQGrpPStDrpInProfPkt,
        tPortNetEgrQGrpPStDrpInProfPktL,
        tPortNetEgrQGrpPStDrpInProfPktH,
        tPortNetEgrQGrpPStOffOutProfPkt,
        tPortNetEgrQGrpPStOffOutProfPktL,
        tPortNetEgrQGrpPStOffOutProfPktH,
        tPortNetEgrQGrpPStFwdOutProfPkt,
        tPortNetEgrQGrpPStFwdOutProfPktL,
        tPortNetEgrQGrpPStFwdOutProfPktH,
        tPortNetEgrQGrpPStDrpOutProfPkt,
        tPortNetEgrQGrpPStDrpOutProfPktL,
        tPortNetEgrQGrpPStDrpOutProfPktH,
        tPortNetEgrQGrpPStOffInProfOct,
        tPortNetEgrQGrpPStOffInProfOctL,
        tPortNetEgrQGrpPStOffInProfOctH,
        tPortNetEgrQGrpPStFwdInProfOct,
        tPortNetEgrQGrpPStFwdInProfOctL,
        tPortNetEgrQGrpPStFwdInProfOctH,
        tPortNetEgrQGrpPStDrpInProfOct,
        tPortNetEgrQGrpPStDrpInProfOctL,
        tPortNetEgrQGrpPStDrpInProfOctH,
        tPortNetEgrQGrpPStOffOutProfOct,
        tPortNetEgrQGrpPStOffOutProfOctL,
        tPortNetEgrQGrpPStOffOutProfOctH,
        tPortNetEgrQGrpPStFwdOutProfOct,
        tPortNetEgrQGrpPStFwdOutProfOctL,
        tPortNetEgrQGrpPStFwdOutProfOctH,
        tPortNetEgrQGrpPStDrpOutProfOct,
        tPortNetEgrQGrpPStDrpOutProfOctL,
        tPortNetEgrQGrpPStDrpOutProfOctH,
        tPortNetEgrQGrpPStUncolPktOff,
        tPortNetEgrQGrpPStUncolPktOffL,
        tPortNetEgrQGrpPStUncolPktOffH,
        tPortNetEgrQGrpPStUncolOctOff,
        tPortNetEgrQGrpPStUncolOctOffL,
        tPortNetEgrQGrpPStUncolOctOffH,
        tPortNetEgrQGrpArbitStatFwdPkts,  
        tPortNetEgrQGrpArbitStatFwdPktsL, 
        tPortNetEgrQGrpArbitStatFwdPktsH, 
        tPortNetEgrQGrpArbitStatFwdOcts,  
        tPortNetEgrQGrpArbitStatFwdOctsL, 
        tPortNetEgrQGrpArbitStatFwdOctsH
    }
    STATUS      current
    DESCRIPTION
        "The group of objects added in 10.0 release to support network egress
         queue-group objects on Alcatel-Lucent SROS series systems."
    ::= { tmnxPortGroups 104 }

tmnxDDMLaneGroupV10v0 OBJECT-GROUP
    OBJECTS   {
        tmnxPortSFPNumLanes,
        tmnxDDMLaneTemperature,
        tmnxDDMLaneTempLowWarn,
        tmnxDDMLaneTempLowAlarm,
        tmnxDDMLaneTempHiWarn,
        tmnxDDMLaneTempHiAlarm,
        tmnxDDMLaneTxBiasCurrent,
        tmnxDDMLaneTxBiasCurrentLowWarn,
        tmnxDDMLaneTxBiasCurrentLowAlarm,
        tmnxDDMLaneTxBiasCurrentHiWarn,
        tmnxDDMLaneTxBiasCurrentHiAlarm,
        tmnxDDMLaneTxOutputPower,
        tmnxDDMLaneTxOutputPowerLowWarn,
        tmnxDDMLaneTxOutputPowerLowAlarm,
        tmnxDDMLaneTxOutputPowerHiWarn,
        tmnxDDMLaneTxOutputPowerHiAlarm,
        tmnxDDMLaneRxOpticalPower,
        tmnxDDMLaneRxOpticalPwrLowWarn,
        tmnxDDMLaneRxOpticalPwrLowAlarm,
        tmnxDDMLaneRxOpticalPwrHiWarn,
        tmnxDDMLaneRxOpticalPwrHiAlarm,
        tmnxDDMLaneRxOpticalPowerType,
        tmnxDDMLaneFailedThresholds
              }
    STATUS        current
    DESCRIPTION
        "The group of objects enhancing the management of
         Digital Diagnostic Monitoring SFFs for revision 10.0 on
         Alcatel-Lucent SROS series systems."
    ::= { tmnxPortGroups 105 }

tmnxPortNotifyObjsGroupV10v0     OBJECT-GROUP
    OBJECTS {
        tmnxDDMLaneIdOrModule
            }
    STATUS        current
    DESCRIPTION
        "The group of objects supporting physical port notifications
         for revision 10.0 on Alcatel-Lucent SROS series systems."
    ::= { tmnxPortGroups 106 }

tmnxPortPlcyGroup   OBJECT-GROUP
    OBJECTS {
        tmnxPortPlcyTableLastCh,
        tmnxPortPlcyRowStatus,
        tmnxPortPlcyLastCh,
        tmnxPortPlcyDescription,
        tmnxPortPlcyEgrPortSchedPlcy
    }
    STATUS      current
    DESCRIPTION
        "The group of objects to support network egress
         port policies on Alcatel-Lucent SROS series systems."
    ::= { tmnxPortGroups 107 }

tmnxPortLoadBalGroupV10v0        OBJECT-GROUP
    OBJECTS {
        tmnxIpLoadBalancing,
        tmnxServiceIdLagHashing
    }
    STATUS      current
    DESCRIPTION
        "The group of additional objects supporting ECMP and LAG load balancing
         in Alcatel-Lucent SROS release 10.0 systems."
    ::= { tmnxPortGroups 108 }

tmnxPortEthernetV10v0Group       OBJECT-GROUP
    OBJECTS {
        tmnxPortEtherMinFrameLength,
        tmnxPortPhysStateChangeCount
    }
    STATUS      current
    DESCRIPTION
        "The group of additional objects enhancing Ethernet Port functionality
         in Alcatel-Lucent SROS release 10.0 systems."
    ::= { tmnxPortGroups 109 }

tmnxHsmdaGroupV10v0 OBJECT-GROUP
    OBJECTS   {
        tmnxPortEgrHsmdaSchedPlcy,
        tmnxHsmdaPortSchOvrTblLastChngd,
        tmnxHsmdaPortSchOvrRowStatus,
        tmnxHsmdaPortSchOvrLastChanged,
        tmnxHsmdaPortSchOvrMaxRate,
        tmnxHsmdaPortSchOvrGrp1Rate,
        tmnxHsmdaPortSchOvrGrp2Rate,
        tmnxHsmdaPortSchOvrClass1Rate,
        tmnxHsmdaPortSchOvrClass1WtInGp,
        tmnxHsmdaPortSchOvrClass2Rate,
        tmnxHsmdaPortSchOvrClass2WtInGp,
        tmnxHsmdaPortSchOvrClass3Rate,
        tmnxHsmdaPortSchOvrClass3WtInGp,
        tmnxHsmdaPortSchOvrClass4Rate,
        tmnxHsmdaPortSchOvrClass4WtInGp,
        tmnxHsmdaPortSchOvrClass5Rate,
        tmnxHsmdaPortSchOvrClass5WtInGp,
        tmnxHsmdaPortSchOvrClass6Rate,
        tmnxHsmdaPortSchOvrClass6WtInGp,
        tmnxHsmdaPortSchOvrClass7Rate,
        tmnxHsmdaPortSchOvrClass7WtInGp,
        tmnxHsmdaPortSchOvrClass8Rate,
        tmnxHsmdaPortSchOvrClass8WtInGp
    }
    STATUS        current
    DESCRIPTION
        "The group of objects supporting the management of HSMDA
         ports for revision 10.0 on Alcatel-Lucent SROS series systems."
    ::= { tmnxPortGroups 110 }    

tmnxPortObsoletedV10v0Group  OBJECT-GROUP
    OBJECTS {   
        tmnxPortEgrShaperTblLastChanged,
        tmnxPortEgrShaperRowStatus,
        tmnxPortEgrShaperLastChanged,
        tmnxPortEgrShaperRate
    }
    STATUS      current
    DESCRIPTION
        "The objects which were obsoleted for revision 10.0 on Alcatel-Lucent
         SROS series systems."
    ::= { tmnxPortGroups 111 }

tmnxPwPortV10v0Group OBJECT-GROUP
    OBJECTS {
       tmnxPwPortTblLastChanged,
       tmnxPwPortRowStatus,
       tmnxPwPortLastChgd,
       tmnxPwPortEncapType
    }
    STATUS current
    DESCRIPTION
        "The group of objects supporting specific pseudo-wire port feature
         on Alcatel-Lucnet SROS series systems."
    ::= { tmnxPortGroups 112 }

tmnxPortEtherPhysStatsGroup      OBJECT-GROUP
    OBJECTS {
        tmnxPortEtherPhysAcctPolicyId,
        tmnxPortEtherPhysCollectStats
    }
    STATUS      current
    DESCRIPTION
        "The group of objects supporting Physical Layer Ethernet statistics
         collection in Alcatel-Lucent SROS release 10.0 systems."
    ::= { tmnxPortGroups 113 }

tmnxPortEgrQGrpV11v0Group OBJECT-GROUP
    OBJECTS {
       tPortAccEgrQOverWeight,
       tPortAccEgrQOverCIRWeight
    }
    STATUS current
    DESCRIPTION
        "The group of objects supporting specific port egress queue-group 
         feature on Alcatel-Lucent SROS release 11.0 systems."
    ::= { tmnxPortGroups 114 }    

tmnxWaveTrackerV11v0Group    OBJECT-GROUP
    OBJECTS {
        tmnxWaveTrackerPortType,
        tmnxWaveTrackerSfpVoaEquipped,
        tmnxWaveTrackerSfpVoaType,
        tmnxWaveTrackerSfpVoaSerialNum,
        tmnxWaveTrackerSfpVoaModelNum
    }
    STATUS      current
    DESCRIPTION
        "The group of additional objects supporting Wave Tracker in
         Alcatel-Lucent SROS release 11.0 systems."
    ::= { tmnxPortGroups 115 }    

tmnxCohOptPortGroup              OBJECT-GROUP
    OBJECTS {
        tmnxCohOptPortCfgAlarms,
        tmnxCohOptPortCfgRxChan,
        tmnxCohOptPortDispCtrlMode,
        tmnxCohOptPortManCfgDisp,
        tmnxCohOptPortDispSwpStart,
        tmnxCohOptPortDispSwpEnd,
        tmnxCohOptPortCfgTxPower,
        tmnxCohOptPortCfgCprWinSize,
        tmnxCohOptPortCfgRxLosThresh,
        tmnxCohOptPortCprWinSizeSearch,
        tmnxCohOptPortCprWnSzSrchStatus,
        tmnxCohOptPortCprWnSzSrchResult,
        tmnxCohOptPortAlarmState,
        tmnxCohOptPortDefectPoints,
        tmnxCohOptPortPresRxChan,
        tmnxCohOptPortModState,
        tmnxCohOptPortModTxTurnUpStates,
        tmnxCohOptPortModRxTurnUpStates,
        tmnxCohOptPortRxSNRXPolar,
        tmnxCohOptPortRxSNRYPolar,
        tmnxCohOptPortRxQMargin
    }
    STATUS      current
    DESCRIPTION
        "The group of objects supporting coherent optical ports in
         Alcatel-Lucent SROS release 11.0 systems."
    ::= { tmnxPortGroups 116 }    

tmnxCohOptPortStatsGroup         OBJECT-GROUP
    OBJECTS {
        tmnxCohOptPortStatsElapsedSec,
        tmnxCohOptPortRxBER,
        tmnxCohOptPortRxBERAvg,
        tmnxCohOptPortRxBERMin,
        tmnxCohOptPortRxBERMax,
        tmnxCohOptPortRxSNR,
        tmnxCohOptPortRxSNRAvg,
        tmnxCohOptPortRxSNRMin,
        tmnxCohOptPortRxSNRMax,
        tmnxCohOptPortRxChromaticDisp,
        tmnxCohOptPortRxChromaticDispAvg,
        tmnxCohOptPortRxChromaticDispMin,
        tmnxCohOptPortRxChromaticDispMax,
        tmnxCohOptPortRxDiffGrpDly,
        tmnxCohOptPortRxDiffGrpDlyAvg,
        tmnxCohOptPortRxDiffGrpDlyMin,
        tmnxCohOptPortRxDiffGrpDlyMax,
        tmnxCohOptPortRxFreqOffset,
        tmnxCohOptPortRxFreqOffsetAvg,
        tmnxCohOptPortRxFreqOffsetMin,
        tmnxCohOptPortRxFreqOffsetMax,
        tmnxCohOptPortRxQ,
        tmnxCohOptPortRxQAvg,
        tmnxCohOptPortRxQMin,
        tmnxCohOptPortRxQMax,
        tmnxCohOptPortRxPower,
        tmnxCohOptPortRxPowerAvg,
        tmnxCohOptPortRxPowerMin,
        tmnxCohOptPortRxPowerMax,
        tmnxCohOptPortTxPower,
        tmnxCohOptPortTxPowerAvg,
        tmnxCohOptPortTxPowerMin,
        tmnxCohOptPortTxPowerMax
    }
    STATUS      current
    DESCRIPTION
        "The group of objects supporting coherent optical port statistics
         collection in Alcatel-Lucent SROS release 11.0 systems."
    ::= { tmnxPortGroups 117 }    

tmnxPortNotificationV11v0Group   NOTIFICATION-GROUP
    NOTIFICATIONS {
        tmnxEqCohOptPortAlarm
    }
    STATUS        current
    DESCRIPTION
        "The group of additional notifications supporting the management of
         physical ports for release 11.0 on Alcatel-Lucent SROS series
         systems."
    ::= { tmnxPortGroups 118 }

tmnxPortEgrHsmdaStatV11v0Group OBJECT-GROUP
    OBJECTS {
       tPortEgrHsmdaQStatFwdInProfPkts,
       tPortEgrHsmdaQStatFwdInProfPktH,
       tPortEgrHsmdaQStatFwdInProfPktL,
       tPortEgrHsmdaQStatDpdInProfPkts,
       tPortEgrHsmdaQStatDpdInProfPktH,
       tPortEgrHsmdaQStatDpdInProfPktL,
       tPortEgrHsmdaQStatFwdOutProfPkts,
       tPortEgrHsmdaQStatFwdOutProfPktH,
       tPortEgrHsmdaQStatFwdOutProfPktL,
       tPortEgrHsmdaQStatDpdOutProfPkts,
       tPortEgrHsmdaQStatDpdOutProfPktH,
       tPortEgrHsmdaQStatDpdOutProfPktL,
       tPortEgrHsmdaQStatFwdInProfOcts,
       tPortEgrHsmdaQStatFwdInProfOctH,
       tPortEgrHsmdaQStatFwdInProfOctL,
       tPortEgrHsmdaQStatDpdInProfOcts,
       tPortEgrHsmdaQStatDpdInProfOctH,
       tPortEgrHsmdaQStatDpdInProfOctL,
       tPortEgrHsmdaQStatFwdOutProfOcts,
       tPortEgrHsmdaQStatFwdOutProfOctH,
       tPortEgrHsmdaQStatFwdOutProfOctL,
       tPortEgrHsmdaQStatDpdOutProfOcts,
       tPortEgrHsmdaQStatDpdOutProfOctH,
       tPortEgrHsmdaQStatDpdOutProfOctL,
       tPortEgrHsmdaCStatFwdInProfPkts,
       tPortEgrHsmdaCStatFwdInProfPktH,
       tPortEgrHsmdaCStatFwdInProfPktL,
       tPortEgrHsmdaCStatDpdInProfPkts,
       tPortEgrHsmdaCStatDpdInProfPktH,
       tPortEgrHsmdaCStatDpdInProfPktL,
       tPortEgrHsmdaCStatFwdOutProfPkts,
       tPortEgrHsmdaCStatFwdOutProfPktH,
       tPortEgrHsmdaCStatFwdOutProfPktL,
       tPortEgrHsmdaCStatDpdOutProfPkts,
       tPortEgrHsmdaCStatDpdOutProfPktH,
       tPortEgrHsmdaCStatDpdOutProfPktL,
       tPortEgrHsmdaCStatFwdInProfOcts,
       tPortEgrHsmdaCStatFwdInProfOctH,
       tPortEgrHsmdaCStatFwdInProfOctL,
       tPortEgrHsmdaCStatDpdInProfOcts,
       tPortEgrHsmdaCStatDpdInProfOctH,
       tPortEgrHsmdaCStatDpdInProfOctL,
       tPortEgrHsmdaCStatFwdOutProfOcts,
       tPortEgrHsmdaCStatFwdOutProfOctH,
       tPortEgrHsmdaCStatFwdOutProfOctL,
       tPortEgrHsmdaCStatDpdOutProfOcts,
       tPortEgrHsmdaCStatDpdOutProfOctH,
       tPortEgrHsmdaCStatDpdOutProfOctL
    }
    STATUS current
    DESCRIPTION
        "The group of objects supporting specific port egress Hsmda statictics
         feature on Alcatel-Lucent SROS release 11.0 systems."
    ::= { tmnxPortGroups 119 }    

tmnxPortEgrHsmdaOverV11v0Group OBJECT-GROUP
    OBJECTS {
        tPortAccEgrQGrpHsmdaShaperOvr,
        tPortAccEgrQGrpHsmdaPktOffOvr,
        tPortAccEgrQGrpHsmdaWrrPolicyOvr,
        tPortAccEgrHsmdaQOverRowStatus,
        tPortAccEgrHsmdaQOverLastChanged,
        tPortAccEgrHsmdaQOverAdminPIR,
        tPortAccEgrHsmdaQOverSlopePolicy,
        tPortAccEgrHsmdaQOverWrrWeight,
        tPortAccEgrHsmdaQOverMBS
    }
    STATUS      current
    DESCRIPTION
        "The group of objects supporting specific port egress HSMDA override  
         feature on Alcatel-Lucent SROS release 11.0 systems."
    ::= { tmnxPortGroups 120 } 

tmnxPortEthernetV11v0Group       OBJECT-GROUP
    OBJECTS {
        tmnxPortEtherOperPhyTxClock
    }
    STATUS      current
    DESCRIPTION
        "The group of additional objects enhancing Ethernet Port functionality
         in Alcatel-Lucent SROS release 11.0 systems."
    ::= { tmnxPortGroups 121 }

tmnxScalarPortV11v0Group         OBJECT-GROUP
    OBJECTS {
        tmnxMulticastEnhLoadBalancing
    }
    STATUS      current
    DESCRIPTION
        "The group of objects supporting enhanced load-balancing techniques
        added in release 11.0 of Alcatel-Lucent SROS series systems."
        ::= { tmnxPortGroups 122 }
tmnxPortVPortV11v0Group       OBJECT-GROUP
    OBJECTS {
        tPortEgrVPortEgrRateModify,
        tPortEgrVPortEgrRateModifyDelta
    }
    STATUS        current
    DESCRIPTION
        "The group of objects supporting the configuration of egres virtual
         ports added in release 11.0 of Alcatel-Lucent SROS series systems."
    ::= { tmnxPortGroups 125 }

tmnxPortVPortV12v0Group       OBJECT-GROUP
    OBJECTS {
        tPortEgrVPortSchedStatTblLastCh,
        tPortEgrVPSchedStatFwdPkts,
        tPortEgrVPSchedStatFwdOcts
    }
    STATUS        current
    DESCRIPTION
        "The group of objects supporting the configuration of egres virtual
         ports added in release 12.0 of Alcatel-Lucent SROS series systems."
    ::= { tmnxPortGroups 126 }

tmnxCohOptPortV11v0Group       OBJECT-GROUP
    OBJECTS {
        tmnxCohOptPortRxLosReaction
    }
    STATUS        current
    DESCRIPTION
        "The group of additional objects supporting the configuration of
         coherent optical ports in release 11.0 of Alcatel-Lucent SROS series
         systems."
    ::= { tmnxPortGroups 127 }

tmnxDot1xPaePortGroup       OBJECT-GROUP
    OBJECTS {
        tmnxDot1xPaePortTunneling,
        tmnxDot1xPaePortTblLastChanged
    }
    STATUS        current
    DESCRIPTION
        "The group of additional objects supporting the configuration of dot1x
         PAE ports in release 12.0 of Alcatel-Lucent SROS series systems."
    ::= { tmnxPortGroups 128 }

tmnxPortAggRateV12v0Group  OBJECT-GROUP
    OBJECTS {
        tPortAccEgrQGrpAggRateLUB,
        tPortNetEgrQGrpAggRateLUB,
        tPortEgrVPortAggRateLUB
    }
    STATUS current
    DESCRIPTION
        "The group of objects supporting the configuration of QoS capabilities 
         on physical ports for release 12.0 on Alcatel-Lucent SROS series
         systems."
    ::= { tmnxPortGroups 129 }

tmnxPortEtherSymMonGroupV12v0   OBJECT-GROUP
    OBJECTS {
        tmnxPortEtherSymMonTblLastChange,
        tmnxPortEtherSymMonEnabled,
        tmnxPortEtherSymMonSdThreshold,
        tmnxPortEtherSymMonSdTMultiplier,
        tmnxPortEtherSymMonSfThreshold,
        tmnxPortEtherSymMonSfTMultiplier,
        tmnxPortEtherSymMonWindowSize,
        tmnxPortEtherSymMonAlarmReason,
        tmnxPortEtherSymMonErrorCount
    }
    STATUS      current
    DESCRIPTION
        "The group of additional objects supporting the configuration and state
         of Symbol Monitoring on Ethernet Ports introduced for release 12.0 on
         Alcatel-Lucent SROS series systems."
    ::= { tmnxPortGroups 130 }

tmnxPrtEthSmMnNotifyObjsGrpV12v0 OBJECT-GROUP
    OBJECTS {
        tmnxPortNotifyEtherSymThreshold,
        tmnxPortNotifyEtherSymMultiplier,
        tmnxPortNotifyEtherSymAlarmValue
    }
    STATUS      current
    DESCRIPTION
        "The group of additional NOTIFICATION objects supporting the
         configuration and state of Symbol Monitoring on Ethernet Ports
         introduced for release 12.0 on Alcatel-Lucent SROS series systems."
    ::= { tmnxPortGroups 131 }

tmnxPortEthSymMonNotifyGrpV12v0 NOTIFICATION-GROUP
    NOTIFICATIONS {
        tmnxEqPortEtherSymMonAlarm,
        tmnxEqPortEtherSymMonAlarmClear
    }
    STATUS      current
    DESCRIPTION
        "The group of additional NOTIFICATION-TYPEs supporting the notification
         of Symbol Monitoring on Ethernet Ports introduced for release 12.0 on
         Alcatel-Lucent SROS series systems."
    ::= { tmnxPortGroups 132 }

tmnxPortSchedPlcyV12v0Group OBJECT-GROUP
    OBJECTS {
        tmnxPortSchedOvrMaxRatePercent,
        tmnxPortSchedOvrLvl1PIRPercent,
        tmnxPortSchedOvrLvl1CIRPercent,
        tmnxPortSchedOvrLvl2PIRPercent,
        tmnxPortSchedOvrLvl2CIRPercent,
        tmnxPortSchedOvrLvl3PIRPercent,
        tmnxPortSchedOvrLvl3CIRPercent,
        tmnxPortSchedOvrLvl4PIRPercent,
        tmnxPortSchedOvrLvl4CIRPercent,
        tmnxPortSchedOvrLvl5PIRPercent,
        tmnxPortSchedOvrLvl5CIRPercent,
        tmnxPortSchedOvrLvl6PIRPercent,
        tmnxPortSchedOvrLvl6CIRPercent,
        tmnxPortSchedOvrLvl7PIRPercent,
        tmnxPortSchedOvrLvl7CIRPercent,
        tmnxPortSchedOvrLvl8PIRPercent,
        tmnxPortSchedOvrLvl8CIRPercent
    }
    STATUS      current
    DESCRIPTION
        "The group of additional objects supporting management of Qos Port
         Scheduler policies on Alcatel-Lucent SROS series systems release 12.0."
    ::= { tmnxPortGroups 133 }

tmnxPortParentLocV12v0Group       OBJECT-GROUP
    OBJECTS {
        tPortEgrVPortQosSchedPolicy
    }
    STATUS        current
    DESCRIPTION
        "The group of objects supporting the configuration of egress virtual
         ports added in release 12.0 of Alcatel-Lucent SROS series systems."
    ::= { tmnxPortGroups 134 }

tmnxDS3V12v0Group               OBJECT-GROUP
    OBJECTS {
        tmnxDS3HoldTimeUp,
        tmnxDS3HoldTimeDown
    }
    STATUS      current
    DESCRIPTION
        "The group of objects supporting DS3 physical ports added in release
         12.0 of Alcatel-Lucent SROS series systems."
    ::= { tmnxPortGroups 135 }

END
