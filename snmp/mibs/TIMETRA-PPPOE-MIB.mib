TIMETRA-PPPOE-MIB DEFINITIONS ::= BEGIN

IMPORTS
    MODULE-IDENTITY, OBJECT-TYPE,
    NOTIFICATION-TYPE, Unsigned32, Counter32,
    TimeTicks, Integer32, Gauge32                   FROM SNMPv2-SMI

    MODULE-COMPLIANCE, OBJECT-GROUP,
    NOTIFICATION-GROUP                              FROM SNMPv2-CONF

    RowStatus, TimeStamp, TruthValue,
    TEXTUAL-CONVENTION, MacAddress,
    DisplayString                                   FROM SNMPv2-TC

    timetraSRMIBModules, tmnxSRObjs,
    tmnxSRNotifyPrefix, tmnxSRConfs                 FROM TIMETRA-GLOBAL-MIB

    TNamedItem, TNamedItemOrEmpty,
    TItemDescription, TmnxAncpStringOrZero,
    TmnxSubIdentStringOrEmpty,
    TmnxSubProfileStringOrEmpty,
    TmnxSlaProfileStringOrEmpty,
    TmnxPppoeUserNameOrEmpty,
    TmnxAppProfileStringOrEmpty,
    TmnxSubMgtIntDestIdOrEmpty,
    TmnxDhcpOptionType, TmnxManagedRouteStatus,
    TmnxPppoeSessionId, TmnxPppoePadoDelay,
    TmnxPppoeSessionInfoOrigin, 
    TmnxPppoeSessionType,
    TmnxServId, TmnxVRtrIDOrZero,
    TPolicyStatementNameOrEmpty,
    TmnxBgpAutonomousSystem, BgpPeeringStatus,
    TPIRRateOverride, TCIRRateOverride,
    TDirection, TBurstSizeBytesOverride,
    TQosOverrideType,
    TmnxAccessLoopEncapDataLink,
    TmnxAccessLoopEncaps1,
    TmnxAccessLoopEncaps2,
    TmnxMlpppEpClass,
    TmnxAuthPassword
                                                    FROM TIMETRA-TC-MIB

    svcId, iesIfIndex                               FROM TIMETRA-SERV-MIB
    sapPortId, sapEncapValue                        FROM TIMETRA-SAP-MIB

    TmnxPppCpState                                  FROM TIMETRA-PPP-MIB

    InetAddressPrefixLength,
    InetAddressType, InetAddress, 
    InetAddressIPv4,
    InetAutonomousSystemNumber                      FROM INET-ADDRESS-MIB

    InterfaceIndexOrZero                            FROM IF-MIB
    
    tmnxSubPppIndex                             FROM TIMETRA-SUBSCRIBER-MGMT-MIB
    ;

timetraPppoeMIBModule MODULE-IDENTITY
        LAST-UPDATED "201401010000Z"
        ORGANIZATION "Alcatel-Lucent"
        CONTACT-INFO
            "Alcatel-Lucent SROS Support
             Web: http://support.alcatel-lucent.com"
    DESCRIPTION
        "This document is the SNMP MIB module to manage and provision
         the PPP over Ethernet (PPPoE) for the Alcatel-Lucent SROS device.

         Copyright 2008-2014 Alcatel-Lucent. All rights reserved.
         Reproduction of this document is authorized on the condition that
         the foregoing copyright notice is included.

         This SNMP MIB module (Specification) embodies Alcatel-Lucent's
         proprietary intellectual property. Alcatel-Lucent retains all title and
         ownership in the Specification, including any revisions.

         Alcatel-Lucent grants all interested parties a non-exclusive
         license to use and distribute an unmodified copy of this
         Specification in connection with management of Alcatel-Lucent products,
         and without fee, provided this copyright notice and license appear
         on all copies.

         This Specification is supplied 'as is', and Alcatel-Lucent
         makes no warranty, either express or implied, as to the use,
         operation, condition, or performance of the Specification."

    REVISION     "201401010000Z"
    DESCRIPTION  "Rev 12.0                1 Jan 2014 00:00
                  12.0 release of the TIMETRA-PPPOE-MIB."

    REVISION     "200902280000Z"
    DESCRIPTION  "Rev 9.0                 1 Feb 2011 00:00
                  9.0 release of the TIMETRA-PPPOE-MIB."

    REVISION     "201102010000Z"
    DESCRIPTION  "Rev 7.0                28 Feb 2009 00:00
                  7.0 release of the TIMETRA-PPPOE-MIB."

    REVISION     "200807010000Z"
    DESCRIPTION  "Rev 6.1                01 Jul 2008 00:00
                  6.1 release of the TIMETRA-PPPOE-MIB."

    REVISION     "200801010000Z"
    DESCRIPTION  "Rev 0.1                01 Jan 2008 00:00
                  Initial version of the TIMETRA-PPPOE-MIB."

        ::= { timetraSRMIBModules 49 }

-- ----------------------------------------------------------------------------
--  Alcatel-Lucent SROS series PPPOE MIB structure
-- ----------------------------------------------------------------------------
tmnxPppoe                      OBJECT IDENTIFIER ::= { tmnxSRObjs 49 }
    tmnxPppoeObjects           OBJECT IDENTIFIER ::= { tmnxPppoe 1 }
    tmnxPppoeNotificationObjs  OBJECT IDENTIFIER ::= { tmnxPppoe 2 }
    tmnxPppObjects             OBJECT IDENTIFIER ::= { tmnxPppoe 3 }

tmnxPppoeConformance           OBJECT IDENTIFIER ::= { tmnxSRConfs 49 }
    tmnxPppoeCompliances       OBJECT IDENTIFIER ::= { tmnxPppoeConformance 1 }
    tmnxPppoeGroups            OBJECT IDENTIFIER ::= { tmnxPppoeConformance 2 }

tmnxPppoeNotifyPrefix          OBJECT IDENTIFIER ::= { tmnxSRNotifyPrefix 49 }
    tmnxPppoeNotifications     OBJECT IDENTIFIER ::= { tmnxPppoeNotifyPrefix 0 }

--
-- Subtrees
--

tmnxMlpppObjects               OBJECT IDENTIFIER ::= { tmnxPppObjects 3 }

----------------------------------------------------------------------------
--  Textual Conventions
----------------------------------------------------------------------------
TmnxPppoeAdminStatus ::= TEXTUAL-CONVENTION
    STATUS      current
    DESCRIPTION
        "The TmnxPppoeAdminStatus data type is an enumerated integer that
         describes the values used to identify the administrative state."
    SYNTAX INTEGER {
        enabled  (1),
        disabled (2)
    }

----------------------------------------------------------------------------
--  Object definitions
----------------------------------------------------------------------------
-- --------------------------------------------------------
-- tmnxPppoePlcyTable
-- --------------------------------------------------------
tmnxPppoePlcyTableLastChanged OBJECT-TYPE
    SYNTAX      TimeStamp
    MAX-ACCESS  read-only
    STATUS      current
    DESCRIPTION
        "The value of tmnxPppoePlcyTableLastChanged indicates the sysUpTime at
         the time of the most recent management-initiated change to the
         tmnxPppoePlcyTable."
    ::= { tmnxPppoeObjects 1 }

tmnxPppoePlcyTable OBJECT-TYPE
    SYNTAX      SEQUENCE OF TmnxPppoePlcyEntry
    MAX-ACCESS  not-accessible
    STATUS      current
    DESCRIPTION
        "The tmnxPppoePlcyTable has an entry for each PPP(oE) policy configured
         in the system.
         
         This table can be used to configure PPP for PPPoE (PPP over Ethernet) 
         and PPPoA (PPP over ATM) subscribers."
    ::= { tmnxPppoeObjects 2 }

tmnxPppoePlcyEntry OBJECT-TYPE
    SYNTAX      TmnxPppoePlcyEntry
    MAX-ACCESS  not-accessible
    STATUS      current
    DESCRIPTION
        "Each row entry represents a PPP(oE) policy configured in the system.

         Entries can be created and deleted via SNMP SET operations on the
         object tmnxPppoePlcyRowStatus."
    INDEX { IMPLIED tmnxPppoePlcyName }
    ::= { tmnxPppoePlcyTable 1 }

TmnxPppoePlcyEntry ::=
    SEQUENCE {
        tmnxPppoePlcyName                TNamedItem,
        tmnxPppoePlcyRowStatus           RowStatus,
        tmnxPppoePlcyLastMgmtChange      TimeStamp,
        tmnxPppoePlcyDescription         TItemDescription,
        tmnxPppoePlcyPppMtu              Unsigned32,
        tmnxPppoePlcyLcpKaInterval       Unsigned32,
        tmnxPppoePlcyLcpKaHoldUpMplier   Unsigned32,
        tmnxPppoePlcyDisableAcCookies    TruthValue,
        tmnxPppoePlcyPadoDelay           TmnxPppoePadoDelay,
        tmnxPppoePlcyMaxSessionsPerMac   Unsigned32,
        tmnxPppoePlcyReplyOnPadt         TruthValue,
        tmnxPppoePlcyPppAuthentication   INTEGER,
        tmnxPppoePlcyPppMinChapChallenge Unsigned32,
        tmnxPppoePlcyPppMaxChapChallenge Unsigned32,
        tmnxPppoePlcyPppInitialDelay     Unsigned32,
        tmnxPppoePlcyPppIpcpSubnetNeg    TruthValue,
        tmnxPppoePlcyPadoAcName          DisplayString,
        tmnxPppoePlcyPppMtuForceGt1492   TruthValue,
        tmnxPppoePlcyUniqueSessIdsPerSap INTEGER,
        tmnxPppoePlcyRejectDisabledNcp   TruthValue,
        tmnxPppoePlcyLcpIgnoreMagic      TruthValue,
        tmnxPppoePlcySessionTimeout      Unsigned32,
        tmnxPppoePlcyAllowSameCidForDhcp TruthValue,
        tmnxPppoePlcyReestablishSession  INTEGER,
        tmnxPppoePlcyDefaultUserName     TmnxPppoeUserNameOrEmpty,
        tmnxPppoePlcyDefaultPapPassword  TmnxAuthPassword
             
    }

tmnxPppoePlcyName OBJECT-TYPE
    SYNTAX      TNamedItem
    MAX-ACCESS  not-accessible
    STATUS      current
    DESCRIPTION
        "The value of tmnxPppoePlcyName specifies the name of the PPP(oE)
         policy."
    ::= { tmnxPppoePlcyEntry 1 }

tmnxPppoePlcyRowStatus OBJECT-TYPE
    SYNTAX      RowStatus
    MAX-ACCESS  read-create
    STATUS      current
    DESCRIPTION
        "The value of tmnxPppoePlcyRowStatus controls the creation and
         deletion of rows in this table."
    ::= { tmnxPppoePlcyEntry 2 }

tmnxPppoePlcyLastMgmtChange OBJECT-TYPE
    SYNTAX      TimeStamp
    MAX-ACCESS  read-only
    STATUS      current
    DESCRIPTION
        "The value of tmnxPppoePlcyLastMgmtChange indicates the sysUpTime at
         the time of the most recent management-initiated change to this
         table row."
    ::= { tmnxPppoePlcyEntry 3 }

tmnxPppoePlcyDescription OBJECT-TYPE
    SYNTAX      TItemDescription
    MAX-ACCESS  read-create
    STATUS      current
    DESCRIPTION
        "The value of tmnxPppoePlcyDescription specifies the user provided
         description of this PPP policy."
    DEFVAL { "" }
    ::= { tmnxPppoePlcyEntry 4 }

tmnxPppoePlcyPppMtu OBJECT-TYPE
    SYNTAX      Unsigned32 (0|512..9212)
    MAX-ACCESS  read-create
    STATUS      current
    DESCRIPTION
        "The value of tmnxPppoePlcyPppMtu specifies the largest IP packet that
         can be sent out without being fragmented over the specific PPPoE
         tunnel.

         A value of 0 indicates the specific MTU is derived from the
         interface."
    DEFVAL { 0 }
    ::= { tmnxPppoePlcyEntry 5 }

tmnxPppoePlcyLcpKaInterval OBJECT-TYPE
    SYNTAX      Unsigned32 (4..300)
    UNITS       "seconds"
    MAX-ACCESS  read-create
    STATUS      current
    DESCRIPTION
        "The value tmnxPppoePlcyLcpKaInterval specifies the time interval in
         seconds at which LCP echo requests are transmitted."
    DEFVAL { 30 }
    ::= { tmnxPppoePlcyEntry 6 }

tmnxPppoePlcyLcpKaHoldUpMplier OBJECT-TYPE
    SYNTAX      Unsigned32 (1..5)
    MAX-ACCESS  read-create
    STATUS      current
    DESCRIPTION
        "The value of tmnxPppoePlcyLcpKaHoldUpMplier specifies how many LCP
         keepalive messages can be missed before the related PPP session is
         brought down."
    DEFVAL { 3 }
    ::= { tmnxPppoePlcyEntry 7 }

tmnxPppoePlcyDisableAcCookies OBJECT-TYPE
    SYNTAX      TruthValue
    MAX-ACCESS  read-create
    STATUS      current
    DESCRIPTION
        "The value tmnxPppoePlcyDisableAcCookies specifies whether the use
         of AC-Cookie tags during the PPPoE discovery phase is disabled."
    DEFVAL { false }
    ::= { tmnxPppoePlcyEntry 8 }

tmnxPppoePlcyPadoDelay OBJECT-TYPE
    SYNTAX      TmnxPppoePadoDelay
    UNITS       "deci-seconds"
    MAX-ACCESS  read-create
    STATUS      current
    DESCRIPTION
        "The value tmnxPppoePlcyPadoDelay specifies the delay timeout before
         sending a PADO (PPPoE Active Discovery Offer)."
    DEFVAL { 0 }
    ::= { tmnxPppoePlcyEntry 9 }

tmnxPppoePlcyMaxSessionsPerMac OBJECT-TYPE
    SYNTAX      Unsigned32 (1..8191)
    MAX-ACCESS  read-create
    STATUS      current
    DESCRIPTION
        "The value tmnxPppoePlcyMaxSessionsPerMac specifies the maximum number
         of PPPoE sessions that can be created per MAC address."
    DEFVAL { 1 }
    ::= { tmnxPppoePlcyEntry 10 }

tmnxPppoePlcyReplyOnPadt OBJECT-TYPE
    SYNTAX      TruthValue
    MAX-ACCESS  read-create
    STATUS      current
    DESCRIPTION
        "The value tmnxPppoePlcyReplyOnPadt specifies whether the system
         replies with a PADT (PPPoE Active Discovery Terminate) packet when
         a PADT packet is received for an existing PPPoE session."
    DEFVAL { false }
    ::= { tmnxPppoePlcyEntry 11 }

tmnxPppoePlcyPppAuthentication OBJECT-TYPE
    SYNTAX      INTEGER {
                    pap      (1),
                    chap     (2),
                    prefChap (3),
                    prefPap  (4)
                }
    MAX-ACCESS  read-create
    STATUS      current
    DESCRIPTION
        "The value tmnxPppoePlcyPppAuthentication specifies what PPP
         authentication protocol(s) will be negotiated during the LCP phase.
         This field is only applicable if PAP/CHAP authentication is enabled
         via configuration of a RADIUS authentication policy or a local user
         database.
         
         If set to 'pap' or 'chap', only PAP respectively CHAP is negotiated.
         If set to 'prefChap', first CHAP is negotiated followed by PAP.
         If set to 'prefPap', first PAP is negotiated followed by CHAP."
    DEFVAL { prefChap }
    ::= { tmnxPppoePlcyEntry 12 }

tmnxPppoePlcyPppMinChapChallenge OBJECT-TYPE
    SYNTAX      Unsigned32 (8..64)
    MAX-ACCESS  read-create
    STATUS      current
    DESCRIPTION
        "The value of tmnxPppoePlcyPppMinChapChallenge specifies the minimum
         length of the CHAP challenge generated by the system."
    DEFVAL { 32 }
    ::= { tmnxPppoePlcyEntry 13 }

tmnxPppoePlcyPppMaxChapChallenge OBJECT-TYPE
    SYNTAX      Unsigned32 (8..64)
    MAX-ACCESS  read-create
    STATUS      current
    DESCRIPTION
        "The value of tmnxPppoePlcyPppMaxChapChallenge specifies the maximum
         length of the CHAP challenge generated by the system."
    DEFVAL { 64 }
    ::= { tmnxPppoePlcyEntry 14 }

tmnxPppoePlcyPppInitialDelay OBJECT-TYPE
    SYNTAX      Unsigned32 (0|5)
    UNITS       "hundredths of a second"
    MAX-ACCESS  read-create
    STATUS      current
    DESCRIPTION
        "The value of tmnxPppoePlcyPppInitialDelay specifies 
         the delay before starting the PPP stack of a PPPoE session."
    DEFVAL { 0 }
    ::= { tmnxPppoePlcyEntry 15 }

tmnxPppoePlcyPppIpcpSubnetNeg OBJECT-TYPE
    SYNTAX      TruthValue
    MAX-ACCESS  read-create
    STATUS      current
    DESCRIPTION
        "The value tmnxPppoePlcyPppIpcpSubnetNeg specifies 
         if IPCP subnet negotiation is enabled."
    DEFVAL { false }
    ::= { tmnxPppoePlcyEntry 20 }

tmnxPppoePlcyPadoAcName OBJECT-TYPE
    SYNTAX      DisplayString (SIZE (0..128))
    MAX-ACCESS  read-create
    STATUS      current
    DESCRIPTION
        "The value tmnxPppoePlcyPadoAcName specifies the AC-name (Access
         Concentrator's name) tag which will be included in the PADO (PPPoE
         Active Discovery Offer).
         
         If the empty string is specified, the chassis name 
         (TIMETRA-CHASSIS-NAME::tmnxChassisName) will be used as AC-name."
    DEFVAL { "" }
    ::= { tmnxPppoePlcyEntry 21 }
    
tmnxPppoePlcyPppMtuForceGt1492 OBJECT-TYPE    
    SYNTAX      TruthValue
    MAX-ACCESS  read-create
    STATUS      current
    DESCRIPTION
        "The value tmnxPppoePlcyPppMtuForceGt1492 specifies for PPPoE sessions
         whether a PPP MTU greater than 1492 can be negotiated without
         following the procedure described in RFC 4638."   
    DEFVAL { false }
    ::= { tmnxPppoePlcyEntry 22 }
    
tmnxPppoePlcyUniqueSessIdsPerSap OBJECT-TYPE
    SYNTAX      INTEGER {
                    perCaptureSap (1),
                    disabled      (2),
                    perMsap       (3)
                }
    MAX-ACCESS  read-create
    STATUS      current
    DESCRIPTION
        "The value tmnxPppoePlcyUniqueSessIdsPerSap specifies whether each
         PPPoE session on the same SAP gets a unique session-id.
         
         The value 'disabled' specifies that sessions belonging to the same
         SAP do not get a unique session-id. The session-id gets allocated
         the default way, meaning that the combination MAC address plus 
         session-id is unique.
         
         The value 'perCaptureSap' specifies that sessions created via a
         specific capture SAP get a unique session-id. This limits the total
         number sessions that can get created via a specific capture SAP to
         1023.
         
         The value 'perMsap' specifies that sessions belonging to the same 
         MSAP get a unique session-id. The session-ids are not unique over
         the corresponding capture SAP.
         
         For plain statically configured SAPs the values 'perCaptureSap' and
         'perMsap' result in the same. Sessions belonging to that SAP get a
         unique session-id." 
    DEFVAL { disabled }
    ::= { tmnxPppoePlcyEntry 23 }

tmnxPppoePlcyRejectDisabledNcp OBJECT-TYPE
    SYNTAX      TruthValue
    MAX-ACCESS  read-create
    STATUS      current
    DESCRIPTION
        "The value tmnxPppoePlcyRejectDisabledNcp specifies whether
         disabled NCP's (Network Control Protocol) are rejected or
         silently ignored.
         
         When the value of this object is set to 'true(1)'
         then disabled NCP's are explicitly rejected." 
    DEFVAL { false }
    ::= { tmnxPppoePlcyEntry 24 }

tmnxPppoePlcyLcpIgnoreMagic OBJECT-TYPE
    SYNTAX      TruthValue
    MAX-ACCESS  read-create
    STATUS      current
    DESCRIPTION
        "The value of tmnxPppoePlcyLcpIgnoreMagic specifies 
         if checking the Magic-Number field in LCP Echo-Request and 
         Echo-Reply messages is skipped.
         
         If the value of tmnxPppoePlcyLcpIgnoreMagic is equal to 'false',
         checking is performed.
         
         If the value of tmnxPppoePlcyLcpIgnoreMagic is equal to 'true',
         checking is not performed."
    REFERENCE
       "RFC 1661 PPP section 6.4. Magic-Number."
    DEFVAL { false }
    ::= { tmnxPppoePlcyEntry 30 }
    
tmnxPppoePlcySessionTimeout OBJECT-TYPE
    SYNTAX      Unsigned32 (0|1..31104000)
    UNITS       "seconds"
    MAX-ACCESS  read-create
    STATUS      current
    DESCRIPTION
        "The value of tmnxPppoePlcySessionTimeout specifies 
         the session timeout period to be used for this PPPOE session.
         The value '0' has the meaning of 'unlimited'"
    DEFVAL { 0 }
    ::= { tmnxPppoePlcyEntry 31 }

tmnxPppoePlcyAllowSameCidForDhcp OBJECT-TYPE
    SYNTAX      TruthValue
    MAX-ACCESS  read-create
    STATUS      current
    DESCRIPTION
        "The value of tmnxPppoePlcyAllowSameCidForDhcp specifies
         whether it is allowed to have multiple PPPoE sessions with the same
         MAC address and circuit-id for a specific SAP when using the internal
         DHCP client to retrieve the IP address from a local or remote DHCP
         server.
         
         When set to 'true', the PPPoE session ID will be included to select 
         the IP address.
         
         The value of tmnxPppoePlcyAllowSameCidForDhcp is only relevant
         while the value of tmnxPppoePlcyMaxSessionsPerMac is not equal
         to one."
    DEFVAL { false }
    ::= { tmnxPppoePlcyEntry 32 }
    
tmnxPppoePlcyReestablishSession OBJECT-TYPE
    SYNTAX      INTEGER {
                    disabled (1),
                    padr     (2)
                }
    MAX-ACCESS  read-create
    STATUS      current
    DESCRIPTION
        "The value of tmnxPppoePlcyReestablishSession specifies
         whether the setup of a new PPPoE session triggers the termination
         of an already existing session with the same MAC address.
         
         The value of tmnxPppoePlcyReestablishSession can only be set 
         different from 'disabled' if the value of 
         tmnxPppoePlcyMaxSessionsPerMac is equal to one.
         
         When set to 'disabled', no session will be deleted. When set to 
         'padr', the existing session will be deleted upon reception of the
         PADR."
    DEFVAL { disabled }
    ::= { tmnxPppoePlcyEntry 33 }

tmnxPppoePlcyDefaultUserName OBJECT-TYPE
    SYNTAX      TmnxPppoeUserNameOrEmpty
    MAX-ACCESS  read-create
    STATUS      current
    DESCRIPTION
        "The value of tmnxPppoePlcyDefaultUserName specifies
         the default PPP username.
         
         A non-empty value of this object is used when the PPP client
         (the 'peer') does not provide a PPP username during authentication.

         If the peer does not provide a PPP username during authentication 
         while there is no default PPP username specified, the PPP session
         cannot be established."
    DEFVAL { "" }
    ::= { tmnxPppoePlcyEntry 34 }

tmnxPppoePlcyDefaultPapPassword OBJECT-TYPE
    SYNTAX      TmnxAuthPassword 
    MAX-ACCESS  read-create
    STATUS      current
    DESCRIPTION
        "The value of tmnxPppoePlcyDefaultPapPassword specifies
         the default PPP password.
         
         A non-empty value of this object is used when the PPP client
         (the 'peer') does not provide a password during Password Authentication Protocol (PAP)
         authentication.

         An SNMP get request for the value of this object will result in
         a response with an empty string."
    DEFVAL { "" }
    ::= { tmnxPppoePlcyEntry 35 }

-- --------------------------------------------------------
-- tmnxPppoePlcyPppOptionTable
-- --------------------------------------------------------
tmnxPppoePlcyPppOptionTblLstChg OBJECT-TYPE
    SYNTAX      TimeStamp
    MAX-ACCESS  read-only
    STATUS      current
    DESCRIPTION
        "The value of tmnxPppoePlcyPppOptionTblLstChg indicates the
         sysUpTime at the time of the most recent management-initiated change
         to the tmnxPppoePlcyPppOptionTable."
    ::= { tmnxPppoeObjects 3 }

tmnxPppoePlcyPppOptionTable OBJECT-TYPE
    SYNTAX      SEQUENCE OF TmnxPppoePlcyPppOptionEntry
    MAX-ACCESS  not-accessible
    STATUS      current
    DESCRIPTION
        "The tmnxPppoePlcyPppOptionTable has an entry for each PPP option
         configured in the system."
    ::= { tmnxPppoeObjects 4 }

tmnxPppoePlcyPppOptionEntry OBJECT-TYPE
    SYNTAX      TmnxPppoePlcyPppOptionEntry
    MAX-ACCESS  not-accessible
    STATUS      current
    DESCRIPTION
        "Each row entry represents a PPP option configured in the system.

         Entries can be created and deleted via SNMP SET operations on the
         object tmnxPppoePlcyOptionRowStatus."
    INDEX { tmnxPppoePlcyName,
            tmnxPppoePlcyOptionProtocol,
            tmnxPppoePlcyOptionNumber }
    ::= { tmnxPppoePlcyPppOptionTable 1 }

TmnxPppoePlcyPppOptionEntry ::=
    SEQUENCE {
        tmnxPppoePlcyOptionProtocol      INTEGER,
        tmnxPppoePlcyOptionNumber        Unsigned32,
        tmnxPppoePlcyOptionRowStatus     RowStatus,
        tmnxPppoePlcyOptionLstMgmtChange TimeStamp,
        tmnxPppoePlcyOptionType          TmnxDhcpOptionType,
        tmnxPppoePlcyOptionValue         OCTET STRING
    }

tmnxPppoePlcyOptionProtocol OBJECT-TYPE
    SYNTAX      INTEGER {
                    lcp    (1),
                    ipcp   (2),
                    ipv6cp (3)
                }
    MAX-ACCESS  not-accessible
    STATUS      current
    DESCRIPTION
        "The value of tmnxPppoePlcyOptionProtocol specifies the PPP protocol
         for this option."
    ::= { tmnxPppoePlcyPppOptionEntry 1 }

tmnxPppoePlcyOptionNumber OBJECT-TYPE
    SYNTAX      Unsigned32 (0..255)
    MAX-ACCESS  not-accessible
    STATUS      current
    DESCRIPTION
        "The value of tmnxPppoePlcyOptionNumber specifies the number of this
         option."
    ::= { tmnxPppoePlcyPppOptionEntry 2 }

tmnxPppoePlcyOptionRowStatus OBJECT-TYPE
    SYNTAX      RowStatus
    MAX-ACCESS  read-create
    STATUS      current
    DESCRIPTION
        "The value of tmnxPppoePlcyOptionRowStatus controls the creation and
         deletion of rows in this table.

         The objects tmnxPppoePlcyOptionType and tmnxPppoePlcyOptionValue must
         be set when creating a new row."
    ::= { tmnxPppoePlcyPppOptionEntry 3 }

tmnxPppoePlcyOptionLstMgmtChange OBJECT-TYPE
    SYNTAX      TimeStamp
    MAX-ACCESS  read-only
    STATUS      current
    DESCRIPTION
        "The value of tmnxPppoePlcyOptionLstMgmtChange indicates the sysUpTime
         at the time of the most recent management-initiated change to this
         table row."
    ::= { tmnxPppoePlcyPppOptionEntry 4 }

tmnxPppoePlcyOptionType OBJECT-TYPE
    SYNTAX      TmnxDhcpOptionType
    MAX-ACCESS  read-create
    STATUS      current
    DESCRIPTION
        "The value of tmnxPppoePlcyOptionType specifies how the value of this
         option in stored in tmnxPppoePlcyOptionValue.

         This object is mandatory at creation time."
    ::= { tmnxPppoePlcyPppOptionEntry 5 }

tmnxPppoePlcyOptionValue OBJECT-TYPE
    SYNTAX      OCTET STRING (SIZE (0..127))
    MAX-ACCESS  read-create
    STATUS      current
    DESCRIPTION
        "The value of tmnxPppoePlcyOptionValue specifies the value of this
         option.

         This object is mandatory at creation time. A zero length value is only
         allowed when the value of tmnxPppoePlcyOptionType is 'hex'."
    ::= { tmnxPppoePlcyPppOptionEntry 6 }

-- --------------------------------------------------------
-- tmnxPppoeIesIfInfoTable
-- --------------------------------------------------------
tmnxPppoeIesIfInfoTableLastChg OBJECT-TYPE
    SYNTAX      TimeStamp
    MAX-ACCESS  read-only
    STATUS      current
    DESCRIPTION
        "The value of tmnxPppoeIesIfInfoTableLastChg indicates the sysUpTime at
         the time of the most recent management-initiated change to the
         tmnxPppoeIesIfInfoTable."
    ::= { tmnxPppoeObjects 5 }

tmnxPppoeIesIfInfoTable OBJECT-TYPE
    SYNTAX      SEQUENCE OF TmnxPppoeIesIfInfoEntry
    MAX-ACCESS  not-accessible
    STATUS      current
    DESCRIPTION
        "A table that contains IES interface PPPoE configuration information.

         A row is automatically created in the tmnxPppoeIesIfInfoTable for an 
         entry in the iesIfTable where either the value of the object iesIfType 
         - is equal to 'group (3)' and the value of iesIfGroupInterfaceType is 
         equal to 'plain', or 
         - equal to 'subscriber (2)' while the value
         of the objects iesIfFwdServId and iesIfFwdSubIf are not equal to zero.
         
         The first case is referred to as 'group interface' and the second as
         'retailer interface'."
    ::= { tmnxPppoeObjects 6 }

tmnxPppoeIesIfInfoEntry OBJECT-TYPE
    SYNTAX      TmnxPppoeIesIfInfoEntry
    MAX-ACCESS  not-accessible
    STATUS      current
    DESCRIPTION
        "PPPoE specific information about an IES interface."
    INDEX { svcId,
            iesIfIndex }
    ::= { tmnxPppoeIesIfInfoTable 1 }

TmnxPppoeIesIfInfoEntry ::=
    SEQUENCE {
        tmnxPppoeIesIfLastChg            TimeStamp,
        tmnxPppoeIesIfDescription        TItemDescription,
        tmnxPppoeIesIfAdminState         TmnxPppoeAdminStatus,
        tmnxPppoeIesIfPolicy             TNamedItem,
        tmnxPppoeIesIfSessionLimit       Unsigned32,
        tmnxPppoeIesIfSapSessionLimit    Unsigned32,
        tmnxPppoeIesIfPapChapUserDb      TNamedItemOrEmpty,
        tmnxPppoeIesIfUserDb             TNamedItemOrEmpty,
        tmnxPppoeIesIfDhcpcCcagOriginSap TruthValue,
        tmnxPppoeIesIfAntiSpoofing       INTEGER,
        tmnxPppoeIesIfDhcpcInclOptString DisplayString
    }

tmnxPppoeIesIfLastChg OBJECT-TYPE
    SYNTAX      TimeStamp
    MAX-ACCESS  read-only
    STATUS      current
    DESCRIPTION
        "The value of tmnxPppoeIesIfLastChg indicates the sysUpTime at
         the time of the most recent management-initiated change to this
         table row."
    ::= { tmnxPppoeIesIfInfoEntry 1 }

tmnxPppoeIesIfDescription OBJECT-TYPE
    SYNTAX      TItemDescription
    MAX-ACCESS  read-write
    STATUS      current
    DESCRIPTION
        "The value of the object tmnxPppoeIesIfDescription specifies a user
         provided description for PPPoE on this IES interface.

         It consists of any printable, seven-bit ASCII characters up to 80
         characters in length."
    DEFVAL { "" }
    ::= { tmnxPppoeIesIfInfoEntry 2 }

tmnxPppoeIesIfAdminState OBJECT-TYPE
    SYNTAX      TmnxPppoeAdminStatus
    MAX-ACCESS  read-write
    STATUS      current
    DESCRIPTION
        "The value of the object tmnxPppoeIesIfAdminState specifies the
         administrative state of PPPoE on this IES interface.

         The default value of this object is equal to 'disabled', 
         except for a retailer interface, where it is equal to 'enabled'.
         
         In case of a retailer interface, setting the value of this object
         (to 'disabled') is not allowed."
    ::= { tmnxPppoeIesIfInfoEntry 3 }

tmnxPppoeIesIfPolicy OBJECT-TYPE
    SYNTAX      TNamedItem
    MAX-ACCESS  read-write
    STATUS      current
    DESCRIPTION
        "The value of tmnxPppoeIesIfPolicy specifies the PPPoE policy
         applicable on this IES interface. The corresponding policy is defined
         in tmnxPppoePlcyTable.
         
         In case of a retailer interface, the value of this object
         is irrelevant and setting it (to a value other than default) is not 
         allowed."
    DEFVAL { "default" }
    ::= { tmnxPppoeIesIfInfoEntry 4 }

tmnxPppoeIesIfSessionLimit OBJECT-TYPE
    SYNTAX      Unsigned32 (1..262143)
    MAX-ACCESS  read-write
    STATUS      current
    DESCRIPTION
        "The value of tmnxPppoeIesIfSessionLimit specifies the maximum
         number of PPPoE sessions allowed on this IES interface."
    DEFVAL { 1 }
    ::= { tmnxPppoeIesIfInfoEntry 5 }

tmnxPppoeIesIfSapSessionLimit OBJECT-TYPE
    SYNTAX      Unsigned32 (1..65535)
    MAX-ACCESS  read-write
    STATUS      current
    DESCRIPTION
        "The value of tmnxPppoeIesIfSapSessionLimit specifies the maximum
         number of PPPoE sessions allowed on each SAP belonging to this IES
         interface.
         
         In case of a retailer interface, the value of this object is
         irrelevant, and setting it (to a value other than 1) is not allowed."
    DEFVAL { 1 }
    ::= { tmnxPppoeIesIfInfoEntry 6 }

tmnxPppoeIesIfPapChapUserDb OBJECT-TYPE
    SYNTAX      TNamedItemOrEmpty
    MAX-ACCESS  read-write
    STATUS      obsolete
    DESCRIPTION
        "The value of tmnxPppoeIesIfPapChapUserDb specifies the local user
         database to use for PPP PAP/CHAP authentication.

         If no PPP authentication is required, the value of this object must
         be set to the empty string."
    DEFVAL { "" }
    ::= { tmnxPppoeIesIfInfoEntry 7 }

tmnxPppoeIesIfUserDb OBJECT-TYPE
    SYNTAX      TNamedItemOrEmpty
    MAX-ACCESS  read-write
    STATUS      current
    DESCRIPTION
        "The value of tmnxPppoeIesIfUserDb specifies the local user database
         to use for PPPoE PADI or PPP PAP/CHAP based authentication.

         If no authentication with the local user database is required, the
         value of this object must be set to the empty string.
         
         In case of a retailer interface, setting the value of this object
         (to a value other than the empty string) is not allowed."
    DEFVAL { "" }
    ::= { tmnxPppoeIesIfInfoEntry 8 }

tmnxPppoeIesIfDhcpcCcagOriginSap OBJECT-TYPE
    SYNTAX      TruthValue
    MAX-ACCESS  read-write
    STATUS      current
    DESCRIPTION
        "In case this interface is connected to a VPLS via a CCA (Cross Connect
         Adaptor) MDA, the value of tmnxPppoeIesIfDhcpcCcagOriginSap specifies
         whether the system includes the original VPLS SAP in the circuit-id
         option to send to the DHCP server(s).
         
         In case of a retailer interface, the value of this object is
         irrelevant, and setting it (to a value other than false) is not
         allowed."
    DEFVAL { false }
    ::= { tmnxPppoeIesIfInfoEntry 9 }

tmnxPppoeIesIfAntiSpoofing OBJECT-TYPE
    SYNTAX      INTEGER {
                    macSid   (1),
                    macSidIp (2)
                }
    MAX-ACCESS  read-write
    STATUS      current
    DESCRIPTION
        "The value of tmnxPppoeIesIfAntiSpoofing specifies the type of PPPoE
         anti-spoof filtering to use."
    DEFVAL { macSid }
    ::= { tmnxPppoeIesIfInfoEntry 10 }

tmnxPppoeIesIfDhcpcInclOptString OBJECT-TYPE
    SYNTAX      DisplayString (SIZE (0..32))
    MAX-ACCESS  read-write
    STATUS      obsolete
    DESCRIPTION
        "The value of tmnxPppoeIesIfDhcpcInclOptString specifies the string that
         goes into the Alcatel-Lucent vendor specific sub-option of option 82."
    DEFVAL { "" }
    ::= { tmnxPppoeIesIfInfoEntry 11 }

-- --------------------------------------------------------
-- tmnxPppoeSapStatsTable
-- --------------------------------------------------------
tmnxPppoeSapStatsTable OBJECT-TYPE
    SYNTAX      SEQUENCE OF TmnxPppoeSapStatsEntry
    MAX-ACCESS  not-accessible
    STATUS      current
    DESCRIPTION
        "A table that contains statistics on PPPoE per SAP."
    ::= { tmnxPppoeObjects 7 }

tmnxPppoeSapStatsEntry OBJECT-TYPE
    SYNTAX      TmnxPppoeSapStatsEntry
    MAX-ACCESS  not-accessible
    STATUS      current
    DESCRIPTION
        "PPPoE statistics about a SAP."
    INDEX { svcId,
            sapPortId,
            sapEncapValue }
    ::= { tmnxPppoeSapStatsTable 1 }

TmnxPppoeSapStatsEntry ::=
    SEQUENCE {
        tmnxPppoeSapRxPadi            Counter32,
        tmnxPppoeSapRxPadr            Counter32,
        tmnxPppoeSapRxPadt            Counter32,
        tmnxPppoeSapRxSession         Counter32,
        tmnxPppoeSapRxInvalidVersion  Counter32,
        tmnxPppoeSapRxInvalidType     Counter32,
        tmnxPppoeSapRxInvalidCode     Counter32,
        tmnxPppoeSapRxInvalidSession  Counter32,
        tmnxPppoeSapRxInvalidLen      Counter32,
        tmnxPppoeSapRxInvalidTags     Counter32,
        tmnxPppoeSapRxInvalidAcCookie Counter32,
        tmnxPppoeSapRxDropped         Counter32,
        tmnxPppoeSapTxPado            Counter32,
        tmnxPppoeSapTxPads            Counter32,
        tmnxPppoeSapTxPadt            Counter32,
        tmnxPppoeSapTxSession         Counter32,
        tmnxPppoeSapRxInvalidMac      Counter32
    }

tmnxPppoeSapRxPadi OBJECT-TYPE
    SYNTAX      Counter32
    MAX-ACCESS  read-only
    STATUS      current
    DESCRIPTION
        "The value of tmnxPppoeSapRxPadi indicates the number of PADI
         (PPPoE Active Discovery Initiation) packets received on this SAP."
    ::= { tmnxPppoeSapStatsEntry 1 }

tmnxPppoeSapRxPadr OBJECT-TYPE
    SYNTAX      Counter32
    MAX-ACCESS  read-only
    STATUS      current
    DESCRIPTION
        "The value of tmnxPppoeSapRxPadr indicates the number of PADR
         (PPPoE Active Discovery Request) packets received on this SAP."
    ::= { tmnxPppoeSapStatsEntry 2 }

tmnxPppoeSapRxPadt OBJECT-TYPE
    SYNTAX      Counter32
    MAX-ACCESS  read-only
    STATUS      current
    DESCRIPTION
        "The value of tmnxPppoeSapRxPadt indicates the number of PADT
         (PPPoE Active Discovery Terminate) packets received on this SAP."
    ::= { tmnxPppoeSapStatsEntry 3 }

tmnxPppoeSapRxSession OBJECT-TYPE
    SYNTAX      Counter32
    MAX-ACCESS  read-only
    STATUS      current
    DESCRIPTION
        "The value of tmnxPppoeSapRxSession indicates the number packets
         received during the PPP session stage on this SAP."
    ::= { tmnxPppoeSapStatsEntry 4 }

tmnxPppoeSapRxInvalidVersion OBJECT-TYPE
    SYNTAX      Counter32
    MAX-ACCESS  read-only
    STATUS      current
    DESCRIPTION
        "The value of tmnxPppoeSapRxInvalidVersion indicates the number of
         PPPoE packets received with an invalid version field."
    ::= { tmnxPppoeSapStatsEntry 5 }

tmnxPppoeSapRxInvalidType OBJECT-TYPE
    SYNTAX      Counter32
    MAX-ACCESS  read-only
    STATUS      current
    DESCRIPTION
        "The value of tmnxPppoeSapRxInvalidType indicates the number of PPPoE
         packets received with an invalid type field."
    ::= { tmnxPppoeSapStatsEntry 6 }

tmnxPppoeSapRxInvalidCode OBJECT-TYPE
    SYNTAX      Counter32
    MAX-ACCESS  read-only
    STATUS      current
    DESCRIPTION
        "The value of tmnxPppoeSapRxInvalidCode indicates the number of PPPoE
         packets received with an invalid code field."
    ::= { tmnxPppoeSapStatsEntry 7 }

tmnxPppoeSapRxInvalidSession OBJECT-TYPE
    SYNTAX      Counter32
    MAX-ACCESS  read-only
    STATUS      current
    DESCRIPTION
        "The value of tmnxPppoeSapRxInvalidSession indicates the number of
         PPPoE packets received with an invalid session-id field."
    ::= { tmnxPppoeSapStatsEntry 8 }

tmnxPppoeSapRxInvalidLen OBJECT-TYPE
    SYNTAX      Counter32
    MAX-ACCESS  read-only
    STATUS      current
    DESCRIPTION
        "The value of tmnxPppoeSapRxInvalidLen indicates the number of PPPoE
         packets received with an invalid length field."
    ::= { tmnxPppoeSapStatsEntry 9 }

tmnxPppoeSapRxInvalidTags OBJECT-TYPE
    SYNTAX      Counter32
    MAX-ACCESS  read-only
    STATUS      current
    DESCRIPTION
        "The value of tmnxPppoeSapRxInvalidTags indicates the number of PPPoE
         Active Discovery packets received with invalid tags."
    ::= { tmnxPppoeSapStatsEntry 10 }

tmnxPppoeSapRxInvalidAcCookie OBJECT-TYPE
    SYNTAX      Counter32
    MAX-ACCESS  read-only
    STATUS      current
    DESCRIPTION
        "The value of tmnxPppoeSapRxInvalidAcCookie indicates the number of
         PPPoE Active Discovery packets received with an invalid AC-Cookie
         tag."
    ::= { tmnxPppoeSapStatsEntry 11 }

tmnxPppoeSapRxDropped OBJECT-TYPE
    SYNTAX      Counter32
    MAX-ACCESS  read-only
    STATUS      current
    DESCRIPTION
        "The value of tmnxPppoeSapRxDropped indicates the number of dropped
         PPPoE packets."
    ::= { tmnxPppoeSapStatsEntry 12 }

tmnxPppoeSapTxPado OBJECT-TYPE
    SYNTAX      Counter32
    MAX-ACCESS  read-only
    STATUS      current
    DESCRIPTION
        "The value of tmnxPppoeSapTxPado indicates the number of PADO
         (PPPoE Active Discovery Offer) packets transmitted on this SAP."
    ::= { tmnxPppoeSapStatsEntry 13 }

tmnxPppoeSapTxPads OBJECT-TYPE
    SYNTAX      Counter32
    MAX-ACCESS  read-only
    STATUS      current
    DESCRIPTION
        "The value of tmnxPppoeSapTxPads indicates the number of PADS
         (PPPoE Active Discovery Session) packets transmitted on this SAP."
    ::= { tmnxPppoeSapStatsEntry 14 }

tmnxPppoeSapTxPadt OBJECT-TYPE
    SYNTAX      Counter32
    MAX-ACCESS  read-only
    STATUS      current
    DESCRIPTION
        "The value of tmnxPppoeSapTxPadt indicates the number of PADT
         (PPPoE Active Discovery Terminate) packets transmitted on this SAP."
    ::= { tmnxPppoeSapStatsEntry 15 }

tmnxPppoeSapTxSession OBJECT-TYPE
    SYNTAX      Counter32
    MAX-ACCESS  read-only
    STATUS      current
    DESCRIPTION
        "The value of tmnxPppoeSapTxSession indicates the number packets
         transmitted during the PPP session stage on this SAP."
    ::= { tmnxPppoeSapStatsEntry 16 }

tmnxPppoeSapRxInvalidMac OBJECT-TYPE
    SYNTAX      Counter32
    MAX-ACCESS  read-only
    STATUS      current
    DESCRIPTION
        "The value of tmnxPppoeSapRxInvalidMac indicates the number of
         PPPoE packets received with an invalid MAC address."
    ::= { tmnxPppoeSapStatsEntry 17 }

-- --------------------------------------------------------
-- tmnxPppoeSessionTable
-- --------------------------------------------------------
tmnxPppoeSessionTable OBJECT-TYPE
    SYNTAX      SEQUENCE OF TmnxPppoeSessionEntry
    MAX-ACCESS  not-accessible
    STATUS      current
    DESCRIPTION
        "A table that contains PPPoE sessions."
    ::= { tmnxPppoeObjects 8 }

tmnxPppoeSessionEntry OBJECT-TYPE
    SYNTAX      TmnxPppoeSessionEntry
    MAX-ACCESS  not-accessible
    STATUS      current
    DESCRIPTION
        "Information about a specific PPPoE session.
        
         In release 9.0 and higher, the actual information
         is in the SUBSCRIBER-MGMT-MIB::tmnxSubPppTable.
         
         The corresponding row in that table can be directly retrieved using
         the value of the object tmnxPppoeSessionSubPppIndex."
    INDEX { svcId,
            sapPortId,
            sapEncapValue,
            tmnxPppoeSessionMac,
            tmnxPppoeSessionId }
    ::= { tmnxPppoeSessionTable 1 }

TmnxPppoeSessionEntry ::=
    SEQUENCE {
        tmnxPppoeSessionMac              MacAddress,
        tmnxPppoeSessionId               TmnxPppoeSessionId,
        tmnxPppoeSessionUpTime           TimeTicks,
        tmnxPppoeSessionLcpState         TmnxPppCpState,
        tmnxPppoeSessionIpcpState        TmnxPppCpState,
        tmnxPppoeSessionPppMtu           Unsigned32,
        tmnxPppoeSessionPppAuthProtocol  INTEGER,
        tmnxPppoeSessionPppUserName      TmnxPppoeUserNameOrEmpty,
        tmnxPppoeSessionSubIdent         TmnxSubIdentStringOrEmpty,
        tmnxPppoeSessionOriginSubIdent   TmnxPppoeSessionInfoOrigin,
        tmnxPppoeSessionSubProfString    TmnxSubProfileStringOrEmpty,
        tmnxPppoeSessionSlaProfString    TmnxSlaProfileStringOrEmpty,
        tmnxPppoeSessionAncpString       TmnxAncpStringOrZero,
        tmnxPppoeSessionInterDestId      TmnxSubMgtIntDestIdOrEmpty,
        tmnxPppoeSessionAppProfString    TmnxAppProfileStringOrEmpty,
        tmnxPppoeSessionOriginStrings    TmnxPppoeSessionInfoOrigin,
        tmnxPppoeSessionSessionTimeout   Unsigned32,
        tmnxPppoeSessionIpAddrType       InetAddressType,
        tmnxPppoeSessionIpAddr           InetAddress,
        tmnxPppoeSessionPrimaryDnsType   InetAddressType,
        tmnxPppoeSessionPrimaryDns       InetAddress,
        tmnxPppoeSessionSecondryDnsType  InetAddressType,
        tmnxPppoeSessionSecondryDns      InetAddress,
        tmnxPppoeSessionPrimaryNbnsType  InetAddressType,
        tmnxPppoeSessionPrimaryNbns      InetAddress,
        tmnxPppoeSessionSecondryNbnsType InetAddressType,
        tmnxPppoeSessionSecondryNbns     InetAddress,
        tmnxPppoeSessionOriginIpcpInfo   TmnxPppoeSessionInfoOrigin,
        tmnxPppoeSessionCircuitId        OCTET STRING,
        tmnxPppoeSessionRemoteId         OCTET STRING,
        tmnxPppoeSessionAddressPool      DisplayString,
        tmnxPppoeSessionType             TmnxPppoeSessionType,
        tmnxPppoeSessionRetailerSvcId    TmnxServId,
        tmnxPppoeSessionRetailerIf       InterfaceIndexOrZero,
        tmnxPppoeSessionL2tpVrtrId       TmnxVRtrIDOrZero,
        tmnxPppoeSessionL2tpConnectionId Unsigned32,
        tmnxPppoeSessionServiceName      DisplayString,
        tmnxPppoeSessionCategoryMapName  TNamedItemOrEmpty,
        tmnxPppoeSessionRadiusClassAttr  OCTET STRING,
        tmnxPppoeSessionRadiusUserName   DisplayString,

        tmnxPppoeSessionIpv6cpState      TmnxPppCpState,
        tmnxPppoeSessionInterfaceId      OCTET STRING,
        tmnxPppoeSessionOriginIpv6cpInfo TmnxPppoeSessionInfoOrigin,
        tmnxPppoeSessionIpv6DnsType      InetAddressType,
        tmnxPppoeSessionIpv6Dns1         InetAddress,
        tmnxPppoeSessionIpv6Dns2         InetAddress,
        tmnxPppoeSessionIpv6DelPfxType   InetAddressType,
        tmnxPppoeSessionIpv6DelPfxLen    InetAddressPrefixLength,
        tmnxPppoeSessionIpv6DelPfx       InetAddress,
        tmnxPppoeSessionIpv6PrefixType   InetAddressType,
        tmnxPppoeSessionIpv6PrefixLen    InetAddressPrefixLength,
        tmnxPppoeSessionIpv6Prefix       InetAddress,
        tmnxPppoeSessionSubPppIndex      Unsigned32
    }

tmnxPppoeSessionMac OBJECT-TYPE
    SYNTAX      MacAddress
    MAX-ACCESS  not-accessible
    STATUS      current
    DESCRIPTION
        "The value of tmnxPppoeSessionMac indicates the MAC address of the
         PPPoE session."
    ::= { tmnxPppoeSessionEntry 1 }

tmnxPppoeSessionId OBJECT-TYPE
    SYNTAX      TmnxPppoeSessionId
    MAX-ACCESS  not-accessible
    STATUS      current
    DESCRIPTION
        "The value of tmnxPppoeSessionId indicates the session id of the PPPoE
         session."
    ::= { tmnxPppoeSessionEntry 2 }

tmnxPppoeSessionUpTime OBJECT-TYPE
    SYNTAX      TimeTicks
    MAX-ACCESS  read-only
    STATUS      obsolete
    DESCRIPTION
        "The value of tmnxPppoeSessionUpTime indicates how long (in hundredths
         of a second) that the session already exists in this table."
    ::= { tmnxPppoeSessionEntry 3 }

tmnxPppoeSessionLcpState OBJECT-TYPE
    SYNTAX      TmnxPppCpState
    MAX-ACCESS  read-only
    STATUS      obsolete
    DESCRIPTION
        "The value of tmnxPppoeSessionLcpState indicates the obsolete state of
         the PPP Link Control Protocol of the PPPoE session."
    ::= { tmnxPppoeSessionEntry 4 }

tmnxPppoeSessionIpcpState OBJECT-TYPE
    SYNTAX      TmnxPppCpState
    MAX-ACCESS  read-only
    STATUS      obsolete
    DESCRIPTION
        "The value of tmnxPppoeSessionIpcpState indicates the obsolete state of
         the PPP IP Control Protocol of the PPPoE session."
    ::= { tmnxPppoeSessionEntry 5 }

tmnxPppoeSessionPppMtu OBJECT-TYPE
    SYNTAX      Unsigned32
    UNITS       "bytes"
    MAX-ACCESS  read-only
    STATUS      obsolete
    DESCRIPTION
        "The value of tmnxPppoeSessionPppMtu indicates the PPP MTU of the
         PPPoE session."
    ::= { tmnxPppoeSessionEntry 6 }

tmnxPppoeSessionPppAuthProtocol OBJECT-TYPE
    SYNTAX      INTEGER {
                    none (1),
                    pap  (2),
                    chap (3)
                }
    MAX-ACCESS  read-only
    STATUS      obsolete
    DESCRIPTION
        "The value of tmnxPppoeSessionPppAuthProtocol indicates the PPP
         protocol used to authenticate the PPPoE session.

         The value 'none' indicates that no PPP authentication was done. The
         value 'pap' indicates that authentication was done via the Password
         Authentication Protocol. The value 'chap' indicates that
         authentication was done via the Challenge-Handshake Authentication
         Protocol."
    ::= { tmnxPppoeSessionEntry 7 }

tmnxPppoeSessionPppUserName OBJECT-TYPE
    SYNTAX      TmnxPppoeUserNameOrEmpty
    MAX-ACCESS  read-only
    STATUS      obsolete
    DESCRIPTION
        "The value of tmnxPppoeSessionPppUserName indicates the user name
         learned during the PPP authentication phase."
    ::= { tmnxPppoeSessionEntry 8 }

tmnxPppoeSessionSubIdent OBJECT-TYPE
    SYNTAX      TmnxSubIdentStringOrEmpty
    MAX-ACCESS  read-only
    STATUS      obsolete
    DESCRIPTION
        "The value of tmnxPppoeSessionSubIdent indicates the subscriber
         applicable for this PPPoE session.

         The value of tmnxPppoeSessionOriginSubIdent indicates from what
         source this subscriber identification was received."
    ::= { tmnxPppoeSessionEntry 9 }

tmnxPppoeSessionOriginSubIdent OBJECT-TYPE
    SYNTAX      TmnxPppoeSessionInfoOrigin
    MAX-ACCESS  read-only
    STATUS      obsolete
    DESCRIPTION
        "The value of tmnxPppoeSessionOriginSubIdent indicates which source
         provided the subscriber."
    ::= { tmnxPppoeSessionEntry 10 }

tmnxPppoeSessionSubProfString OBJECT-TYPE
    SYNTAX      TmnxSubProfileStringOrEmpty
    MAX-ACCESS  read-only
    STATUS      obsolete
    DESCRIPTION
        "The value of tmnxPppoeSessionSubProfString indicates the subscriber
         profile string applicable for this PPPoE session.

         The value of tmnxPppoeSessionOriginStrings indicates from what source
         this string was received."
    ::= { tmnxPppoeSessionEntry 11 }

tmnxPppoeSessionSlaProfString OBJECT-TYPE
    SYNTAX      TmnxSlaProfileStringOrEmpty
    MAX-ACCESS  read-only
    STATUS      obsolete
    DESCRIPTION
        "The value of tmnxPppoeSessionSlaProfString indicates the SLA profile
         string applicable for this PPPoE session.

         The value of tmnxPppoeSessionOriginStrings indicates from what source
         this string was received."
    ::= { tmnxPppoeSessionEntry 12 }

tmnxPppoeSessionAncpString OBJECT-TYPE
    SYNTAX      TmnxAncpStringOrZero
    MAX-ACCESS  read-only
    STATUS      obsolete
    DESCRIPTION
        "The value of tmnxPppoeSessionAncpString indicates the ANCP string
         applicable for this PPPoE session.

         The value of tmnxPppoeSessionOriginStrings indicates from what source
         this string was received."
    ::= { tmnxPppoeSessionEntry 13 }

tmnxPppoeSessionInterDestId OBJECT-TYPE
    SYNTAX      TmnxSubMgtIntDestIdOrEmpty
    MAX-ACCESS  read-only
    STATUS      obsolete
    DESCRIPTION
        "The value of tmnxPppoeSessionInterDestId indicates the intermediate
         destination identifier applicable for this PPPoE session.

         The value of tmnxPppoeSessionOriginStrings indicates from what source
         this string was received."
    ::= { tmnxPppoeSessionEntry 14 }

tmnxPppoeSessionAppProfString OBJECT-TYPE
    SYNTAX      TmnxAppProfileStringOrEmpty
    MAX-ACCESS  read-only
    STATUS      obsolete
    DESCRIPTION
        "The value of tmnxPppoeSessionAppProfString indicates the application
         profile string applicable for this PPPoE session.

         The value of tmnxPppoeSessionOriginStrings indicates from what source
         this string was received."
    ::= { tmnxPppoeSessionEntry 15 }

tmnxPppoeSessionOriginStrings OBJECT-TYPE
    SYNTAX      TmnxPppoeSessionInfoOrigin
    MAX-ACCESS  read-only
    STATUS      obsolete
    DESCRIPTION
        "The value of tmnxPppoeSessionOriginStrings indicates which source
         provided the subscriber identification strings
         (subscriber profile string, SLA profile string, ANCP string,
         intermediate destination identifier and application profile string)."
    ::= { tmnxPppoeSessionEntry 16 }

tmnxPppoeSessionSessionTimeout OBJECT-TYPE
    SYNTAX      Unsigned32 (0..65535)
    UNITS       "seconds"
    MAX-ACCESS  read-only
    STATUS      obsolete
    DESCRIPTION
        "The value of tmnxPppoeSessionSessionTimeout indicates the session
         timeout received from the Radius server (if applicable)."
    ::= { tmnxPppoeSessionEntry 17 }

tmnxPppoeSessionIpAddrType OBJECT-TYPE
    SYNTAX      InetAddressType
    MAX-ACCESS  read-only
    STATUS      obsolete
    DESCRIPTION
        "The value of tmnxPppoeSessionIpAddrType indicates the address type of
         tmnxPppoeSessionIpAddr."
    ::= { tmnxPppoeSessionEntry 18 }

tmnxPppoeSessionIpAddr OBJECT-TYPE
    SYNTAX      InetAddress (SIZE (0|4))
    MAX-ACCESS  read-only
    STATUS      obsolete
    DESCRIPTION
        "The value of tmnxPppoeSessionIpAddr indicates the IP address of the
         PPPoE session.

         The value of tmnxPppoeSessionOriginIpcpInfo indicates from what
         source this IP address was received."
    ::= { tmnxPppoeSessionEntry 19 }

tmnxPppoeSessionPrimaryDnsType OBJECT-TYPE
    SYNTAX      InetAddressType
    MAX-ACCESS  read-only
    STATUS      obsolete
    DESCRIPTION
        "The value of tmnxPppoeSessionPrimaryDnsType indicates the address
         type of tmnxPppoeSessionPrimaryDns."
    ::= { tmnxPppoeSessionEntry 20 }

tmnxPppoeSessionPrimaryDns OBJECT-TYPE
    SYNTAX      InetAddress (SIZE (0|4))
    MAX-ACCESS  read-only
    STATUS      obsolete
    DESCRIPTION
        "The value of tmnxPppoeSessionPrimaryDns indicates the primary DNS
         server.

         The value of this object is ''H when not applicable.

         The value of tmnxPppoeSessionOriginIpcpInfo indicates from what
         source this IP address was received."
    ::= { tmnxPppoeSessionEntry 21 }

tmnxPppoeSessionSecondryDnsType OBJECT-TYPE
    SYNTAX      InetAddressType
    MAX-ACCESS  read-only
    STATUS      obsolete
    DESCRIPTION
        "The value of tmnxPppoeSessionSecondryDnsType indicates the address
         type of tmnxPppoeSessionSecondryDns."
    ::= { tmnxPppoeSessionEntry 22 }

tmnxPppoeSessionSecondryDns OBJECT-TYPE
    SYNTAX      InetAddress (SIZE (0|4))
    MAX-ACCESS  read-only
    STATUS      obsolete
    DESCRIPTION
        "The value of tmnxPppoeSessionSecondryDns indicates the secondary DNS
         server.

         The value of this object is ''H when not applicable.

         The value of tmnxPppoeSessionOriginIpcpInfo indicates from what
         source this IP address was received."
    ::= { tmnxPppoeSessionEntry 23 }

tmnxPppoeSessionPrimaryNbnsType OBJECT-TYPE
    SYNTAX      InetAddressType
    MAX-ACCESS  read-only
    STATUS      obsolete
    DESCRIPTION
        "The value of tmnxPppoeSessionPrimaryNbnsType indicates the address
         type of tmnxPppoeSessionPrimaryNbns."
    ::= { tmnxPppoeSessionEntry 24 }

tmnxPppoeSessionPrimaryNbns OBJECT-TYPE
    SYNTAX      InetAddress (SIZE (0|4))
    MAX-ACCESS  read-only
    STATUS      obsolete
    DESCRIPTION
        "The value of tmnxPppoeSessionPrimaryNbns indicates the primary NBNS
         server.

         The value of this object is ''H when not applicable.

         The value of tmnxPppoeSessionOriginIpcpInfo indicates from what
         source this IP address was received."
    ::= { tmnxPppoeSessionEntry 25 }

tmnxPppoeSessionSecondryNbnsType OBJECT-TYPE
    SYNTAX      InetAddressType
    MAX-ACCESS  read-only
    STATUS      obsolete
    DESCRIPTION
        "The value of tmnxPppoeSessionSecondryNbnsType indicates the address
         type of tmnxPppoeSessionSecondryNbns."
    ::= { tmnxPppoeSessionEntry 26 }

tmnxPppoeSessionSecondryNbns OBJECT-TYPE
    SYNTAX      InetAddress (SIZE(0|4))
    MAX-ACCESS  read-only
    STATUS      obsolete
    DESCRIPTION
        "The value of tmnxPppoeSessionSecondryNbns indicates the secondary
         NBNS server.

         The value of this object is ''H when not applicable.

         The value of tmnxPppoeSessionOriginIpcpInfo indicates from what
         source this IP address was received."
    ::= { tmnxPppoeSessionEntry 27 }

tmnxPppoeSessionOriginIpcpInfo OBJECT-TYPE
    SYNTAX      TmnxPppoeSessionInfoOrigin
    MAX-ACCESS  read-only
    STATUS      obsolete
    DESCRIPTION
        "The value of tmnxPppoeSessionOriginIpcpInfo indicates which source
         provided the IPCP information (IP, DNS and NBNS addresses)."
    ::= { tmnxPppoeSessionEntry 28 }

tmnxPppoeSessionCircuitId OBJECT-TYPE
    SYNTAX      OCTET STRING (SIZE (0..256))
    MAX-ACCESS  read-only
    STATUS      obsolete
    DESCRIPTION
        "The value of tmnxPppoeSessionCircuitId indicates the value of the
         circuit-id sub-option inserted by the PPPoE intermediate agent."
    ::= { tmnxPppoeSessionEntry 29 }

tmnxPppoeSessionRemoteId OBJECT-TYPE
    SYNTAX      OCTET STRING (SIZE (0..256))
    MAX-ACCESS  read-only
    STATUS      obsolete
    DESCRIPTION
        "The value of tmnxPppoeSessionRemoteId indicates the value of the
         remote-id sub-option inserted by the PPPoE intermediate agent."
    ::= { tmnxPppoeSessionEntry 30 }

tmnxPppoeSessionAddressPool OBJECT-TYPE
    SYNTAX      DisplayString (SIZE (0..32))
    MAX-ACCESS  read-only
    STATUS      obsolete
    DESCRIPTION
        "The value of tmnxPppoeSessionAddressPool indicates the IP address pool
         which is used to search for an IP address for this session."
    ::= { tmnxPppoeSessionEntry 31 }

tmnxPppoeSessionType OBJECT-TYPE
    SYNTAX      TmnxPppoeSessionType
    MAX-ACCESS  read-only
    STATUS      obsolete
    DESCRIPTION
        "The value of tmnxPppoeSessionType indicates the type of this
         session."
    ::= { tmnxPppoeSessionEntry 32 }

tmnxPppoeSessionRetailerSvcId OBJECT-TYPE
    SYNTAX      TmnxServId
    MAX-ACCESS  read-only
    STATUS      obsolete
    DESCRIPTION
        "The value of tmnxPppoeSessionRetailerSvcId indicates the service ID of
         the retailer VPRN service to which this session belongs. If the value
         of this object is non-zero, the session belongs to a retailer VPRN."
    ::= { tmnxPppoeSessionEntry 33 }

tmnxPppoeSessionRetailerIf OBJECT-TYPE
    SYNTAX      InterfaceIndexOrZero
    MAX-ACCESS  read-only
    STATUS      obsolete
    DESCRIPTION
        "The value of tmnxPppoeSessionRetailerIf indicates the interface index
         of the retailer VPRN interface to which this session belongs. If the
         value of this object is non-zero, the session belongs to a retailer
         VPRN."
    ::= { tmnxPppoeSessionEntry 34 }

tmnxPppoeSessionL2tpVrtrId OBJECT-TYPE
    SYNTAX      TmnxVRtrIDOrZero
    MAX-ACCESS  read-only
    STATUS      obsolete
    DESCRIPTION
        "The value of tmnxPppoeSessionL2tpVrtrId indicates the virtual router 
         ID of the L2TP session associated with this PPPoE session. 
         
         If there is no L2TP session associated with this PPPoE session, the
         value of this object is equal to zero."
    ::= { tmnxPppoeSessionEntry 35 }

tmnxPppoeSessionL2tpConnectionId OBJECT-TYPE
    SYNTAX      Unsigned32
    MAX-ACCESS  read-only
    STATUS      obsolete
    DESCRIPTION
        "The value of tmnxPppoeSessionL2tpVrtrId indicates the connection 
         ID of the L2TP session associated with this PPPoE session.
         
         The values of tmnxPppoeSessionL2tpVrtrId and 
         tmnxPppoeSessionL2tpConnectionId are the index in the table
         TIMETRA-L2TP-MIB::tmnxL2tpSeStatusTable of the L2TP session associated
         with this PPPoE session. 
         
         If there is no L2TP session associated with this PPPoE session, the
         value of this object is equal to zero."
    ::= { tmnxPppoeSessionEntry 36 }

tmnxPppoeSessionServiceName OBJECT-TYPE
    SYNTAX      DisplayString (SIZE (0..255))
    MAX-ACCESS  read-only
    STATUS      current
    DESCRIPTION
        "The value of tmnxPppoeSessionServiceName indicates the value of the
         PPPoE service-name tag received in PADI packets."
    ::= { tmnxPppoeSessionEntry 37 }

tmnxPppoeSessionCategoryMapName OBJECT-TYPE
    SYNTAX      TNamedItemOrEmpty
    MAX-ACCESS  read-only
    STATUS      obsolete
    DESCRIPTION
        "The value of tmnxPppoeSessionCategoryMapName indicates the
         category map name applicable for this PPPoE session.

         The value of tmnxPppoeSessionOriginStrings indicates from what source
         this string was received."
    ::= { tmnxPppoeSessionEntry 38 }

tmnxPppoeSessionRadiusClassAttr OBJECT-TYPE
    SYNTAX      OCTET STRING (SIZE (0..64))
    MAX-ACCESS  read-only
    STATUS      obsolete
    DESCRIPTION
        "The value of tmnxPppoeSessionRadiusClassAttr indicates the Class
         attribute returned by the RADIUS server in an Access-Accept message.
         
         If no RADIUS authentication is performed for this session, or RADIUS
         did not return this attribute, the value of this object is empty."
    ::= { tmnxPppoeSessionEntry 39 }

tmnxPppoeSessionRadiusUserName OBJECT-TYPE
    SYNTAX      DisplayString (SIZE (0..128))
    MAX-ACCESS  read-only
    STATUS      obsolete
    DESCRIPTION
        "The value of tmnxPppoeSessionRadiusUserName indicates the User-Name
         attribute returned by the RADIUS server in an Access-Accept message.

         If RADIUS did not return this attribute, the value of this object
         is equal to the User-Name attribute sent in the original
         Access-Request message.
         
         If no RADIUS authentication is performed for this session, the value
         of this object is empty."
    ::= { tmnxPppoeSessionEntry 40 }


tmnxPppoeSessionIpv6cpState OBJECT-TYPE
    SYNTAX      TmnxPppCpState
    MAX-ACCESS  read-only
    STATUS      obsolete
    DESCRIPTION
        "The value of tmnxPppoeSessionIpv6cpState indicates the obsolete state of
         the PPP IPv6 Control Protocol of the PPPoE session."
    ::= { tmnxPppoeSessionEntry 41 }

tmnxPppoeSessionInterfaceId OBJECT-TYPE
    SYNTAX      OCTET STRING (SIZE (8))
    MAX-ACCESS  read-only
    STATUS      obsolete
    DESCRIPTION
        "The value of tmnxPppoeSessionInterfaceId indicates the value of the
         remote-id sub-option inserted by the PPPoE intermediate agent."
    ::= { tmnxPppoeSessionEntry 42 }

tmnxPppoeSessionOriginIpv6cpInfo OBJECT-TYPE
    SYNTAX      TmnxPppoeSessionInfoOrigin
    MAX-ACCESS  read-only
    STATUS      obsolete
    DESCRIPTION
        "The value of tmnxPppoeSessionOriginIpv6cpInfo indicates which source
         provided the IPCP information (IP, DNS and NBNS addresses)."
    ::= { tmnxPppoeSessionEntry 43 }

tmnxPppoeSessionIpv6DnsType OBJECT-TYPE
    SYNTAX      InetAddressType
    MAX-ACCESS  read-only
    STATUS      obsolete
    DESCRIPTION
        "The value of tmnxPppoeSessionIpv6DnsType indicates the address
         type of tmnxPppoeSessionIpv6Dns1/2."
    ::= { tmnxPppoeSessionEntry 44 }

tmnxPppoeSessionIpv6Dns1 OBJECT-TYPE
    SYNTAX      InetAddress (SIZE (0|16))
    MAX-ACCESS  read-only
    STATUS      obsolete
    DESCRIPTION
        "The value of tmnxPppoeSessionIpv6Dns1 indicates the primary DNS
         server.

         The value of this object is ''H when not applicable.

         The value of tmnxPppoeSessionOriginIpv6cpInfo indicates from what
         source this IP address was received."
    ::= { tmnxPppoeSessionEntry 45 }

tmnxPppoeSessionIpv6Dns2 OBJECT-TYPE
    SYNTAX      InetAddress (SIZE (0|16))
    MAX-ACCESS  read-only
    STATUS      obsolete
    DESCRIPTION
        "The value of tmnxPppoeSessionIpv6Dns2 indicates the secondary DNS
         server.

         The value of this object is ''H when not applicable.

         The value of tmnxPppoeSessionOriginIpv6cpInfo indicates from what
         source this IP address was received."
    ::= { tmnxPppoeSessionEntry 46 }

tmnxPppoeSessionIpv6DelPfxType OBJECT-TYPE
    SYNTAX      InetAddressType
    MAX-ACCESS  read-only
    STATUS      obsolete
    DESCRIPTION
        "The value of tmnxPppoeSessionIpv6DelPfxType indicates the address
         type of tmnxPppoeSessionIpv6DelPfx."
    ::= { tmnxPppoeSessionEntry 47 }

tmnxPppoeSessionIpv6DelPfxLen OBJECT-TYPE
    SYNTAX      InetAddressPrefixLength (0..128)
    MAX-ACCESS  read-only
    STATUS      obsolete
    DESCRIPTION 
        "The value of tmnxPppoeSessionIpv6DelPfxLen indicates
         the length of tmnxPppoeSessionIpv6DelPfx."
    ::= { tmnxPppoeSessionEntry 48 }

tmnxPppoeSessionIpv6DelPfx OBJECT-TYPE
    SYNTAX      InetAddress (SIZE (0|16))
    MAX-ACCESS  read-only
    STATUS      obsolete
    DESCRIPTION
        "The value of tmnxPppoeSessionIpv6DelPfx indicates the IPv6 prefix
         used for DHCPv6 prefix delegation."
    ::= { tmnxPppoeSessionEntry 49 }

tmnxPppoeSessionIpv6PrefixType OBJECT-TYPE
    SYNTAX      InetAddressType
    MAX-ACCESS  read-only
    STATUS      obsolete
    DESCRIPTION
        "The value of tmnxPppoeSessionIpv6PrefixType indicates the address
         type of tmnxPppoeSessionIpv6Prefix."
    ::= { tmnxPppoeSessionEntry 50 }

tmnxPppoeSessionIpv6PrefixLen OBJECT-TYPE
    SYNTAX      InetAddressPrefixLength (0..128)
    MAX-ACCESS  read-only
    STATUS      obsolete
    DESCRIPTION 
        "The value of tmnxPppoeSessionIpv6PrefixLen indicates
         the length of tmnxPppoeSessionIpv6Prefix."
    ::= { tmnxPppoeSessionEntry 51 }

tmnxPppoeSessionIpv6Prefix OBJECT-TYPE
    SYNTAX      InetAddress (SIZE (0|16))
    MAX-ACCESS  read-only
    STATUS      obsolete
    DESCRIPTION
        "The value of tmnxPppoeSessionIpv6Prefix indicates the IPv6 prefix
         used for stateless address autoconfiguration."
    ::= { tmnxPppoeSessionEntry 52 }

tmnxPppoeSessionSubPppIndex OBJECT-TYPE
    SYNTAX      Unsigned32
    MAX-ACCESS  read-only
    STATUS      current
    DESCRIPTION
        "The value of tmnxPppoeSessionSubPppIndex indicates 
         the local identifier of the subscriber PPP session.
         
         It is the index of the corresponding conceptual row in the
         TIMETRA-SUBSCRIBER-MGMT-MIB::tmnxSubPppTable."
    ::= { tmnxPppoeSessionEntry 53 }

-- --------------------------------------------------------
-- tmnxPppoeSessionModifyTable
-- --------------------------------------------------------
tmnxPppoeSessionModifyTable OBJECT-TYPE
    SYNTAX      SEQUENCE OF TmnxPppoeSessionModifyEntry
    MAX-ACCESS  not-accessible
    STATUS      obsolete
    DESCRIPTION
        "The tmnxPppoeSessionModifyTable augments the tmnxPppoeSessionTable.
         The table allows the operator to modify attributes of the PPPoE
         session.
         
         This table is replaced with
         TIMETRA-SUBSCRIBER-MGMT-MIB::tmnxSubPppModTable."
    ::= { tmnxPppoeObjects 9 }

tmnxPppoeSessionModifyEntry OBJECT-TYPE
    SYNTAX      TmnxPppoeSessionModifyEntry
    MAX-ACCESS  not-accessible
    STATUS      obsolete
    DESCRIPTION
        "Each row entry contains parameters that allow to modify a
         PPPoE session's attributes."
    AUGMENTS { tmnxPppoeSessionEntry }
    ::= { tmnxPppoeSessionModifyTable 1 }

TmnxPppoeSessionModifyEntry ::=
    SEQUENCE {
        tmnxPppoeSessionModSubIdent    TmnxSubIdentStringOrEmpty,
        tmnxPppoeSessionModSubProfStr  TmnxSubProfileStringOrEmpty,
        tmnxPppoeSessionModSlaProfStr  TmnxSlaProfileStringOrEmpty,
        tmnxPppoeSessionModAncpStr     TmnxAncpStringOrZero,
        tmnxPppoeSessionModInterDestId TmnxSubMgtIntDestIdOrEmpty,
        tmnxPppoeSessionModAppProfStr  TmnxAppProfileStringOrEmpty,
        tmnxPppoeSessionEvaluateState  TruthValue
    }

tmnxPppoeSessionModSubIdent OBJECT-TYPE
    SYNTAX      TmnxSubIdentStringOrEmpty
    MAX-ACCESS  read-write
    STATUS      obsolete
    DESCRIPTION
        "The value of tmnxPppoeSessionModSubIdent allows to specify a new
         subscriber name for this session.

         When a SET of this object is done with a non empty string, the system
         will attempt to assign a new subscriber name.

         A SET with an empty string has no effect on the system. (NOOP).

         GETs and GETNEXTs on this variable return an empty string."
    DEFVAL { "" }
    ::= { tmnxPppoeSessionModifyEntry 1 }

tmnxPppoeSessionModSubProfStr OBJECT-TYPE
    SYNTAX      TmnxSubProfileStringOrEmpty
    MAX-ACCESS  read-write
    STATUS      obsolete
    DESCRIPTION
        "The value of tmnxPppoeSessionModSubProfStr allows to specify a new
         subscriber profile string for this session.

         When a SET of this object is done with a non empty string, the system
         will attempt to assign a new subscriber profile string.

         A SET with an empty string has no effect on the system. (NOOP).

         GETs and GETNEXTs on this variable return an empty string."
    DEFVAL { "" }
    ::= { tmnxPppoeSessionModifyEntry 2 }

tmnxPppoeSessionModSlaProfStr OBJECT-TYPE
    SYNTAX      TmnxSlaProfileStringOrEmpty
    MAX-ACCESS  read-write
    STATUS      obsolete
    DESCRIPTION
        "The value of tmnxPppoeSessionModSlaProfStr allows to specify a new
         SLA profile string for this session.

         When a SET of this object is done with a non empty string, the system
         will attempt to assign a new SLA profile string.

         A SET with an empty string has no effect on the system. (NOOP).

         GETs and GETNEXTs on this variable return an empty string."
    DEFVAL { "" }
    ::= { tmnxPppoeSessionModifyEntry 3 }

tmnxPppoeSessionModAncpStr OBJECT-TYPE
    SYNTAX      TmnxAncpStringOrZero
    MAX-ACCESS  read-write
    STATUS      obsolete
    DESCRIPTION
        "The value of tmnxPppoeSessionModAncpStr allows to specify a new
         ANCP-string for this session.

         When a SET of this object is done with a non empty string, the system
         will attempt to assign a new ANCP-string.

         A SET with an empty string has no effect on the system. (NOOP).

         GETs and GETNEXTs on this variable return an empty string."
    DEFVAL { "" }
    ::= { tmnxPppoeSessionModifyEntry 4 }

tmnxPppoeSessionModInterDestId OBJECT-TYPE
    SYNTAX      TmnxSubMgtIntDestIdOrEmpty
    MAX-ACCESS  read-write
    STATUS      obsolete
    DESCRIPTION
        "The value of tmnxPppoeSessionModInterDestId allows to specify a new
         intermediate destination id for this session.

         When a SET of this object is done with a non empty string, the system
         will attempt to assign a new intermediate destination id.

         A SET with an empty string has no effect on the system. (NOOP).

         GETs and GETNEXTs on this variable return an empty string."
    DEFVAL { "" }
    ::= { tmnxPppoeSessionModifyEntry 5 }

tmnxPppoeSessionModAppProfStr OBJECT-TYPE
    SYNTAX      TmnxAppProfileStringOrEmpty
    MAX-ACCESS  read-write
    STATUS      obsolete
    DESCRIPTION
        "The value of tmnxPppoeSessionModAppProfStr specifies a new
         application profile string for this session.

         When a SET of this object is done with a non empty string, the system
         will attempt to assign a new application profile string.

         A SET with an empty string has no effect on the system. (NOOP).

         GETs and GETNEXTs on this variable return an empty string."
    DEFVAL { "" }
    ::= { tmnxPppoeSessionModifyEntry 6 }

tmnxPppoeSessionEvaluateState OBJECT-TYPE
    SYNTAX      TruthValue
    MAX-ACCESS  read-write
    STATUS      obsolete
    DESCRIPTION
        "The value of tmnxPppoeSessionEvaluateState allows to cause a
         re-evaluation of the specified session.

         When this object is set to 'true', the system will perform a
         re-evaluation of the session.

         GETs and GETNEXTs on this variable return false.

         It is not possible to simultaneously request for a session
         re-evaluation, and modify any of the strings."
    DEFVAL { false }
    ::= { tmnxPppoeSessionModifyEntry 7 }

-- --------------------------------------------------------
-- tmnxPppoeSessionStatsTable
-- --------------------------------------------------------
tmnxPppoeSessionStatsTable OBJECT-TYPE
    SYNTAX      SEQUENCE OF TmnxPppoeSessionStatsEntry
    MAX-ACCESS  not-accessible
    STATUS      obsolete
    DESCRIPTION
        "A table that contains statistics per PPPoE session.
        
         This table is replaced with 
         TIMETRA-SUBSCRIBER-MGMT-MIB::tmnxSubPppStatTable."
    ::= { tmnxPppoeObjects 10 }

tmnxPppoeSessionStatsEntry OBJECT-TYPE
    SYNTAX      TmnxPppoeSessionStatsEntry
    MAX-ACCESS  not-accessible
    STATUS      obsolete
    DESCRIPTION
        "Statistics about a PPPoE session."
    INDEX { svcId,
            sapPortId,
            sapEncapValue,
            tmnxPppoeSessionMac,
            tmnxPppoeSessionId }
    ::= { tmnxPppoeSessionStatsTable 1 }

TmnxPppoeSessionStatsEntry ::=
    SEQUENCE {
        tmnxPppoeSessionRxUnknownProto  Counter32,
        tmnxPppoeSessionRxLcpConfReq    Counter32,
        tmnxPppoeSessionRxLcpConfAck    Counter32,
        tmnxPppoeSessionRxLcpConfNak    Counter32,
        tmnxPppoeSessionRxLcpConfRej    Counter32,
        tmnxPppoeSessionRxLcpTermReq    Counter32,
        tmnxPppoeSessionRxLcpTermAck    Counter32,
        tmnxPppoeSessionRxLcpCodeRej    Counter32,
        tmnxPppoeSessionRxLcpEchoReq    Counter32,
        tmnxPppoeSessionRxLcpEchoRep    Counter32,
        tmnxPppoeSessionRxLcpProtRej    Counter32,
        tmnxPppoeSessionRxLcpDiscReq    Counter32,
        tmnxPppoeSessionTxLcpConfReq    Counter32,
        tmnxPppoeSessionTxLcpConfAck    Counter32,
        tmnxPppoeSessionTxLcpConfNak    Counter32,
        tmnxPppoeSessionTxLcpConfRej    Counter32,
        tmnxPppoeSessionTxLcpTermReq    Counter32,
        tmnxPppoeSessionTxLcpTermAck    Counter32,
        tmnxPppoeSessionTxLcpCodeRej    Counter32,
        tmnxPppoeSessionTxLcpEchoReq    Counter32,
        tmnxPppoeSessionTxLcpEchoRep    Counter32,
        tmnxPppoeSessionTxLcpProtRej    Counter32,
        tmnxPppoeSessionTxLcpDiscReq    Counter32,
        tmnxPppoeSessionRxPapAuthReq    Counter32,
        tmnxPppoeSessionTxPapAuthAck    Counter32,
        tmnxPppoeSessionTxPapAuthNak    Counter32,
        tmnxPppoeSessionRxChapResponse  Counter32,
        tmnxPppoeSessionTxChapChallenge Counter32,
        tmnxPppoeSessionTxChapSuccess   Counter32,
        tmnxPppoeSessionTxChapFailure   Counter32,
        tmnxPppoeSessionRxIpcpConfReq   Counter32,
        tmnxPppoeSessionRxIpcpConfAck   Counter32,
        tmnxPppoeSessionRxIpcpConfNak   Counter32,
        tmnxPppoeSessionRxIpcpConfRej   Counter32,
        tmnxPppoeSessionRxIpcpTermReq   Counter32,
        tmnxPppoeSessionRxIpcpTermAck   Counter32,
        tmnxPppoeSessionRxIpcpCodeRej   Counter32,
        tmnxPppoeSessionTxIpcpConfReq   Counter32,
        tmnxPppoeSessionTxIpcpConfAck   Counter32,
        tmnxPppoeSessionTxIpcpConfNak   Counter32,
        tmnxPppoeSessionTxIpcpConfRej   Counter32,
        tmnxPppoeSessionTxIpcpTermReq   Counter32,
        tmnxPppoeSessionTxIpcpTermAck   Counter32,
        tmnxPppoeSessionTxIpcpCodeRej   Counter32,
        tmnxPppoeSessionRxIpv6cpConfReq Counter32,
        tmnxPppoeSessionRxIpv6cpConfAck Counter32,
        tmnxPppoeSessionRxIpv6cpConfNak Counter32,
        tmnxPppoeSessionRxIpv6cpConfRej Counter32,
        tmnxPppoeSessionRxIpv6cpTermReq Counter32,
        tmnxPppoeSessionRxIpv6cpTermAck Counter32,
        tmnxPppoeSessionRxIpv6cpCodeRej Counter32,
        tmnxPppoeSessionTxIpv6cpConfReq Counter32,
        tmnxPppoeSessionTxIpv6cpConfAck Counter32,
        tmnxPppoeSessionTxIpv6cpConfNak Counter32,
        tmnxPppoeSessionTxIpv6cpConfRej Counter32,
        tmnxPppoeSessionTxIpv6cpTermReq Counter32,
        tmnxPppoeSessionTxIpv6cpTermAck Counter32,
        tmnxPppoeSessionTxIpv6cpCodeRej Counter32
    }

tmnxPppoeSessionRxUnknownProto OBJECT-TYPE
    SYNTAX      Counter32
    MAX-ACCESS  read-only
    STATUS      obsolete
    DESCRIPTION
        "The value of tmnxPppoeSessionRxUnknownProto indicates the number of
         packets with unknown PPP protocol received for this PPPoE session."
    ::= { tmnxPppoeSessionStatsEntry 1 }

tmnxPppoeSessionRxLcpConfReq OBJECT-TYPE
    SYNTAX      Counter32
    MAX-ACCESS  read-only
    STATUS      obsolete
    DESCRIPTION
        "The value of tmnxPppoeSessionRxLcpConfReq indicates the number of
         LCP configure requests received for this PPPoE session."
    ::= { tmnxPppoeSessionStatsEntry 2 }

tmnxPppoeSessionRxLcpConfAck OBJECT-TYPE
    SYNTAX      Counter32
    MAX-ACCESS  read-only
    STATUS      obsolete
    DESCRIPTION
        "The value of tmnxPppoeSessionRxLcpConfAck indicates the number of
         LCP configure acknowledgements received for this PPPoE session."
    ::= { tmnxPppoeSessionStatsEntry 3 }

tmnxPppoeSessionRxLcpConfNak OBJECT-TYPE
    SYNTAX      Counter32
    MAX-ACCESS  read-only
    STATUS      obsolete
    DESCRIPTION
        "The value of tmnxPppoeSessionRxLcpConfNak indicates the number of
         negative LCP configure acknowledgements received for this PPPoE
         session."
    ::= { tmnxPppoeSessionStatsEntry 4 }

tmnxPppoeSessionRxLcpConfRej OBJECT-TYPE
    SYNTAX      Counter32
    MAX-ACCESS  read-only
    STATUS      obsolete
    DESCRIPTION
        "The value of tmnxPppoeSessionRxLcpConfRej indicates the number of
         LCP configure rejects received for this PPPoE session."
    ::= { tmnxPppoeSessionStatsEntry 5 }

tmnxPppoeSessionRxLcpTermReq OBJECT-TYPE
    SYNTAX      Counter32
    MAX-ACCESS  read-only
    STATUS      obsolete
    DESCRIPTION
        "The value of tmnxPppoeSessionRxLcpTermReq indicates the number of
         LCP terminate requests received for this PPPoE session."
    ::= { tmnxPppoeSessionStatsEntry 6 }

tmnxPppoeSessionRxLcpTermAck OBJECT-TYPE
    SYNTAX      Counter32
    MAX-ACCESS  read-only
    STATUS      obsolete
    DESCRIPTION
        "The value of tmnxPppoeSessionRxLcpTermAck indicates the number of
         LCP terminate acknowledgements received for this PPPoE session."
    ::= { tmnxPppoeSessionStatsEntry 7 }

tmnxPppoeSessionRxLcpCodeRej OBJECT-TYPE
    SYNTAX      Counter32
    MAX-ACCESS  read-only
    STATUS      obsolete
    DESCRIPTION
        "The value of tmnxPppoeSessionRxLcpCodeRej indicates the number of
         LCP code rejects received for this PPPoE session."
    ::= { tmnxPppoeSessionStatsEntry 8 }

tmnxPppoeSessionRxLcpEchoReq OBJECT-TYPE
    SYNTAX      Counter32
    MAX-ACCESS  read-only
    STATUS      obsolete
    DESCRIPTION
        "The value of tmnxPppoeSessionRxLcpEchoReq indicates the number of
         LCP echo requests received for this PPPoE session."
    ::= { tmnxPppoeSessionStatsEntry 9 }

tmnxPppoeSessionRxLcpEchoRep OBJECT-TYPE
    SYNTAX      Counter32
    MAX-ACCESS  read-only
    STATUS      obsolete
    DESCRIPTION
        "The value of tmnxPppoeSessionRxLcpEchoRep indicates the number of
         LCP echo replies received for this PPPoE session."
    ::= { tmnxPppoeSessionStatsEntry 10 }

tmnxPppoeSessionRxLcpProtRej OBJECT-TYPE
    SYNTAX      Counter32
    MAX-ACCESS  read-only
    STATUS      obsolete
    DESCRIPTION
        "The value of tmnxPppoeSessionRxLcpProtRej indicates the number of
         LCP protocol rejects received for this PPPoE session."
    ::= { tmnxPppoeSessionStatsEntry 11 }

tmnxPppoeSessionRxLcpDiscReq OBJECT-TYPE
    SYNTAX      Counter32
    MAX-ACCESS  read-only
    STATUS      obsolete
    DESCRIPTION
        "The value of tmnxPppoeSessionRxLcpDiscReq indicates the number of
         LCP discard requests received for this PPPoE session."
    ::= { tmnxPppoeSessionStatsEntry 12 }

tmnxPppoeSessionTxLcpConfReq OBJECT-TYPE
    SYNTAX      Counter32
    MAX-ACCESS  read-only
    STATUS      obsolete
    DESCRIPTION
        "The value of tmnxPppoeSessionTxLcpConfReq indicates the number of
         LCP configure requests transmitted for this PPPoE session."
    ::= { tmnxPppoeSessionStatsEntry 13 }

tmnxPppoeSessionTxLcpConfAck OBJECT-TYPE
    SYNTAX      Counter32
    MAX-ACCESS  read-only
    STATUS      obsolete
    DESCRIPTION
        "The value of tmnxPppoeSessionTxLcpConfAck indicates the number of
         LCP configure acknowledgements transmitted for this PPPoE session."
    ::= { tmnxPppoeSessionStatsEntry 14 }

tmnxPppoeSessionTxLcpConfNak OBJECT-TYPE
    SYNTAX      Counter32
    MAX-ACCESS  read-only
    STATUS      obsolete
    DESCRIPTION
        "The value of tmnxPppoeSessionTxLcpConfNak indicates the number of
         negative LCP configure acknowledgements transmitted for this PPPoE
         session."
    ::= { tmnxPppoeSessionStatsEntry 15 }

tmnxPppoeSessionTxLcpConfRej OBJECT-TYPE
    SYNTAX      Counter32
    MAX-ACCESS  read-only
    STATUS      obsolete
    DESCRIPTION
        "The value of tmnxPppoeSessionTxLcpConfRej indicates the number of
         LCP configure rejects transmitted for this PPPoE session."
    ::= { tmnxPppoeSessionStatsEntry 16 }

tmnxPppoeSessionTxLcpTermReq OBJECT-TYPE
    SYNTAX      Counter32
    MAX-ACCESS  read-only
    STATUS      obsolete
    DESCRIPTION
        "The value of tmnxPppoeSessionTxLcpTermReq indicates the number of
         LCP terminate requests transmitted for this PPPoE session."
    ::= { tmnxPppoeSessionStatsEntry 17 }

tmnxPppoeSessionTxLcpTermAck OBJECT-TYPE
    SYNTAX      Counter32
    MAX-ACCESS  read-only
    STATUS      obsolete
    DESCRIPTION
        "The value of tmnxPppoeSessionTxLcpTermAck indicates the number of
         LCP terminate acknowledgements transmitted for this PPPoE session."
    ::= { tmnxPppoeSessionStatsEntry 18 }

tmnxPppoeSessionTxLcpCodeRej OBJECT-TYPE
    SYNTAX      Counter32
    MAX-ACCESS  read-only
    STATUS      obsolete
    DESCRIPTION
        "The value of tmnxPppoeSessionTxLcpCodeRej indicates the number of
         LCP code rejects transmitted for this PPPoE session."
    ::= { tmnxPppoeSessionStatsEntry 19 }

tmnxPppoeSessionTxLcpEchoReq OBJECT-TYPE
    SYNTAX      Counter32
    MAX-ACCESS  read-only
    STATUS      obsolete
    DESCRIPTION
        "The value of tmnxPppoeSessionTxLcpEchoReq indicates the number of
         LCP echo requests transmitted for this PPPoE session."
    ::= { tmnxPppoeSessionStatsEntry 20 }

tmnxPppoeSessionTxLcpEchoRep OBJECT-TYPE
    SYNTAX      Counter32
    MAX-ACCESS  read-only
    STATUS      obsolete
    DESCRIPTION
        "The value of tmnxPppoeSessionTxLcpEchoRep indicates the number of
         LCP echo replies transmitted for this PPPoE session."
    ::= { tmnxPppoeSessionStatsEntry 21 }

tmnxPppoeSessionTxLcpProtRej OBJECT-TYPE
    SYNTAX      Counter32
    MAX-ACCESS  read-only
    STATUS      obsolete
    DESCRIPTION
        "The value of tmnxPppoeSessionTxLcpProtRej indicates the number of
         LCP protocol rejects transmitted for this PPPoE session."
    ::= { tmnxPppoeSessionStatsEntry 22 }

tmnxPppoeSessionTxLcpDiscReq OBJECT-TYPE
    SYNTAX      Counter32
    MAX-ACCESS  read-only
    STATUS      obsolete
    DESCRIPTION
        "The value of tmnxPppoeSessionTxLcpDiscReq indicates the number of
         LCP discard requests transmitted for this PPPoE session."
    ::= { tmnxPppoeSessionStatsEntry 23 }

tmnxPppoeSessionRxPapAuthReq OBJECT-TYPE
    SYNTAX      Counter32
    MAX-ACCESS  read-only
    STATUS      obsolete
    DESCRIPTION
        "The value of tmnxPppoeSessionRxPapAuthReq indicates the number of
         PAP authentication requests received for this PPPoE session."
    ::= { tmnxPppoeSessionStatsEntry 24 }

tmnxPppoeSessionTxPapAuthAck OBJECT-TYPE
    SYNTAX      Counter32
    MAX-ACCESS  read-only
    STATUS      obsolete
    DESCRIPTION
        "The value of tmnxPppoeSessionTxPapAuthAck indicates the number of
         PAP authentication acknowledgements transmitted for this PPPoE
         session."
    ::= { tmnxPppoeSessionStatsEntry 25 }

tmnxPppoeSessionTxPapAuthNak OBJECT-TYPE
    SYNTAX      Counter32
    MAX-ACCESS  read-only
    STATUS      obsolete
    DESCRIPTION
        "The value of tmnxPppoeSessionTxPapAuthNak indicates the number of
         negative PAP authentication acknowledgements transmitted for this
         PPPoE session."
    ::= { tmnxPppoeSessionStatsEntry 26 }

tmnxPppoeSessionRxChapResponse OBJECT-TYPE
    SYNTAX      Counter32
    MAX-ACCESS  read-only
    STATUS      obsolete
    DESCRIPTION
        "The value of tmnxPppoeSessionRxChapResponse indicates the number of
         CHAP authentication responses received for this PPPoE session."
    ::= { tmnxPppoeSessionStatsEntry 27 }

tmnxPppoeSessionTxChapChallenge OBJECT-TYPE
    SYNTAX      Counter32
    MAX-ACCESS  read-only
    STATUS      obsolete
    DESCRIPTION
        "The value of tmnxPppoeSessionTxChapChallenge indicates the number of
         CHAP authentication challenges transmitted for this PPPoE session."
    ::= { tmnxPppoeSessionStatsEntry 28 }

tmnxPppoeSessionTxChapSuccess OBJECT-TYPE
    SYNTAX      Counter32
    MAX-ACCESS  read-only
    STATUS      obsolete
    DESCRIPTION
        "The value of tmnxPppoeSessionTxChapSuccess indicates the number of
         CHAP authentication acknowledgements transmitted for this PPPoE
         session."
    ::= { tmnxPppoeSessionStatsEntry 29 }

tmnxPppoeSessionTxChapFailure OBJECT-TYPE
    SYNTAX      Counter32
    MAX-ACCESS  read-only
    STATUS      obsolete
    DESCRIPTION
        "The value of tmnxPppoeSessionTxChapFailure indicates the number of
         negative CHAP authentication acknowledgements transmitted for this
         PPPoE session."
    ::= { tmnxPppoeSessionStatsEntry 30 }

tmnxPppoeSessionRxIpcpConfReq OBJECT-TYPE
    SYNTAX      Counter32
    MAX-ACCESS  read-only
    STATUS      obsolete
    DESCRIPTION
        "The value of tmnxPppoeSessionRxIpcpConfReq indicates the number of
         IPCP configure requests received for this PPPoE session."
    ::= { tmnxPppoeSessionStatsEntry 31 }

tmnxPppoeSessionRxIpcpConfAck OBJECT-TYPE
    SYNTAX      Counter32
    MAX-ACCESS  read-only
    STATUS      obsolete
    DESCRIPTION
        "The value of tmnxPppoeSessionRxIpcpConfAck indicates the number of
         IPCP configure acknowledgements received for this PPPoE session."
    ::= { tmnxPppoeSessionStatsEntry 32 }

tmnxPppoeSessionRxIpcpConfNak OBJECT-TYPE
    SYNTAX      Counter32
    MAX-ACCESS  read-only
    STATUS      obsolete
    DESCRIPTION
        "The value of tmnxPppoeSessionRxIpcpConfNak indicates the number of
         negative IPCP configure acknowledgements received for this PPPoE
         session."
    ::= { tmnxPppoeSessionStatsEntry 33 }

tmnxPppoeSessionRxIpcpConfRej OBJECT-TYPE
    SYNTAX      Counter32
    MAX-ACCESS  read-only
    STATUS      obsolete
    DESCRIPTION
        "The value of tmnxPppoeSessionRxIpcpConfRej indicates the number of
         IPCP configure rejects received for this PPPoE session."
    ::= { tmnxPppoeSessionStatsEntry 34 }

tmnxPppoeSessionRxIpcpTermReq OBJECT-TYPE
    SYNTAX      Counter32
    MAX-ACCESS  read-only
    STATUS      obsolete
    DESCRIPTION
        "The value of tmnxPppoeSessionRxIpcpTermReq indicates the number of
         IPCP terminate requests received for this PPPoE session."
    ::= { tmnxPppoeSessionStatsEntry 35 }

tmnxPppoeSessionRxIpcpTermAck OBJECT-TYPE
    SYNTAX      Counter32
    MAX-ACCESS  read-only
    STATUS      obsolete
    DESCRIPTION
        "The value of tmnxPppoeSessionRxIpcpTermAck indicates the number of
         IPCP terminate acknowledgements received for this PPPoE session."
    ::= { tmnxPppoeSessionStatsEntry 36 }

tmnxPppoeSessionRxIpcpCodeRej OBJECT-TYPE
    SYNTAX      Counter32
    MAX-ACCESS  read-only
    STATUS      obsolete
    DESCRIPTION
        "The value of tmnxPppoeSessionRxIpcpCodeRej indicates the number of
         IPCP code rejects received for this PPPoE session."
    ::= { tmnxPppoeSessionStatsEntry 37 }

tmnxPppoeSessionTxIpcpConfReq OBJECT-TYPE
    SYNTAX      Counter32
    MAX-ACCESS  read-only
    STATUS      obsolete
    DESCRIPTION
        "The value of tmnxPppoeSessionTxIpcpConfReq indicates the number of
         IPCP configure requests transmitted for this PPPoE session."
    ::= { tmnxPppoeSessionStatsEntry 38 }

tmnxPppoeSessionTxIpcpConfAck OBJECT-TYPE
    SYNTAX      Counter32
    MAX-ACCESS  read-only
    STATUS      obsolete
    DESCRIPTION
        "The value of tmnxPppoeSessionTxIpcpConfAck indicates the number of
         IPCP configure acknowledgements transmitted for this PPPoE session."
    ::= { tmnxPppoeSessionStatsEntry 39 }

tmnxPppoeSessionTxIpcpConfNak OBJECT-TYPE
    SYNTAX      Counter32
    MAX-ACCESS  read-only
    STATUS      obsolete
    DESCRIPTION
        "The value of tmnxPppoeSessionTxIpcpConfNak indicates the number of
         negative IPCP configure acknowledgements transmitted for this PPPoE
         session."
    ::= { tmnxPppoeSessionStatsEntry 40 }

tmnxPppoeSessionTxIpcpConfRej OBJECT-TYPE
    SYNTAX      Counter32
    MAX-ACCESS  read-only
    STATUS      obsolete
    DESCRIPTION
        "The value of tmnxPppoeSessionTxIpcpConfRej indicates the number of
         IPCP configure rejects transmitted for this PPPoE session."
    ::= { tmnxPppoeSessionStatsEntry 41 }

tmnxPppoeSessionTxIpcpTermReq OBJECT-TYPE
    SYNTAX      Counter32
    MAX-ACCESS  read-only
    STATUS      obsolete
    DESCRIPTION
        "The value of tmnxPppoeSessionTxIpcpTermReq indicates the number of
         IPCP terminate requests transmitted for this PPPoE session."
    ::= { tmnxPppoeSessionStatsEntry 42 }

tmnxPppoeSessionTxIpcpTermAck OBJECT-TYPE
    SYNTAX      Counter32
    MAX-ACCESS  read-only
    STATUS      obsolete
    DESCRIPTION
        "The value of tmnxPppoeSessionTxIpcpTermAck indicates the number of
         IPCP terminate acknowledgements transmitted for this PPPoE session."
    ::= { tmnxPppoeSessionStatsEntry 43 }

tmnxPppoeSessionTxIpcpCodeRej OBJECT-TYPE
    SYNTAX      Counter32
    MAX-ACCESS  read-only
    STATUS      obsolete
    DESCRIPTION
        "The value of tmnxPppoeSessionTxIpcpCodeRej indicates the number of
         IPCP code rejects transmitted for this PPPoE session."
    ::= { tmnxPppoeSessionStatsEntry 44 }


tmnxPppoeSessionRxIpv6cpConfReq OBJECT-TYPE
    SYNTAX      Counter32
    MAX-ACCESS  read-only
    STATUS      obsolete
    DESCRIPTION
        "The value of tmnxPppoeSessionRxIpv6cpConfReq indicates the number of
         IPv6CP configure requests received for this PPPoE session."
    ::= { tmnxPppoeSessionStatsEntry 45 }

tmnxPppoeSessionRxIpv6cpConfAck OBJECT-TYPE
    SYNTAX      Counter32
    MAX-ACCESS  read-only
    STATUS      obsolete
    DESCRIPTION
        "The value of tmnxPppoeSessionRxIpv6cpConfAck indicates the number of
         IPv6CP configure acknowledgements received for this PPPoE session."
    ::= { tmnxPppoeSessionStatsEntry 46 }

tmnxPppoeSessionRxIpv6cpConfNak OBJECT-TYPE
    SYNTAX      Counter32
    MAX-ACCESS  read-only
    STATUS      obsolete
    DESCRIPTION
        "The value of tmnxPppoeSessionRxIpv6cpConfNak indicates the number of
         negative IPv6CP configure acknowledgements received for this PPPoE
         session."
    ::= { tmnxPppoeSessionStatsEntry 47 }

tmnxPppoeSessionRxIpv6cpConfRej OBJECT-TYPE
    SYNTAX      Counter32
    MAX-ACCESS  read-only
    STATUS      obsolete
    DESCRIPTION
        "The value of tmnxPppoeSessionRxIpv6cpConfRej indicates the number of
         IPv6CP configure rejects received for this PPPoE session."
    ::= { tmnxPppoeSessionStatsEntry 48 }

tmnxPppoeSessionRxIpv6cpTermReq OBJECT-TYPE
    SYNTAX      Counter32
    MAX-ACCESS  read-only
    STATUS      obsolete
    DESCRIPTION
        "The value of tmnxPppoeSessionRxIpv6cpTermReq indicates the number of
         IPv6CP terminate requests received for this PPPoE session."
    ::= { tmnxPppoeSessionStatsEntry 49 }

tmnxPppoeSessionRxIpv6cpTermAck OBJECT-TYPE
    SYNTAX      Counter32
    MAX-ACCESS  read-only
    STATUS      obsolete
    DESCRIPTION
        "The value of tmnxPppoeSessionRxIpv6cpTermAck indicates the number of
         IPv6CP terminate acknowledgements received for this PPPoE session."
    ::= { tmnxPppoeSessionStatsEntry 50 }

tmnxPppoeSessionRxIpv6cpCodeRej OBJECT-TYPE
    SYNTAX      Counter32
    MAX-ACCESS  read-only
    STATUS      obsolete
    DESCRIPTION
        "The value of tmnxPppoeSessionRxIpv6cpCodeRej indicates the number of
         IPv6CP code rejects received for this PPPoE session."
    ::= { tmnxPppoeSessionStatsEntry 51 }

tmnxPppoeSessionTxIpv6cpConfReq OBJECT-TYPE
    SYNTAX      Counter32
    MAX-ACCESS  read-only
    STATUS      obsolete
    DESCRIPTION
        "The value of tmnxPppoeSessionTxIpv6cpConfReq indicates the number of
         IPv6CP configure requests transmitted for this PPPoE session."
    ::= { tmnxPppoeSessionStatsEntry 52 }

tmnxPppoeSessionTxIpv6cpConfAck OBJECT-TYPE
    SYNTAX      Counter32
    MAX-ACCESS  read-only
    STATUS      obsolete
    DESCRIPTION
        "The value of tmnxPppoeSessionTxIpv6cpConfAck indicates the number of
         IPv6CP configure acknowledgements transmitted for this PPPoE session."
    ::= { tmnxPppoeSessionStatsEntry 53 }

tmnxPppoeSessionTxIpv6cpConfNak OBJECT-TYPE
    SYNTAX      Counter32
    MAX-ACCESS  read-only
    STATUS      obsolete
    DESCRIPTION
        "The value of tmnxPppoeSessionTxIpv6cpConfNak indicates the number of
         negative IPv6CP configure acknowledgements transmitted for this PPPoE
         session."
    ::= { tmnxPppoeSessionStatsEntry 54 }

tmnxPppoeSessionTxIpv6cpConfRej OBJECT-TYPE
    SYNTAX      Counter32
    MAX-ACCESS  read-only
    STATUS      obsolete
    DESCRIPTION
        "The value of tmnxPppoeSessionTxIpv6cpConfRej indicates the number of
         IPv6CP configure rejects transmitted for this PPPoE session."
    ::= { tmnxPppoeSessionStatsEntry 55 }

tmnxPppoeSessionTxIpv6cpTermReq OBJECT-TYPE
    SYNTAX      Counter32
    MAX-ACCESS  read-only
    STATUS      obsolete
    DESCRIPTION
        "The value of tmnxPppoeSessionTxIpv6cpTermReq indicates the number of
         IPv6CP terminate requests transmitted for this PPPoE session."
    ::= { tmnxPppoeSessionStatsEntry 56 }

tmnxPppoeSessionTxIpv6cpTermAck OBJECT-TYPE
    SYNTAX      Counter32
    MAX-ACCESS  read-only
    STATUS      obsolete
    DESCRIPTION
        "The value of tmnxPppoeSessionTxIpv6cpTermAck indicates the number of
         IPv6CP terminate acknowledgements transmitted for this PPPoE session."
    ::= { tmnxPppoeSessionStatsEntry 57 }

tmnxPppoeSessionTxIpv6cpCodeRej OBJECT-TYPE
    SYNTAX      Counter32
    MAX-ACCESS  read-only
    STATUS      obsolete
    DESCRIPTION
        "The value of tmnxPppoeSessionTxIpv6cpCodeRej indicates the number of
         IPv6CP code rejects transmitted for this PPPoE session."
    ::= { tmnxPppoeSessionStatsEntry 58 }


-- ----------------------------------------
-- PPPOE Managed Route Table
-- ----------------------------------------
tmnxPppoeManagedRouteTable OBJECT-TYPE
    SYNTAX          SEQUENCE OF TmnxPppoeManagedRouteEntry
    MAX-ACCESS      not-accessible
    STATUS          obsolete
    DESCRIPTION     "A table that contains PPPoE managed routes.
                    
                     This table is replaced with 
                     TIMETRA-SUBSCRIBER-MGMT-MIB::tmnxSubPppMRtTable."
    ::= { tmnxPppoeObjects 11 }

tmnxPppoeManagedRouteEntry OBJECT-TYPE
    SYNTAX          TmnxPppoeManagedRouteEntry
    MAX-ACCESS      not-accessible
    STATUS          obsolete
    DESCRIPTION     "A specific PPPoE managed route."
    INDEX           { svcId,
                      sapPortId,
                      sapEncapValue,
                      tmnxPppoeSessionMac,
                      tmnxPppoeSessionId,
                      tmnxPppoeManagedRouteAddrType,
                      tmnxPppoeManagedRouteAddr,
                      tmnxPppoeManagedRoutePrefixLen }
    ::= { tmnxPppoeManagedRouteTable 1 }

TmnxPppoeManagedRouteEntry ::=
    SEQUENCE {
        tmnxPppoeManagedRouteAddrType      InetAddressType,
        tmnxPppoeManagedRouteAddr          InetAddress,
        tmnxPppoeManagedRoutePrefixLen     InetAddressPrefixLength,
        tmnxPppoeManagedRouteStatus        TmnxManagedRouteStatus
    }

tmnxPppoeManagedRouteAddrType OBJECT-TYPE
    SYNTAX          InetAddressType
    MAX-ACCESS      not-accessible
    STATUS          obsolete
    DESCRIPTION     "The value of tmnxPppoeManagedRouteAddrType indicates
                     the address type of tmnxPppoeManagedRouteAddr."
    ::= { tmnxPppoeManagedRouteEntry 1 }

tmnxPppoeManagedRouteAddr OBJECT-TYPE
    SYNTAX          InetAddress (SIZE(4|16))
    MAX-ACCESS      not-accessible
    STATUS          obsolete
    DESCRIPTION     "The value of tmnxPppoeManagedRouteAddr indicates
                     the IP address of the managed route."
    ::= { tmnxPppoeManagedRouteEntry 2 }

tmnxPppoeManagedRoutePrefixLen OBJECT-TYPE
    SYNTAX          InetAddressPrefixLength (0..32)
    MAX-ACCESS      not-accessible
    STATUS          obsolete
    DESCRIPTION     "The value of tmnxPppoeManagedRoutePrefixLen indicates
                     the prefix length of the subnet associated with
                     tmnxPppoeManagedRouteAddr."
    ::= { tmnxPppoeManagedRouteEntry 3 }

tmnxPppoeManagedRouteStatus OBJECT-TYPE
    SYNTAX          TmnxManagedRouteStatus
    MAX-ACCESS      read-only
    STATUS          obsolete
    DESCRIPTION     "The value of tmnxPppoeManagedRouteStatus indicates
                     the state of this managed route."
    ::= { tmnxPppoeManagedRouteEntry 4 }

-- ----------------------------------------
-- PPPOE Bgp Peering Table
-- ----------------------------------------
tmnxPppoeSessionBgpTable OBJECT-TYPE
    SYNTAX          SEQUENCE OF TmnxPppoeSessionBgpEntry
    MAX-ACCESS      not-accessible
    STATUS          obsolete
    DESCRIPTION     "The tmnxPppoeSessionBgpTable augments the
                     tmnxPppoeSessionTable.
                     
                     This table is replaced with
                     TIMETRA-SUBSCRIBER-MGMT-MIB::tmnxSubPppBgpTable."
    ::= { tmnxPppoeObjects 12 }

tmnxPppoeSessionBgpEntry OBJECT-TYPE
    SYNTAX          TmnxPppoeSessionBgpEntry
    MAX-ACCESS      not-accessible
    STATUS          obsolete
    DESCRIPTION     "A row entry contains parameters used for a BGP peering."
    AUGMENTS        { tmnxPppoeSessionEntry }
    ::= { tmnxPppoeSessionBgpTable 1 }

TmnxPppoeSessionBgpEntry ::=
    SEQUENCE {
        tmnxPppoeSessionBgpPrngPlcyName   TNamedItemOrEmpty,
        tmnxPppoeSessionBgpAuthKeyChain   TNamedItemOrEmpty,
        tmnxPppoeSessionBgpMD5AuthKey     OCTET STRING,
        tmnxPppoeSessionBgpImportPolicy   TPolicyStatementNameOrEmpty,
        tmnxPppoeSessionBgpExportPolicy   TPolicyStatementNameOrEmpty,
        tmnxPppoeSessionBgpPeerAS         InetAutonomousSystemNumber,
        tmnxPppoeSessionBgpPeeringStatus  BgpPeeringStatus
    }

tmnxPppoeSessionBgpPrngPlcyName OBJECT-TYPE
    SYNTAX          TNamedItemOrEmpty
    MAX-ACCESS      read-only
    STATUS          obsolete
    DESCRIPTION
        "The value of tmnxPppoeSessionBgpPrngPlcyName indicates the
         peering policy which is used to set up the BGP peer for this
         pppoe session."
    ::= { tmnxPppoeSessionBgpEntry 1 }

tmnxPppoeSessionBgpAuthKeyChain OBJECT-TYPE
    SYNTAX          TNamedItemOrEmpty
    MAX-ACCESS      read-only
    STATUS          obsolete
    DESCRIPTION
        "The value of tmnxPppoeSessionBgpAuthKeyChain indicates the
         keychain which is used to sign and/or authenticate the BGP
         protocol stream."
    ::= { tmnxPppoeSessionBgpEntry 2 }

tmnxPppoeSessionBgpMD5AuthKey OBJECT-TYPE
    SYNTAX          OCTET STRING (SIZE(0..255))
    MAX-ACCESS      read-only
    STATUS          obsolete
    DESCRIPTION     
        "The value of tmnxPppoeSessionBgpMD5AuthKey indicates the 
         authentication key used between BGP peers neighbors before
         establishing sessions. Authentication is done using the
         MD-5 message based digest protocol."
    ::= { tmnxPppoeSessionBgpEntry 3 }

tmnxPppoeSessionBgpImportPolicy OBJECT-TYPE
    SYNTAX          TPolicyStatementNameOrEmpty
    MAX-ACCESS      read-only
    STATUS          obsolete
    DESCRIPTION     
        "The value of tmnxPppoeSessionBgpImportPolicy indicates 
         the import policy."
    ::= { tmnxPppoeSessionBgpEntry 4 }

tmnxPppoeSessionBgpExportPolicy OBJECT-TYPE
    SYNTAX          TPolicyStatementNameOrEmpty
    MAX-ACCESS      read-only
    STATUS          obsolete
    DESCRIPTION     
        "The value of tmnxPppoeSessionBgpExportPolicy indicates 
         the export policy."
    ::= { tmnxPppoeSessionBgpEntry 5 }

tmnxPppoeSessionBgpPeerAS OBJECT-TYPE
    SYNTAX          InetAutonomousSystemNumber
    MAX-ACCESS      read-only
    STATUS          obsolete
    DESCRIPTION     
        "The value of tmnxPppoeSessionBgpPeerAS indicates the Autonomous System
         number for the remote peer."
    ::= { tmnxPppoeSessionBgpEntry 6 }

tmnxPppoeSessionBgpPeeringStatus OBJECT-TYPE
    SYNTAX          BgpPeeringStatus
    MAX-ACCESS      read-only
    STATUS          obsolete
    DESCRIPTION
        "The value of tmnxPppoeSessionBgpPeeringStatus indicates
         the status of the BGP peering session."
    ::= { tmnxPppoeSessionBgpEntry 7 }

-- --------------------------------------------------------
-- tmnxPppoeSessionOverridesTable
-- --------------------------------------------------------
tmnxPppoeSessionOverridesTable OBJECT-TYPE
    SYNTAX      SEQUENCE OF TmnxPppoeSessionOverridesEntry
    MAX-ACCESS  not-accessible
    STATUS      obsolete
    DESCRIPTION
        "A table that contains PPPoE session qos overrides.
        
         This table is replace with 
         TIMETRA-SUBSCRIBER-MGMT-MIB::tmnxSubPppOvrTable."
    ::= { tmnxPppoeObjects 13 }

tmnxPppoeSessionOverridesEntry OBJECT-TYPE
    SYNTAX      TmnxPppoeSessionOverridesEntry
    MAX-ACCESS  not-accessible
    STATUS      obsolete
    DESCRIPTION
        "Information about a specific PPPoE session qos override."
    INDEX { svcId,
            sapPortId,
            sapEncapValue,
            tmnxPppoeSessionMac,
            tmnxPppoeSessionId,
            tmnxPppoeSessionOvrDirection,
            tmnxPppoeSessionOvrType,
            tmnxPppoeSessionOvrTypeId,
            tmnxPppoeSessionOvrTypeName
            }
    ::= { tmnxPppoeSessionOverridesTable 1 }

TmnxPppoeSessionOverridesEntry ::=
    SEQUENCE {
        tmnxPppoeSessionOvrDirection     TDirection,
        tmnxPppoeSessionOvrType          TQosOverrideType,
        tmnxPppoeSessionOvrTypeId        Integer32,
        tmnxPppoeSessionOvrTypeName      TNamedItemOrEmpty,
        tmnxPppoeSessionOvrPIR           TPIRRateOverride,
        tmnxPppoeSessionOvrCIR           TCIRRateOverride,
        tmnxPppoeSessionOvrCBS           TBurstSizeBytesOverride,
        tmnxPppoeSessionOvrMBS           TBurstSizeBytesOverride
    }

tmnxPppoeSessionOvrDirection OBJECT-TYPE
    SYNTAX          TDirection ( 1 | 2 )
    MAX-ACCESS      not-accessible
    STATUS          obsolete
    DESCRIPTION     "The value of tmnxPppoeSessionOvrDirection indicates whether
                     this row specifies ingress or egress qos override 
                     parameters."
    ::= { tmnxPppoeSessionOverridesEntry 1 }

tmnxPppoeSessionOvrType OBJECT-TYPE
    SYNTAX          TQosOverrideType
    MAX-ACCESS      not-accessible
    STATUS          obsolete
    DESCRIPTION     "The value of tmnxPppoeSessionOvrType indicates what field
                     has been overwritten by this row."
    ::= { tmnxPppoeSessionOverridesEntry 2 }

tmnxPppoeSessionOvrTypeId OBJECT-TYPE
    SYNTAX          Integer32
    MAX-ACCESS      not-accessible
    STATUS          obsolete
    DESCRIPTION     "The value of tmnxPppoeSessionOvrTypeId indicates the id of
                     the queue/policer that has been overwritten by this row.
                     
                     If the value of tmnxPppoeSessionOvrType is not 'queue (1)'
                     or 'policer (2)', this field must be set to zero (0)."
    ::= { tmnxPppoeSessionOverridesEntry 3 }

tmnxPppoeSessionOvrTypeName OBJECT-TYPE
    SYNTAX          TNamedItemOrEmpty
    MAX-ACCESS      not-accessible
    STATUS          obsolete
    DESCRIPTION     "The value of tmnxPppoeSessionOvrTypeName indicates the
                     name of the scheduler/arbiter that has been overwritten by
                     this row.
                     
                     If the value of tmnxPppoeSessionOvrType is not 
                     'arbiter (4)' or 'scheduler (5)', this field must be set to
                     zero (0)."
    ::= { tmnxPppoeSessionOverridesEntry 4 }

tmnxPppoeSessionOvrPIR OBJECT-TYPE
    SYNTAX          TPIRRateOverride
    MAX-ACCESS      read-only
    STATUS          obsolete
    DESCRIPTION     "The value of tmnxPppoeSessionOvrPIR indicates the PIR rate
                     in kbps allowed for the object overwritten by this row."
    ::= { tmnxPppoeSessionOverridesEntry 5 }

tmnxPppoeSessionOvrCIR OBJECT-TYPE
    SYNTAX          TCIRRateOverride
    MAX-ACCESS      read-only
    STATUS          obsolete
    DESCRIPTION     "The value of tmnxPppoeSessionOvrCIR indicates the CIR rate
                     in kbps allowed for the object overwritten by this row."
    ::= { tmnxPppoeSessionOverridesEntry 6 }

tmnxPppoeSessionOvrCBS OBJECT-TYPE
    SYNTAX          TBurstSizeBytesOverride
    MAX-ACCESS      read-only
    STATUS          obsolete
    DESCRIPTION     "The value of tmnxPppoeSessionOvrCBS indicates the amount of
                     reserved buffer space (in bytes) for the object
                     overwritten by this row."
    ::= { tmnxPppoeSessionOverridesEntry 7 }

tmnxPppoeSessionOvrMBS OBJECT-TYPE
    SYNTAX          TBurstSizeBytesOverride
    MAX-ACCESS      read-only
    STATUS          obsolete
    DESCRIPTION     "The value of tmnxPppoeSessionOvrMBS indicates the maximum
                     amount of reserved buffer space (in bytes) for the object
                     overwritten by this row."
    ::= { tmnxPppoeSessionOverridesEntry 8 }

-- --------------------------------------------------------
-- tmnxPppoeSessionAleTable
-- --------------------------------------------------------

tmnxPppoeSessionAleTable OBJECT-TYPE
    SYNTAX      SEQUENCE OF TmnxPppoeSessionAleEntry
    MAX-ACCESS  not-accessible
    STATUS      obsolete
    DESCRIPTION
        "A table that contains PPPoE session Access Loop Encapsulation
         information.

         Entries in this table are created and destroyed by the system.
        
         This table is a sparse augment of the tmnxPppoeSessionTable: entries
         are created only for PPPoE sessions for which Access Loop Encapsulation
         information is available.
         
         This table is replaced with 
         TIMETRA-SUBSCRIBER-MGMT-MIB::tmnxSubPppAleTable"
    ::= { tmnxPppoeObjects 15 }

tmnxPppoeSessionAleEntry OBJECT-TYPE
    SYNTAX      TmnxPppoeSessionAleEntry
    MAX-ACCESS  not-accessible
    STATUS      obsolete
    DESCRIPTION
        "Access Loop Encapsulation Information about a specific PPPoE session."
    INDEX { svcId,
            sapPortId,
            sapEncapValue,
            tmnxPppoeSessionMac,
            tmnxPppoeSessionId
          }
    ::= { tmnxPppoeSessionAleTable 1 }

TmnxPppoeSessionAleEntry ::=
    SEQUENCE {
        tmnxPppoeSessionAleDatalink      TmnxAccessLoopEncapDataLink,
        tmnxPppoeSessionAleEncaps1       TmnxAccessLoopEncaps1,
        tmnxPppoeSessionAleEncaps2       TmnxAccessLoopEncaps2
    }

tmnxPppoeSessionAleDatalink OBJECT-TYPE
    SYNTAX          TmnxAccessLoopEncapDataLink
    MAX-ACCESS      read-only
    STATUS          obsolete
    DESCRIPTION     "The value of tmnxPppoeSessionAleDatalink indicates 
                     the data link used by the subscriber host 
                     on the DSL access loop."
    ::= { tmnxPppoeSessionAleEntry 1 }

tmnxPppoeSessionAleEncaps1 OBJECT-TYPE
    SYNTAX          TmnxAccessLoopEncaps1
    MAX-ACCESS      read-only
    STATUS          obsolete
    DESCRIPTION     "The value of tmnxPppoeSessionAleEncaps1 indicates 
                     the encapsulation used by the subscriber host 
                     on the DSL access loop."
    ::= { tmnxPppoeSessionAleEntry 2 }

tmnxPppoeSessionAleEncaps2 OBJECT-TYPE
    SYNTAX          TmnxAccessLoopEncaps2
    MAX-ACCESS      read-only
    STATUS          obsolete
    DESCRIPTION     "The value of tmnxPppoeSessionAleEncaps2 indicates 
                     the encapsulation used by the subscriber host 
                     on the DSL access loop."
    ::= { tmnxPppoeSessionAleEntry 3 }

-- --------------------------------------------------------
-- tmnxPppIesIfInfoTable
-- --------------------------------------------------------
tmnxPppIesIfTableLastChg OBJECT-TYPE
    SYNTAX      TimeStamp
    MAX-ACCESS  read-only
    STATUS      current
    DESCRIPTION
        "The value of tmnxPppIesIfTableLastChg indicates the sysUpTime at
         the time of the most recent management-initiated change to the
         tmnxPppIesIfTable."
    ::= { tmnxPppObjects 1 }

tmnxPppIesIfTable OBJECT-TYPE
    SYNTAX      SEQUENCE OF TmnxPppIesIfEntry
    MAX-ACCESS  not-accessible
    STATUS      current
    DESCRIPTION
        "A table that contains IES interface PPP configuration information.

         A row is automatically created in the tmnxPppIesIfTable for an 
         entry in the iesIfTable where the value of the object iesIfType 
         is equal to 'group (3)'."
    ::= { tmnxPppObjects 2 }

tmnxPppIesIfEntry OBJECT-TYPE
    SYNTAX      TmnxPppIesIfEntry
    MAX-ACCESS  not-accessible
    STATUS      current
    DESCRIPTION
        "PPP specific information about an IES interface."
    INDEX { svcId,
            iesIfIndex }
    ::= { tmnxPppIesIfTable 1 }

TmnxPppIesIfEntry ::=
    SEQUENCE {
        tmnxPppIesIfLastChg            TimeStamp,
        tmnxPppIesIfDescription        TItemDescription,
        tmnxPppIesIfAdminState         TmnxPppoeAdminStatus,
        tmnxPppIesIfPolicy             TNamedItem,
        tmnxPppIesIfSessionLimit       Unsigned32,
        tmnxPppIesIfUserDb             TNamedItemOrEmpty

    }

tmnxPppIesIfLastChg OBJECT-TYPE
    SYNTAX      TimeStamp
    MAX-ACCESS  read-only
    STATUS      current
    DESCRIPTION
        "The value of tmnxPppIesIfLastChg indicates the sysUpTime at
         the time of the most recent management-initiated change to this
         table row."
    ::= { tmnxPppIesIfEntry 1 }

tmnxPppIesIfDescription OBJECT-TYPE
    SYNTAX      TItemDescription
    MAX-ACCESS  read-write
    STATUS      current
    DESCRIPTION
        "The value of the object tmnxPppIesIfDescription specifies a user
         provided description for PPP on this IES interface."
    DEFVAL { "" }
    ::= { tmnxPppIesIfEntry 2 }

tmnxPppIesIfAdminState OBJECT-TYPE
    SYNTAX      TmnxPppoeAdminStatus
    MAX-ACCESS  read-write
    STATUS      current
    DESCRIPTION
        "The value of the object tmnxPppIesIfAdminState specifies the
         administrative state of PPP on this IES interface."
    DEFVAL { disabled }
    ::= { tmnxPppIesIfEntry 3 }

tmnxPppIesIfPolicy OBJECT-TYPE
    SYNTAX      TNamedItem
    MAX-ACCESS  read-write
    STATUS      current
    DESCRIPTION
        "The value of tmnxPppIesIfPolicy specifies the PPP policy
         applicable on this IES interface."
    DEFVAL { "default" }
    ::= { tmnxPppIesIfEntry 4 }

tmnxPppIesIfSessionLimit OBJECT-TYPE
    SYNTAX      Unsigned32 (1..65535)
    MAX-ACCESS  read-write
    STATUS      current
    DESCRIPTION
        "The value of tmnxPppIesIfSessionLimit specifies the maximum
         number of PPP sessions allowed on this IES interface."
    DEFVAL { 1 }
    ::= { tmnxPppIesIfEntry 5 }

tmnxPppIesIfUserDb OBJECT-TYPE
    SYNTAX      TNamedItemOrEmpty
    MAX-ACCESS  read-write
    STATUS      current
    DESCRIPTION
        "The value of tmnxPppIesIfUserDb specifies the local user database
         to use for PPP PAP/CHAP based authentication.

         If no authentication with the local user database is required, the
         value of this object must be set to the empty string."
    DEFVAL { "" }
    ::= { tmnxPppIesIfEntry 8 }

-- --------------------------------------------------------
-- tmnxMlpppBundleTable
-- --------------------------------------------------------

tmnxMlpppBundleTable   OBJECT-TYPE
    SYNTAX      SEQUENCE OF TmnxMlpppBundleEntry
    MAX-ACCESS  not-accessible
    STATUS      current
    DESCRIPTION
       "The tmnxMlpppBundleTable allows the monitoring of
        subscriber MLPPP (Multi Link PPP) Bundles."
    REFERENCE "RFC 1990 The PPP Multilink Protocol"
    ::= { tmnxMlpppObjects 1 }

tmnxMlpppBundleEntry   OBJECT-TYPE
    SYNTAX      TmnxMlpppBundleEntry
    MAX-ACCESS  not-accessible
    STATUS      current
    DESCRIPTION
       "Each conceptual row represents a subscriber MLPPP Bundle.

        Entries in this table are created and destroyed by the system."
    INDEX { tmnxMlpppBundleIndex }
    ::= { tmnxMlpppBundleTable 1 }

TmnxMlpppBundleEntry ::= 
    SEQUENCE {
        tmnxMlpppBundleIndex             Unsigned32,
        tmnxMlpppBundleLocEpClass        TmnxMlpppEpClass,
        tmnxMlpppBundleLocEpAddress      OCTET STRING,
        tmnxMlpppBundleRemEpClass        TmnxMlpppEpClass,
        tmnxMlpppBundleRemEpAddress      OCTET STRING,
        tmnxMlpppBundleSubPppIndex       Unsigned32,
        tmnxMlpppBundleMaxLinks          Unsigned32,
        tmnxMlpppBundleActualLinks       Gauge32,
        tmnxMlpppBundleRemMrru           Unsigned32,
        tmnxMlpppBundleLocMrru           Unsigned32,
        tmnxMlpppBundleIndicators        BITS,
        tmnxMlpppBundleFragmentSize      Unsigned32,
        tmnxMlpppBundleMaxDelayCfg       Unsigned32,
        tmnxMlpppBundleMaxDelay          Unsigned32,
        tmnxMlpppBundleReassemblyTo      Unsigned32,
        tmnxMlpppBundleEgressRate        Unsigned32
    }
        
tmnxMlpppBundleIndex OBJECT-TYPE
    SYNTAX      Unsigned32
    MAX-ACCESS  not-accessible
    STATUS      current
    DESCRIPTION
       "The value of the object tmnxMlpppBundleIndex indicates the local  
        identifier of the bundle."
    ::= { tmnxMlpppBundleEntry 1 }

tmnxMlpppBundleLocEpClass OBJECT-TYPE
    SYNTAX      TmnxMlpppEpClass
    MAX-ACCESS  read-only
    STATUS      current
    DESCRIPTION
       "The value of tmnxMlpppBundleLocEpClass indicates the
        address class of the local endpoint.
        
        If the value of tmnxMlpppBundleLocEpClass is equal to 'null',
        the address class of the MLPPP Endpoint Discriminator option was not
        present in a received Configure-Request."
    REFERENCE
       "RFC 1990 The PPP Multilink Protocol (MP), 
        section 5.1.3 Endpoint Discriminator Option."
    ::= { tmnxMlpppBundleEntry 2 }

tmnxMlpppBundleLocEpAddress OBJECT-TYPE
    SYNTAX      OCTET STRING(SIZE(0..20))
    MAX-ACCESS  read-only
    STATUS      current
    DESCRIPTION
       "The value of tmnxMlpppBundleLocEpAddress indicates the
        address of the local MLPPP Endpoint.
        
        Its interpretation depends on the value of tmnxMlpppBundleLocEpClass."
    REFERENCE
       "RFC 1990 The PPP Multilink Protocol (MP), 
        section 5.1.3 Endpoint Discriminator Option."
    ::= { tmnxMlpppBundleEntry 3 }

tmnxMlpppBundleRemEpClass OBJECT-TYPE
    SYNTAX      TmnxMlpppEpClass
    MAX-ACCESS  read-only
    STATUS      current
    DESCRIPTION
       "The value of tmnxMlpppBundleRemEpClass indicates the
        address class of the local endpoint.
        
        If the value of tmnxMlpppBundleRemEpClass is equal to 'null',
        the address class of the MLPPP Endpoint Discriminator option was not
        present in a received Configure-Request."
    REFERENCE
       "RFC 1990 The PPP Multilink Protocol (MP), 
        section 5.1.3 Endpoint Discriminator Option."
    ::= { tmnxMlpppBundleEntry 4 }

tmnxMlpppBundleRemEpAddress OBJECT-TYPE
    SYNTAX      OCTET STRING(SIZE(0..20))
    MAX-ACCESS  read-only
    STATUS      current
    DESCRIPTION
       "The value of tmnxMlpppBundleRemEpAddress indicates the
        address of the local MLPPP Endpoint.
        
        Its interpretation depends on the value of tmnxMlpppBundleRemEpClass."
    REFERENCE
       "RFC 1990 The PPP Multilink Protocol (MP), 
        section 5.1.3 Endpoint Discriminator Option."
    ::= { tmnxMlpppBundleEntry 5 }

tmnxMlpppBundleSubPppIndex OBJECT-TYPE
    SYNTAX      Unsigned32
    MAX-ACCESS  read-only
    STATUS      current
    DESCRIPTION
        "The value of tmnxMlpppBundleSubPppIndex indicates 
         the local identifier of the subscriber PPP session.
         
         It is the index of the corresponding conceptual row in the
         TIMETRA-SUBSCRIBER-MGMT-MIB::tmnxSubPppTable."
    ::= { tmnxMlpppBundleEntry 6 }
    
tmnxMlpppBundleMaxLinks OBJECT-TYPE
    SYNTAX      Unsigned32
    MAX-ACCESS  read-only
    STATUS      current
    DESCRIPTION
        "The value of tmnxMlpppBundleMaxLinks indicates 
         the maximum number of links allowed for this bundle."
    ::= { tmnxMlpppBundleEntry 7 }

tmnxMlpppBundleActualLinks OBJECT-TYPE
    SYNTAX      Gauge32
    MAX-ACCESS  read-only
    STATUS      current
    DESCRIPTION
        "The value of tmnxMlpppBundleActualLinks indicates 
         the actual number of links of this bundle."
    ::= { tmnxMlpppBundleEntry 8 }

tmnxMlpppBundleRemMrru OBJECT-TYPE
    SYNTAX      Unsigned32
    MAX-ACCESS  read-only
    STATUS      current
    DESCRIPTION
        "The value of tmnxMlpppBundleRemMrru indicates 
         the Maximum Reconstructed Receive Unit (MRRU) for this MLPPP bundle.
         
         This value is derived from the values proposed by the
         MLPPP peer for the MLPPP links in this bundle."
    REFERENCE
        "RFC 1990 The PPP Multilink Protocol (MP), 
         section 5.1.1 Multilink MRRU LCP option."
    ::= { tmnxMlpppBundleEntry 9 }

tmnxMlpppBundleLocMrru OBJECT-TYPE
    SYNTAX      Unsigned32
    MAX-ACCESS  read-only
    STATUS      current
    DESCRIPTION
        "The value of tmnxMlpppBundleLocMrru indicates 
         the Maximum Reconstructed Receive Unit (MRRU) for this MLPPP bundle."
    REFERENCE
        "RFC 1990 The PPP Multilink Protocol (MP), 
         section 5.1.1 Multilink MRRU LCP option."
    ::= { tmnxMlpppBundleEntry 10 }

tmnxMlpppBundleIndicators OBJECT-TYPE
    SYNTAX      BITS {
                    lfiCfg (0),
                    lfi (1),
                    shortSeqNrRx (2),
                    shortSeqNrTx (3)                 
                }
    MAX-ACCESS  read-only
    STATUS      current
    DESCRIPTION
        "The value of tmnxMlpppBundleIndicators indicates 
         various information about this bundle.
         
         lfiCfg - Link Fragmentation and Interleaving (LFI) configured
                  when this bundle was created;
         lfi - LFI active;
         shortSeqNrRx - Short Sequence Numbers used for incoming messages;
         shortSeqNrTx - Short Sequence Numbers for outgoing messages."
    ::= { tmnxMlpppBundleEntry 11 }

tmnxMlpppBundleFragmentSize OBJECT-TYPE
    SYNTAX      Unsigned32
    UNITS       "bytes"
    MAX-ACCESS  read-only
    STATUS      current
    DESCRIPTION
        "The value of tmnxMlpppBundleFragmentSize indicates 
         the fragment size for this bundle.
         
         While there is no fragmentation and interleaving on this bundle,
         the value of this object is equal to zero."
    ::= { tmnxMlpppBundleEntry 12 }

tmnxMlpppBundleMaxDelayCfg OBJECT-TYPE
     SYNTAX      Unsigned32
     UNITS       "milliseconds"
     MAX-ACCESS  read-only
     STATUS      current
     DESCRIPTION
         "The value of tmnxMlpppBundleMaxDelayCfg indicates 
          the maximum delay configured for this bundle when it was created."
     ::= { tmnxMlpppBundleEntry 13 }

tmnxMlpppBundleMaxDelay OBJECT-TYPE
     SYNTAX      Unsigned32
     UNITS       "milliseconds"
     MAX-ACCESS  read-only
     STATUS      current
     DESCRIPTION
         "The value of tmnxMlpppBundleMaxDelay indicates 
          the maximum delay for this bundle."
     ::= { tmnxMlpppBundleEntry 14 }

 tmnxMlpppBundleReassemblyTo OBJECT-TYPE
      SYNTAX      Unsigned32
      UNITS       "milliseconds"
      MAX-ACCESS  read-only
      STATUS      current
      DESCRIPTION
          "The value of tmnxMlpppBundleReassemblyTo indicates 
           the reassembly timeout configured for this bundle when it was 
           created."
      ::= { tmnxMlpppBundleEntry 15 }

 tmnxMlpppBundleEgressRate OBJECT-TYPE
      SYNTAX      Unsigned32
      UNITS       "kbps"
      MAX-ACCESS  read-only
      STATUS      current
      DESCRIPTION
          "The value of tmnxMlpppBundleEgressRate indicates 
           the nominal egress rate for this bundle."
      ::= { tmnxMlpppBundleEntry 16 }

-- --------------------------------------------------------
-- tmnxMlpppLinkTable
-- --------------------------------------------------------

tmnxMlpppLinkTable   OBJECT-TYPE
    SYNTAX      SEQUENCE OF TmnxMlpppLinkEntry
    MAX-ACCESS  not-accessible
    STATUS      current
    DESCRIPTION
       "The tmnxMlpppLinkTable contains the subscriber MLPPP (Multi Link PPP) 
        link sessions ordered per bundle."
    REFERENCE "RFC 1990 The PPP Multilink Protocol"
    ::= { tmnxMlpppObjects 2 }

tmnxMlpppLinkEntry   OBJECT-TYPE
    SYNTAX      TmnxMlpppLinkEntry
    MAX-ACCESS  not-accessible
    STATUS      current
    DESCRIPTION
       "Each conceptual row represents a subscriber MLPPP link.

        Entries in this table are created and destroyed by the system."
    INDEX { tmnxMlpppBundleIndex, tmnxSubPppIndex }
    ::= { tmnxMlpppLinkTable 1 }

TmnxMlpppLinkEntry ::= 
    SEQUENCE {
        tmnxMlpppLinkRemMrru         Unsigned32
    }
        
tmnxMlpppLinkRemMrru OBJECT-TYPE
    SYNTAX      Unsigned32
    MAX-ACCESS  read-only
    STATUS      current
    DESCRIPTION
        "The value of tmnxMlpppLinkRemMrru indicates 
         the Maximum Reconstructed Receive Unit (MRRU) proposed by the
         MLPPP peer for this MLPPP link."
    REFERENCE
        "RFC 1990 The PPP Multilink Protocol (MP), 
         section 5.1.1 Multilink MRRU LCP option."
    ::= { tmnxMlpppLinkEntry 1 }

-- --------------------------------------------------------
-- tmnxPppPlcyMlpppTable
-- --------------------------------------------------------
tmnxPppPlcyMlpppTableLastCh OBJECT-TYPE
    SYNTAX      TimeStamp
    MAX-ACCESS  read-only
    STATUS      current
    DESCRIPTION
        "The value of tmnxPppPlcyMlpppTableLastCh indicates the sysUpTime at
         the time of the most recent management-initiated change to the
         tmnxPppPlcyMlpppTable."
    ::= { tmnxMlpppObjects 3 }

tmnxPppPlcyMlpppTable OBJECT-TYPE
    SYNTAX      SEQUENCE OF TmnxPppPlcyMlpppEntry
    MAX-ACCESS  not-accessible
    STATUS      current
    DESCRIPTION
        "The tmnxPppPlcyMlpppTable has an entry for each PPP(oE) policy configured
         in the system.
         
         This table can be used to configure MLPPP for PPPoE (PPP over Ethernet) 
         and PPPoA (PPP over ATM) subscribers."
    ::= { tmnxMlpppObjects 4 }

tmnxPppPlcyMlpppEntry OBJECT-TYPE
    SYNTAX      TmnxPppPlcyMlpppEntry
    MAX-ACCESS  not-accessible
    STATUS      current
    DESCRIPTION
        "Each row entry represents MLPPP information 
         of a PPP(oE) policy configured in the system.

         Conceptual rows are created and destroyed automatically by the system."
    AUGMENTS { tmnxPppoePlcyEntry }
    ::= { tmnxPppPlcyMlpppTable 1 }

TmnxPppPlcyMlpppEntry ::=
    SEQUENCE {
        tmnxPppPlcyMlpppLastCh           TimeStamp,
        tmnxPppPlcyMlpppAcceptMrru       TruthValue,
        tmnxPppPlcyMlpppEpClass          TmnxMlpppEpClass,
        tmnxPppPlcyMlpppEpIpv4Address    InetAddressIPv4,
        tmnxPppPlcyMlpppEpMacAddress     MacAddress,
        tmnxPppPlcyMlpppShortSeqNumberRx TruthValue
    }

tmnxPppPlcyMlpppLastCh OBJECT-TYPE
    SYNTAX      TimeStamp
    MAX-ACCESS  read-only
    STATUS      current
    DESCRIPTION
        "The value of tmnxPppPlcyMlpppLastCh indicates the sysUpTime at
         the time of the most recent management-initiated change to this
         table row."
    ::= { tmnxPppPlcyMlpppEntry 1 }

tmnxPppPlcyMlpppAcceptMrru OBJECT-TYPE
    SYNTAX      TruthValue
    MAX-ACCESS  read-create
    STATUS      current
    DESCRIPTION
       "The value of tmnxPppPlcyMlpppAcceptMrru specifies
        if this system will accept the Multilink MRRU LCP option
        for the PPP sessions using this policy."
    REFERENCE
       "RFC 1990 The PPP Multilink Protocol (MP), 
        section 5.1.1.  Multilink MRRU LCP option."
    DEFVAL { false }
    ::= { tmnxPppPlcyMlpppEntry 2 }

tmnxPppPlcyMlpppEpClass OBJECT-TYPE
    SYNTAX      TmnxMlpppEpClass {
                    null  (0),
                    ipv4Address (2),
                    macAddress (3)
                }
    MAX-ACCESS  read-create
    STATUS      current
    DESCRIPTION
       "The value of tmnxPppPlcyMlpppEpClass specifies the
        type of endpoint.
        
        If the value of 'tmnxPppPlcyMlpppEpClass' is equal to 'ipv4Address',
        the address for the MLPPP Endpoint Discriminator Option is taken from
        tmnxPppPlcyMlpppEpIpv4Address.
        
        If the value of 'tmnxPppPlcyMlpppEpClass' is equal to 'macAddress',
        the address for the MLPPP Endpoint Discriminator Option is taken from
        tmnxPppPlcyMlpppEpMacAddress.
        
        If the value of 'tmnxPppPlcyMlpppEpClass' is equal to 'null',
        the MLPPP Endpoint Discriminator Option must not be transmitted.
        
        A value other than 'null' is only allowed if this system performs
        the role of LAC with respect to the PPP clients using this policy."
    REFERENCE
       "RFC 1990 The PPP Multilink Protocol (MP), 
        section 5.1.3 Endpoint Discriminator Option."
    DEFVAL { null }
    ::= { tmnxPppPlcyMlpppEntry 3 }

tmnxPppPlcyMlpppEpIpv4Address OBJECT-TYPE
    SYNTAX      InetAddressIPv4
    MAX-ACCESS  read-create
    STATUS      current
    DESCRIPTION
       "The value of tmnxPppPlcyMlpppEpIpv4Address specifies the
        class 2 address to use in the MLPPP Endpoint Discriminator Option.
        
        While the value of tmnxPppPlcyMlpppEpClass is equal to 'ipv4Address',
        a value of all zeroes specifies that the system IP address be used;
        otherwise, it means that no address is specified."
    REFERENCE
       "RFC 1990 The PPP Multilink Protocol (MP), 
        section 5.1.3 Endpoint Discriminator Option."
    DEFVAL { '00000000'H }  
    ::= { tmnxPppPlcyMlpppEntry 4 }

tmnxPppPlcyMlpppEpMacAddress OBJECT-TYPE
    SYNTAX      MacAddress
    MAX-ACCESS  read-create
    STATUS      current
    DESCRIPTION
       "The value of tmnxPppPlcyMlpppEpMacAddress specifies the
        class 3 address to use in the MLPPP Endpoint Discriminator Option.
        
        While the value of tmnxPppPlcyMlpppEpClass is equal to 'macAddress',
        a value of all zeroes specifies that the system MAC address be used;
        otherwise, it means that no address is specified."
    REFERENCE
       "RFC 1990 The PPP Multilink Protocol (MP), 
        section 5.1.3 Endpoint Discriminator Option."
    DEFVAL { '000000000000'H }  
    ::= { tmnxPppPlcyMlpppEntry 5 }

tmnxPppPlcyMlpppShortSeqNumberRx OBJECT-TYPE
    SYNTAX      TruthValue
    MAX-ACCESS  read-create
    STATUS      current
    DESCRIPTION
       "The value of tmnxPppPlcyMlpppShortSeqNumberRx specifies 
        if this system requests to receive short sequence numbers from the peer.
         
        If the value of this object is 'true', this system includes 
        the Short Sequence Number Header Format Option in its LCP configuration
        options.
        
        If the value of this object is 'false', this system does not includes 
        the Short Sequence Number Header Format Option in its LCP configuration
        options."
    REFERENCE
       "RFC 1990 The PPP Multilink Protocol (MP)
        section 5.1.2."
    DEFVAL { false }  
    ::= { tmnxPppPlcyMlpppEntry 6 }
    
----------------------------------------------------------------------------
--  Notifications
----------------------------------------------------------------------------

-- --------------------------------------------------------
-- Notification Objects
-- --------------------------------------------------------
tmnxPppoeSessionFailureReason OBJECT-TYPE
    SYNTAX      DisplayString
    MAX-ACCESS  accessible-for-notify
    STATUS      current
    DESCRIPTION
        "The object tmnxPppoeSessionFailureReason indicates the
         problem encountered by the system while trying to create
         a new PPPoE session in the tmnxPppoeSessionTable."
    ::= { tmnxPppoeNotificationObjs 1 }

tmnxPppoeNcpFailureProtocol OBJECT-TYPE
    SYNTAX      INTEGER {
                    ipcp  (1),
                    ipv6cp (2)
                }
    MAX-ACCESS  accessible-for-notify
    STATUS      current
    DESCRIPTION
        "The value of tmnxPppoeNcpFailureProtocol indicates the
         failing NCP protocol."
    ::= { tmnxPppoeNotificationObjs 2 }

tmnxPppoeNcpFailureReason OBJECT-TYPE
    SYNTAX      DisplayString
    MAX-ACCESS  accessible-for-notify
    STATUS      current
    DESCRIPTION
        "The object tmnxPppoeNcpFailureReason indicates the
         problem encountered by the system during NCP phase."
    ::= { tmnxPppoeNotificationObjs 3 }

tmnxPppoeNotifyDescription  OBJECT-TYPE
    SYNTAX       DisplayString
    MAX-ACCESS   accessible-for-notify
    STATUS       current
    DESCRIPTION
        "The object tmnxPppoeNotifyDescription is a printable character 
         string."
::= { tmnxPppoeNotificationObjs 4 }

-- --------------------------------------------------------
-- Notifications
-- --------------------------------------------------------
tmnxPppoeSessionFailure NOTIFICATION-TYPE
    OBJECTS {
        svcId,
        sapPortId,
        sapEncapValue,
        tmnxPppoeSessionFailureReason
    }
    STATUS current
    DESCRIPTION
        "The tmnxPppoeSessionFailure notification indicates that
         the system could not create a new PPPoE session in the
         tmnxPppoeSessionTable. The problem is described in the
         object tmnxPppoeSessionFailureReason."
    ::= { tmnxPppoeNotifications 1}

tmnxPppoeNcpFailure NOTIFICATION-TYPE
    OBJECTS {
        svcId,
        sapPortId,
        sapEncapValue,
        tmnxPppoeNcpFailureProtocol,
        tmnxPppoeNcpFailureReason
    }
    STATUS current
    DESCRIPTION
        "The tmnxPppoeNcpFailure notification indicates that
         there is a NCP phase setup problem."
    ::= { tmnxPppoeNotifications 2}

tmnxMlpppBundleIndicatorsChange NOTIFICATION-TYPE
    OBJECTS {
        tmnxMlpppBundleIndicators,
        tmnxPppoeNotifyDescription
    }
    STATUS current
    DESCRIPTION
        "The tmnxMlpppBundleIndicatorsChange notification indicates that
         the value of the object tmnxMlpppBundleIndicatorsChange has changed.
         
         [CAUSE] The value of the object tmnxMlpppBundleIndicatorsChange has changed.
         A particular change is the change from 'lfi|lfiCfg' to 'lfiCfg': since interleaving
         is only supported on bundles with a single link, interleaving is disabled
         when a second link is added to a bundle.
         
         [EFFECT] When the value of the object tmnxMlpppBundleIndicatorsChange 
         changes from 'lfi|lifCfg' to 'lfiCfg', Link Fragmentation and Interleaving (LFI)
         is disabled on the bundle."
    ::= { tmnxPppoeNotifications 3}


----------------------------------------------------------------------------
--  Conformance Groups
----------------------------------------------------------------------------
tmnxPPPoEV6v0Group OBJECT-GROUP
    OBJECTS {
        tmnxPppoePlcyTableLastChanged,
        tmnxPppoePlcyRowStatus,
        tmnxPppoePlcyLastMgmtChange,
        tmnxPppoePlcyDescription,
        tmnxPppoePlcyPppMtu,
        tmnxPppoePlcyLcpKaInterval,
        tmnxPppoePlcyLcpKaHoldUpMplier,
        tmnxPppoePlcyDisableAcCookies,
        tmnxPppoePlcyPadoDelay,
        tmnxPppoePlcyMaxSessionsPerMac,
        tmnxPppoePlcyReplyOnPadt,

        tmnxPppoePlcyPppOptionTblLstChg,
        tmnxPppoePlcyOptionRowStatus,
        tmnxPppoePlcyOptionLstMgmtChange,
        tmnxPppoePlcyOptionType,
        tmnxPppoePlcyOptionValue,

        tmnxPppoeIesIfInfoTableLastChg,
        tmnxPppoeIesIfLastChg,
        tmnxPppoeIesIfDescription,
        tmnxPppoeIesIfAdminState,
        tmnxPppoeIesIfPolicy,
        tmnxPppoeIesIfSessionLimit,
        tmnxPppoeIesIfSapSessionLimit,
        tmnxPppoeIesIfPapChapUserDb,

        tmnxPppoeSapRxPadi,
        tmnxPppoeSapRxPadr,
        tmnxPppoeSapRxPadt,
        tmnxPppoeSapRxSession,
        tmnxPppoeSapRxInvalidVersion,
        tmnxPppoeSapRxInvalidType,
        tmnxPppoeSapRxInvalidCode,
        tmnxPppoeSapRxInvalidSession,
        tmnxPppoeSapRxInvalidLen,
        tmnxPppoeSapRxInvalidTags,
        tmnxPppoeSapRxInvalidAcCookie,
        tmnxPppoeSapRxDropped,
        tmnxPppoeSapTxPado,
        tmnxPppoeSapTxPads,
        tmnxPppoeSapTxPadt,
        tmnxPppoeSapTxSession,

        tmnxPppoeSessionUpTime,
        tmnxPppoeSessionLcpState,
        tmnxPppoeSessionIpcpState,
        tmnxPppoeSessionPppMtu,
        tmnxPppoeSessionPppAuthProtocol,
        tmnxPppoeSessionPppUserName,
        tmnxPppoeSessionSubIdent,
        tmnxPppoeSessionOriginSubIdent,
        tmnxPppoeSessionSubProfString,
        tmnxPppoeSessionSlaProfString,
        tmnxPppoeSessionAncpString,
        tmnxPppoeSessionInterDestId,
        tmnxPppoeSessionOriginStrings,
        tmnxPppoeSessionSessionTimeout,
        tmnxPppoeSessionIpAddrType,
        tmnxPppoeSessionIpAddr,
        tmnxPppoeSessionPrimaryDnsType,
        tmnxPppoeSessionPrimaryDns,
        tmnxPppoeSessionSecondryDnsType,
        tmnxPppoeSessionSecondryDns,
        tmnxPppoeSessionPrimaryNbnsType,
        tmnxPppoeSessionPrimaryNbns,
        tmnxPppoeSessionSecondryNbnsType,
        tmnxPppoeSessionSecondryNbns,
        tmnxPppoeSessionOriginIpcpInfo,
        tmnxPppoeSessionCircuitId,
        tmnxPppoeSessionRemoteId,

        tmnxPppoeSessionModSubIdent,
        tmnxPppoeSessionModSubProfStr,
        tmnxPppoeSessionModSlaProfStr,
        tmnxPppoeSessionModAncpStr,
        tmnxPppoeSessionModInterDestId,
        tmnxPppoeSessionEvaluateState,

        tmnxPppoeSessionRxUnknownProto,
        tmnxPppoeSessionRxLcpConfReq,
        tmnxPppoeSessionRxLcpConfAck,
        tmnxPppoeSessionRxLcpConfNak,
        tmnxPppoeSessionRxLcpConfRej,
        tmnxPppoeSessionRxLcpTermReq,
        tmnxPppoeSessionRxLcpTermAck,
        tmnxPppoeSessionRxLcpCodeRej,
        tmnxPppoeSessionRxLcpEchoReq,
        tmnxPppoeSessionRxLcpEchoRep,
        tmnxPppoeSessionRxLcpProtRej,
        tmnxPppoeSessionRxLcpDiscReq,
        tmnxPppoeSessionTxLcpConfReq,
        tmnxPppoeSessionTxLcpConfAck,
        tmnxPppoeSessionTxLcpConfNak,
        tmnxPppoeSessionTxLcpConfRej,
        tmnxPppoeSessionTxLcpTermReq,
        tmnxPppoeSessionTxLcpTermAck,
        tmnxPppoeSessionTxLcpCodeRej,
        tmnxPppoeSessionTxLcpEchoReq,
        tmnxPppoeSessionTxLcpEchoRep,
        tmnxPppoeSessionTxLcpProtRej,
        tmnxPppoeSessionTxLcpDiscReq,
        tmnxPppoeSessionRxPapAuthReq,
        tmnxPppoeSessionTxPapAuthAck,
        tmnxPppoeSessionTxPapAuthNak,
        tmnxPppoeSessionRxChapResponse,
        tmnxPppoeSessionTxChapChallenge,
        tmnxPppoeSessionTxChapSuccess,
        tmnxPppoeSessionTxChapFailure,
        tmnxPppoeSessionRxIpcpConfReq,
        tmnxPppoeSessionRxIpcpConfAck,
        tmnxPppoeSessionRxIpcpConfNak,
        tmnxPppoeSessionRxIpcpConfRej,
        tmnxPppoeSessionRxIpcpTermReq,
        tmnxPppoeSessionRxIpcpTermAck,
        tmnxPppoeSessionRxIpcpCodeRej,
        tmnxPppoeSessionTxIpcpConfReq,
        tmnxPppoeSessionTxIpcpConfAck,
        tmnxPppoeSessionTxIpcpConfNak,
        tmnxPppoeSessionTxIpcpConfRej,
        tmnxPppoeSessionTxIpcpTermReq,
        tmnxPppoeSessionTxIpcpTermAck,
        tmnxPppoeSessionTxIpcpCodeRej
    }
    STATUS obsolete
    DESCRIPTION
        "The group of objects supporting PPPoE on
         Alcatel-Lucent SROS series systems 6.0 release."
    ::= { tmnxPppoeGroups 1 }

tmnxPPPoEManagedRoutesGroup OBJECT-GROUP
    OBJECTS {
        tmnxPppoeManagedRouteStatus
    }
    STATUS obsolete
    DESCRIPTION
        "The group of objects supporting PPPoE Managed Routes on
         Alcatel-Lucent SROS series systems."
    ::= { tmnxPppoeGroups 5 }

tmnxPPPoEV6v0NotifyGroup NOTIFICATION-GROUP
     NOTIFICATIONS {
         tmnxPppoeSessionFailure
     }
     STATUS obsolete
     DESCRIPTION
        "The group of notifications generated by the PPPoE
         feature on Alcatel-Lucent SROS series systems 6.0 release."
     ::= { tmnxPppoeGroups 2 }

tmnxPPPoEV6v0NotificationObjGroup OBJECT-GROUP
    OBJECTS {
        tmnxPppoeSessionFailureReason
    }
    STATUS obsolete
    DESCRIPTION
         "The group of objects supporting management of PPPoE
         notification objects on Alcatel-Lucent SROS series systems
         6.0 release."
    ::= { tmnxPppoeGroups 3 }

tmnxPPPoEV6v0BsxGroup OBJECT-GROUP
    OBJECTS {
        tmnxPppoeSessionAppProfString,
        tmnxPppoeSessionModAppProfStr
    }
    STATUS current
    DESCRIPTION
         "The group of objects supporting management of PPPoE
         BSX (Application Assurance) objects on Alcatel-Lucent SROS
         series systems 6.0 release."
    ::= { tmnxPppoeGroups 4 }

tmnxPPPoEV6v1Group OBJECT-GROUP
    OBJECTS {
        tmnxPppoePlcyTableLastChanged,
        tmnxPppoePlcyRowStatus,
        tmnxPppoePlcyLastMgmtChange,
        tmnxPppoePlcyDescription,
        tmnxPppoePlcyPppMtu,
        tmnxPppoePlcyLcpKaInterval,
        tmnxPppoePlcyLcpKaHoldUpMplier,
        tmnxPppoePlcyDisableAcCookies,
        tmnxPppoePlcyPadoDelay,
        tmnxPppoePlcyMaxSessionsPerMac,
        tmnxPppoePlcyReplyOnPadt,
        tmnxPppoePlcyPppAuthentication,
        tmnxPppoePlcyPppInitialDelay,                       -- added in 6.1.R13

        tmnxPppoePlcyPppOptionTblLstChg,
        tmnxPppoePlcyOptionRowStatus,
        tmnxPppoePlcyOptionLstMgmtChange,
        tmnxPppoePlcyOptionType,
        tmnxPppoePlcyOptionValue,

        tmnxPppoeIesIfInfoTableLastChg,
        tmnxPppoeIesIfLastChg,
        tmnxPppoeIesIfDescription,
        tmnxPppoeIesIfAdminState,
        tmnxPppoeIesIfPolicy,
        tmnxPppoeIesIfSessionLimit,
        tmnxPppoeIesIfSapSessionLimit,
        tmnxPppoeIesIfPapChapUserDb,

        tmnxPppoeSapRxPadi,
        tmnxPppoeSapRxPadr,
        tmnxPppoeSapRxPadt,
        tmnxPppoeSapRxSession,
        tmnxPppoeSapRxInvalidVersion,
        tmnxPppoeSapRxInvalidType,
        tmnxPppoeSapRxInvalidCode,
        tmnxPppoeSapRxInvalidSession,
        tmnxPppoeSapRxInvalidLen,
        tmnxPppoeSapRxInvalidTags,
        tmnxPppoeSapRxInvalidAcCookie,
        tmnxPppoeSapRxDropped,
        tmnxPppoeSapTxPado,
        tmnxPppoeSapTxPads,
        tmnxPppoeSapTxPadt,
        tmnxPppoeSapTxSession,

        tmnxPppoeSessionUpTime,
        tmnxPppoeSessionLcpState,
        tmnxPppoeSessionIpcpState,
        tmnxPppoeSessionPppMtu,
        tmnxPppoeSessionPppAuthProtocol,
        tmnxPppoeSessionPppUserName,
        tmnxPppoeSessionSubIdent,
        tmnxPppoeSessionOriginSubIdent,
        tmnxPppoeSessionSubProfString,
        tmnxPppoeSessionSlaProfString,
        tmnxPppoeSessionAncpString,
        tmnxPppoeSessionInterDestId,
        tmnxPppoeSessionOriginStrings,
        tmnxPppoeSessionSessionTimeout,
        tmnxPppoeSessionIpAddrType,
        tmnxPppoeSessionIpAddr,
        tmnxPppoeSessionPrimaryDnsType,
        tmnxPppoeSessionPrimaryDns,
        tmnxPppoeSessionSecondryDnsType,
        tmnxPppoeSessionSecondryDns,
        tmnxPppoeSessionPrimaryNbnsType,
        tmnxPppoeSessionPrimaryNbns,
        tmnxPppoeSessionSecondryNbnsType,
        tmnxPppoeSessionSecondryNbns,
        tmnxPppoeSessionOriginIpcpInfo,
        tmnxPppoeSessionCircuitId,
        tmnxPppoeSessionRemoteId,
        tmnxPppoeSessionAddressPool,

        tmnxPppoeSessionModSubIdent,
        tmnxPppoeSessionModSubProfStr,
        tmnxPppoeSessionModSlaProfStr,
        tmnxPppoeSessionModAncpStr,
        tmnxPppoeSessionModInterDestId,
        tmnxPppoeSessionEvaluateState,

        tmnxPppoeSessionRxUnknownProto,
        tmnxPppoeSessionRxLcpConfReq,
        tmnxPppoeSessionRxLcpConfAck,
        tmnxPppoeSessionRxLcpConfNak,
        tmnxPppoeSessionRxLcpConfRej,
        tmnxPppoeSessionRxLcpTermReq,
        tmnxPppoeSessionRxLcpTermAck,
        tmnxPppoeSessionRxLcpCodeRej,
        tmnxPppoeSessionRxLcpEchoReq,
        tmnxPppoeSessionRxLcpEchoRep,
        tmnxPppoeSessionRxLcpProtRej,
        tmnxPppoeSessionRxLcpDiscReq,
        tmnxPppoeSessionTxLcpConfReq,
        tmnxPppoeSessionTxLcpConfAck,
        tmnxPppoeSessionTxLcpConfNak,
        tmnxPppoeSessionTxLcpConfRej,
        tmnxPppoeSessionTxLcpTermReq,
        tmnxPppoeSessionTxLcpTermAck,
        tmnxPppoeSessionTxLcpCodeRej,
        tmnxPppoeSessionTxLcpEchoReq,
        tmnxPppoeSessionTxLcpEchoRep,
        tmnxPppoeSessionTxLcpProtRej,
        tmnxPppoeSessionTxLcpDiscReq,
        tmnxPppoeSessionRxPapAuthReq,
        tmnxPppoeSessionTxPapAuthAck,
        tmnxPppoeSessionTxPapAuthNak,
        tmnxPppoeSessionRxChapResponse,
        tmnxPppoeSessionTxChapChallenge,
        tmnxPppoeSessionTxChapSuccess,
        tmnxPppoeSessionTxChapFailure,
        tmnxPppoeSessionRxIpcpConfReq,
        tmnxPppoeSessionRxIpcpConfAck,
        tmnxPppoeSessionRxIpcpConfNak,
        tmnxPppoeSessionRxIpcpConfRej,
        tmnxPppoeSessionRxIpcpTermReq,
        tmnxPppoeSessionRxIpcpTermAck,
        tmnxPppoeSessionRxIpcpCodeRej,
        tmnxPppoeSessionTxIpcpConfReq,
        tmnxPppoeSessionTxIpcpConfAck,
        tmnxPppoeSessionTxIpcpConfNak,
        tmnxPppoeSessionTxIpcpConfRej,
        tmnxPppoeSessionTxIpcpTermReq,
        tmnxPppoeSessionTxIpcpTermAck,
        tmnxPppoeSessionTxIpcpCodeRej
    }
    STATUS obsolete
    DESCRIPTION
        "The group of objects supporting PPPoE on
         Alcatel-Lucent SROS series systems 6.1 release."
    ::= { tmnxPppoeGroups 6 }

tmnxPPPoEV7v0Group OBJECT-GROUP
    OBJECTS {
        tmnxPppoePlcyTableLastChanged,
        tmnxPppoePlcyRowStatus,
        tmnxPppoePlcyLastMgmtChange,
        tmnxPppoePlcyDescription,
        tmnxPppoePlcyPppMtu,
        tmnxPppoePlcyLcpKaInterval,
        tmnxPppoePlcyLcpKaHoldUpMplier,
        tmnxPppoePlcyDisableAcCookies,
        tmnxPppoePlcyPadoDelay,
        tmnxPppoePlcyMaxSessionsPerMac,
        tmnxPppoePlcyReplyOnPadt,
        tmnxPppoePlcyPppAuthentication,
        tmnxPppoePlcyPppInitialDelay,                       -- added in 6.1.R13
        tmnxPppoePlcyPppMinChapChallenge,
        tmnxPppoePlcyPppMaxChapChallenge,

        tmnxPppoePlcyPppOptionTblLstChg,
        tmnxPppoePlcyOptionRowStatus,
        tmnxPppoePlcyOptionLstMgmtChange,
        tmnxPppoePlcyOptionType,
        tmnxPppoePlcyOptionValue,

        tmnxPppoeIesIfInfoTableLastChg,
        tmnxPppoeIesIfLastChg,
        tmnxPppoeIesIfDescription,
        tmnxPppoeIesIfAdminState,
        tmnxPppoeIesIfPolicy,
        tmnxPppoeIesIfSessionLimit,
        tmnxPppoeIesIfSapSessionLimit,
        tmnxPppoeIesIfUserDb,
        tmnxPppoeIesIfDhcpcCcagOriginSap,

        tmnxPppoeSapRxPadi,
        tmnxPppoeSapRxPadr,
        tmnxPppoeSapRxPadt,
        tmnxPppoeSapRxSession,
        tmnxPppoeSapRxInvalidVersion,
        tmnxPppoeSapRxInvalidType,
        tmnxPppoeSapRxInvalidCode,
        tmnxPppoeSapRxInvalidSession,
        tmnxPppoeSapRxInvalidLen,
        tmnxPppoeSapRxInvalidTags,
        tmnxPppoeSapRxInvalidAcCookie,
        tmnxPppoeSapRxDropped,
        tmnxPppoeSapTxPado,
        tmnxPppoeSapTxPads,
        tmnxPppoeSapTxPadt,
        tmnxPppoeSapTxSession,

        tmnxPppoeSessionUpTime,
        tmnxPppoeSessionLcpState,
        tmnxPppoeSessionIpcpState,
        tmnxPppoeSessionPppMtu,
        tmnxPppoeSessionPppAuthProtocol,
        tmnxPppoeSessionPppUserName,
        tmnxPppoeSessionSubIdent,
        tmnxPppoeSessionOriginSubIdent,
        tmnxPppoeSessionSubProfString,
        tmnxPppoeSessionSlaProfString,
        tmnxPppoeSessionAncpString,
        tmnxPppoeSessionInterDestId,
        tmnxPppoeSessionOriginStrings,
        tmnxPppoeSessionSessionTimeout,
        tmnxPppoeSessionIpAddrType,
        tmnxPppoeSessionIpAddr,
        tmnxPppoeSessionPrimaryDnsType,
        tmnxPppoeSessionPrimaryDns,
        tmnxPppoeSessionSecondryDnsType,
        tmnxPppoeSessionSecondryDns,
        tmnxPppoeSessionPrimaryNbnsType,
        tmnxPppoeSessionPrimaryNbns,
        tmnxPppoeSessionSecondryNbnsType,
        tmnxPppoeSessionSecondryNbns,
        tmnxPppoeSessionOriginIpcpInfo,
        tmnxPppoeSessionCircuitId,
        tmnxPppoeSessionRemoteId,
        tmnxPppoeSessionAddressPool,
        tmnxPppoeSessionType,
        tmnxPppoeSessionRetailerSvcId,
        tmnxPppoeSessionRetailerIf,
        tmnxPppoeSessionL2tpVrtrId,
        tmnxPppoeSessionL2tpConnectionId,
        tmnxPppoeSessionServiceName,
        tmnxPppoeSessionCategoryMapName,
        tmnxPppoeSessionRadiusClassAttr,
        tmnxPppoeSessionRadiusUserName,

        tmnxPppoeSessionModSubIdent,
        tmnxPppoeSessionModSubProfStr,
        tmnxPppoeSessionModSlaProfStr,
        tmnxPppoeSessionModAncpStr,
        tmnxPppoeSessionModInterDestId,
        tmnxPppoeSessionEvaluateState,

        tmnxPppoeSessionRxUnknownProto,
        tmnxPppoeSessionRxLcpConfReq,
        tmnxPppoeSessionRxLcpConfAck,
        tmnxPppoeSessionRxLcpConfNak,
        tmnxPppoeSessionRxLcpConfRej,
        tmnxPppoeSessionRxLcpTermReq,
        tmnxPppoeSessionRxLcpTermAck,
        tmnxPppoeSessionRxLcpCodeRej,
        tmnxPppoeSessionRxLcpEchoReq,
        tmnxPppoeSessionRxLcpEchoRep,
        tmnxPppoeSessionRxLcpProtRej,
        tmnxPppoeSessionRxLcpDiscReq,
        tmnxPppoeSessionTxLcpConfReq,
        tmnxPppoeSessionTxLcpConfAck,
        tmnxPppoeSessionTxLcpConfNak,
        tmnxPppoeSessionTxLcpConfRej,
        tmnxPppoeSessionTxLcpTermReq,
        tmnxPppoeSessionTxLcpTermAck,
        tmnxPppoeSessionTxLcpCodeRej,
        tmnxPppoeSessionTxLcpEchoReq,
        tmnxPppoeSessionTxLcpEchoRep,
        tmnxPppoeSessionTxLcpProtRej,
        tmnxPppoeSessionTxLcpDiscReq,
        tmnxPppoeSessionRxPapAuthReq,
        tmnxPppoeSessionTxPapAuthAck,
        tmnxPppoeSessionTxPapAuthNak,
        tmnxPppoeSessionRxChapResponse,
        tmnxPppoeSessionTxChapChallenge,
        tmnxPppoeSessionTxChapSuccess,
        tmnxPppoeSessionTxChapFailure,
        tmnxPppoeSessionRxIpcpConfReq,
        tmnxPppoeSessionRxIpcpConfAck,
        tmnxPppoeSessionRxIpcpConfNak,
        tmnxPppoeSessionRxIpcpConfRej,
        tmnxPppoeSessionRxIpcpTermReq,
        tmnxPppoeSessionRxIpcpTermAck,
        tmnxPppoeSessionRxIpcpCodeRej,
        tmnxPppoeSessionTxIpcpConfReq,
        tmnxPppoeSessionTxIpcpConfAck,
        tmnxPppoeSessionTxIpcpConfNak,
        tmnxPppoeSessionTxIpcpConfRej,
        tmnxPppoeSessionTxIpcpTermReq,
        tmnxPppoeSessionTxIpcpTermAck,
        tmnxPppoeSessionTxIpcpCodeRej
    }
    STATUS obsolete
    DESCRIPTION
        "The group of objects supporting PPPoE on
         Alcatel-Lucent SROS series systems 7.0 release."
    ::= { tmnxPppoeGroups 7 }

tmnxPPPoESessionBGPGroup OBJECT-GROUP
    OBJECTS {
        tmnxPppoeSessionBgpPrngPlcyName,
        tmnxPppoeSessionBgpAuthKeyChain,
        tmnxPppoeSessionBgpMD5AuthKey,
        tmnxPppoeSessionBgpImportPolicy,
        tmnxPppoeSessionBgpExportPolicy,
        tmnxPppoeSessionBgpPeerAS,
        tmnxPppoeSessionBgpPeeringStatus
    }
    STATUS obsolete
    DESCRIPTION
        "The group of objects supporting PPPoE BGP peering on
         Alcatel-Lucent SROS series systems."
    ::= { tmnxPppoeGroups 8 }

tmnxPPPoEV8v0Group OBJECT-GROUP
    OBJECTS {
        tmnxPppoePlcyTableLastChanged,
        tmnxPppoePlcyRowStatus,
        tmnxPppoePlcyLastMgmtChange,
        tmnxPppoePlcyDescription,
        tmnxPppoePlcyPppMtu,
        tmnxPppoePlcyLcpKaInterval,
        tmnxPppoePlcyLcpKaHoldUpMplier,
        tmnxPppoePlcyDisableAcCookies,
        tmnxPppoePlcyPadoDelay,
        tmnxPppoePlcyMaxSessionsPerMac,
        tmnxPppoePlcyReplyOnPadt,
        tmnxPppoePlcyPppAuthentication,
        tmnxPppoePlcyPppInitialDelay,                       -- added in 6.1.R13
        tmnxPppoePlcyPppMinChapChallenge,
        tmnxPppoePlcyPppMaxChapChallenge,

        tmnxPppoePlcyPppOptionTblLstChg,
        tmnxPppoePlcyOptionRowStatus,
        tmnxPppoePlcyOptionLstMgmtChange,
        tmnxPppoePlcyOptionType,
        tmnxPppoePlcyOptionValue,

        tmnxPppoeIesIfInfoTableLastChg,
        tmnxPppoeIesIfLastChg,
        tmnxPppoeIesIfDescription,
        tmnxPppoeIesIfAdminState,
        tmnxPppoeIesIfPolicy,
        tmnxPppoeIesIfSessionLimit,
        tmnxPppoeIesIfSapSessionLimit,
        tmnxPppoeIesIfUserDb,
        tmnxPppoeIesIfDhcpcCcagOriginSap,
        tmnxPppoeIesIfAntiSpoofing,
        
        tmnxPppoeSapRxPadi,
        tmnxPppoeSapRxPadr,
        tmnxPppoeSapRxPadt,
        tmnxPppoeSapRxSession,
        tmnxPppoeSapRxInvalidVersion,
        tmnxPppoeSapRxInvalidType,
        tmnxPppoeSapRxInvalidCode,
        tmnxPppoeSapRxInvalidSession,
        tmnxPppoeSapRxInvalidLen,
        tmnxPppoeSapRxInvalidTags,
        tmnxPppoeSapRxInvalidAcCookie,
        tmnxPppoeSapRxDropped,
        tmnxPppoeSapTxPado,
        tmnxPppoeSapTxPads,
        tmnxPppoeSapTxPadt,
        tmnxPppoeSapTxSession,

        tmnxPppoeSessionUpTime,
        tmnxPppoeSessionLcpState,
        tmnxPppoeSessionIpcpState,
        tmnxPppoeSessionPppMtu,
        tmnxPppoeSessionPppAuthProtocol,
        tmnxPppoeSessionPppUserName,
        tmnxPppoeSessionSubIdent,
        tmnxPppoeSessionOriginSubIdent,
        tmnxPppoeSessionSubProfString,
        tmnxPppoeSessionSlaProfString,
        tmnxPppoeSessionAncpString,
        tmnxPppoeSessionInterDestId,
        tmnxPppoeSessionOriginStrings,
        tmnxPppoeSessionSessionTimeout,
        tmnxPppoeSessionIpAddrType,
        tmnxPppoeSessionIpAddr,
        tmnxPppoeSessionPrimaryDnsType,
        tmnxPppoeSessionPrimaryDns,
        tmnxPppoeSessionSecondryDnsType,
        tmnxPppoeSessionSecondryDns,
        tmnxPppoeSessionPrimaryNbnsType,
        tmnxPppoeSessionPrimaryNbns,
        tmnxPppoeSessionSecondryNbnsType,
        tmnxPppoeSessionSecondryNbns,
        tmnxPppoeSessionOriginIpcpInfo,
        tmnxPppoeSessionCircuitId,
        tmnxPppoeSessionRemoteId,
        tmnxPppoeSessionAddressPool,
        tmnxPppoeSessionType,
        tmnxPppoeSessionRetailerSvcId,
        tmnxPppoeSessionRetailerIf,
        tmnxPppoeSessionL2tpVrtrId,
        tmnxPppoeSessionL2tpConnectionId,
        tmnxPppoeSessionServiceName,
        tmnxPppoeSessionCategoryMapName,
        tmnxPppoeSessionRadiusClassAttr,
        tmnxPppoeSessionRadiusUserName,
        tmnxPppoeSessionIpv6cpState,
        tmnxPppoeSessionInterfaceId,
        tmnxPppoeSessionOriginIpv6cpInfo,
        tmnxPppoeSessionIpv6DnsType,
        tmnxPppoeSessionIpv6Dns1,
        tmnxPppoeSessionIpv6Dns2,
        tmnxPppoeSessionIpv6DelPfxType,
        tmnxPppoeSessionIpv6DelPfxLen,
        tmnxPppoeSessionIpv6DelPfx,
        tmnxPppoeSessionIpv6PrefixType,
        tmnxPppoeSessionIpv6PrefixLen,
        tmnxPppoeSessionIpv6Prefix,

        tmnxPppoeSessionModSubIdent,
        tmnxPppoeSessionModSubProfStr,
        tmnxPppoeSessionModSlaProfStr,
        tmnxPppoeSessionModAncpStr,
        tmnxPppoeSessionModInterDestId,
        tmnxPppoeSessionEvaluateState,

        tmnxPppoeSessionRxUnknownProto,
        tmnxPppoeSessionRxLcpConfReq,
        tmnxPppoeSessionRxLcpConfAck,
        tmnxPppoeSessionRxLcpConfNak,
        tmnxPppoeSessionRxLcpConfRej,
        tmnxPppoeSessionRxLcpTermReq,
        tmnxPppoeSessionRxLcpTermAck,
        tmnxPppoeSessionRxLcpCodeRej,
        tmnxPppoeSessionRxLcpEchoReq,
        tmnxPppoeSessionRxLcpEchoRep,
        tmnxPppoeSessionRxLcpProtRej,
        tmnxPppoeSessionRxLcpDiscReq,
        tmnxPppoeSessionTxLcpConfReq,
        tmnxPppoeSessionTxLcpConfAck,
        tmnxPppoeSessionTxLcpConfNak,
        tmnxPppoeSessionTxLcpConfRej,
        tmnxPppoeSessionTxLcpTermReq,
        tmnxPppoeSessionTxLcpTermAck,
        tmnxPppoeSessionTxLcpCodeRej,
        tmnxPppoeSessionTxLcpEchoReq,
        tmnxPppoeSessionTxLcpEchoRep,
        tmnxPppoeSessionTxLcpProtRej,
        tmnxPppoeSessionTxLcpDiscReq,
        tmnxPppoeSessionRxPapAuthReq,
        tmnxPppoeSessionTxPapAuthAck,
        tmnxPppoeSessionTxPapAuthNak,
        tmnxPppoeSessionRxChapResponse,
        tmnxPppoeSessionTxChapChallenge,
        tmnxPppoeSessionTxChapSuccess,
        tmnxPppoeSessionTxChapFailure,
        tmnxPppoeSessionRxIpcpConfReq,
        tmnxPppoeSessionRxIpcpConfAck,
        tmnxPppoeSessionRxIpcpConfNak,
        tmnxPppoeSessionRxIpcpConfRej,
        tmnxPppoeSessionRxIpcpTermReq,
        tmnxPppoeSessionRxIpcpTermAck,
        tmnxPppoeSessionRxIpcpCodeRej,
        tmnxPppoeSessionTxIpcpConfReq,
        tmnxPppoeSessionTxIpcpConfAck,
        tmnxPppoeSessionTxIpcpConfNak,
        tmnxPppoeSessionTxIpcpConfRej,
        tmnxPppoeSessionTxIpcpTermReq,
        tmnxPppoeSessionTxIpcpTermAck,
        tmnxPppoeSessionTxIpcpCodeRej,
        tmnxPppoeSessionRxIpv6cpConfReq ,
        tmnxPppoeSessionRxIpv6cpConfAck ,
        tmnxPppoeSessionRxIpv6cpConfNak ,
        tmnxPppoeSessionRxIpv6cpConfRej ,
        tmnxPppoeSessionRxIpv6cpTermReq ,
        tmnxPppoeSessionRxIpv6cpTermAck ,
        tmnxPppoeSessionRxIpv6cpCodeRej ,
        tmnxPppoeSessionTxIpv6cpConfReq ,
        tmnxPppoeSessionTxIpv6cpConfAck ,
        tmnxPppoeSessionTxIpv6cpConfNak ,
        tmnxPppoeSessionTxIpv6cpConfRej ,
        tmnxPppoeSessionTxIpv6cpTermReq ,
        tmnxPppoeSessionTxIpv6cpTermAck ,
        tmnxPppoeSessionTxIpv6cpCodeRej,

        tmnxPppoeSessionOvrPIR,
        tmnxPppoeSessionOvrCIR,
        tmnxPppoeSessionOvrCBS,
        tmnxPppoeSessionOvrMBS,
        tmnxPppoeSessionAleDatalink,
        tmnxPppoeSessionAleEncaps1, 
        tmnxPppoeSessionAleEncaps2
    }
    STATUS current
    DESCRIPTION
        "The group of objects supporting PPPoE on
         Alcatel-Lucent SROS series systems 8.0 release."
    ::= { tmnxPppoeGroups 10 }

tmnxPPPoEV8v0NotifyGroup NOTIFICATION-GROUP
     NOTIFICATIONS {
         tmnxPppoeSessionFailure,
         tmnxPppoeNcpFailure
     }
     STATUS obsolete
     DESCRIPTION
        "The group of notifications generated by the PPPoE
         feature on Alcatel-Lucent SROS series systems 8.0 release."
     ::= { tmnxPppoeGroups 11 }

tmnxPPPoEV8v0NotifyObjsGroup OBJECT-GROUP
    OBJECTS {
        tmnxPppoeSessionFailureReason,
        tmnxPppoeNcpFailureProtocol,
        tmnxPppoeNcpFailureReason
    }
    STATUS obsolete
    DESCRIPTION
         "The group of objects supporting management of PPPoE
         notification objects on Alcatel-Lucent SROS series systems
         8.0 release."
    ::= { tmnxPppoeGroups 12 }

tmnxPPPoEV9v0Group OBJECT-GROUP
    OBJECTS {
        tmnxPppoePlcyPppIpcpSubnetNeg,
        tmnxPppoePlcyPadoAcName,
        tmnxPppoePlcyPppMtuForceGt1492,
        tmnxPppoePlcyUniqueSessIdsPerSap
    }
    STATUS current
    DESCRIPTION
        "The group of objects supporting PPPoE
         added in Alcatel-Lucent SROS series systems 9.0 release."
    ::= { tmnxPppoeGroups 15 }

tmnxPPPV9v0Group OBJECT-GROUP
    OBJECTS {
        tmnxPppIesIfTableLastChg,
        tmnxPppIesIfLastChg,
        tmnxPppIesIfDescription,
        tmnxPppIesIfAdminState,
        tmnxPppIesIfPolicy,       
        tmnxPppIesIfSessionLimit, 
        tmnxPppIesIfUserDb,
        tmnxPppoeSessionSubPppIndex
    }
    STATUS current
    DESCRIPTION
        "The group of objects supporting PPP
         added in Alcatel-Lucent SROS series systems 9.0 release."
    ::= { tmnxPppoeGroups 16 }

tmnxPPPMlpppGroup OBJECT-GROUP
    OBJECTS {
        tmnxMlpppBundleLocEpClass,      
        tmnxMlpppBundleLocEpAddress,
        tmnxMlpppBundleRemEpClass,      
        tmnxMlpppBundleRemEpAddress,
        tmnxMlpppBundleSubPppIndex,
        tmnxMlpppBundleMaxLinks,     
        tmnxMlpppBundleActualLinks,
        tmnxMlpppBundleRemMrru,
        tmnxMlpppBundleLocMrru,
        tmnxMlpppBundleIndicators,
        tmnxMlpppBundleFragmentSize,
        tmnxMlpppBundleMaxDelayCfg, 
        tmnxMlpppBundleMaxDelay,
        tmnxMlpppBundleReassemblyTo,
        tmnxMlpppBundleEgressRate,
        tmnxPppPlcyMlpppTableLastCh,  
        tmnxMlpppLinkRemMrru,
        tmnxPppPlcyMlpppLastCh,
        tmnxPppPlcyMlpppAcceptMrru,
        tmnxPppPlcyMlpppEpClass,
        tmnxPppPlcyMlpppEpIpv4Address,
        tmnxPppPlcyMlpppEpMacAddress,
        tmnxPppPlcyMlpppShortSeqNumberRx  
    }
    STATUS current
    DESCRIPTION
        "The group of objects supporting subscriber MLPPP
         in Alcatel-Lucent SROS series systems."
    ::= { tmnxPppoeGroups 20 }

tmnxPPPRejectDisabledNcp OBJECT-GROUP
    OBJECTS {
        tmnxPppoePlcyRejectDisabledNcp
    }
    STATUS current
    DESCRIPTION
        "The group of objects supporting management of
         PPP Policy reject disabled NCP's options
         in Alcatel-Lucent SROS series systems."
    ::= { tmnxPppoeGroups 21 }

tmnxPPPoEV10v0NotifyObjsGroup OBJECT-GROUP
    OBJECTS {
        tmnxPppoeSessionFailureReason,
        tmnxPppoeNcpFailureProtocol,
        tmnxPppoeNcpFailureReason,
        tmnxPppoeNotifyDescription
    }
    STATUS current
    DESCRIPTION
         "The group of objects supporting management of PPPoE
         notification objects on Alcatel-Lucent SROS series systems
         10.0 release."
    ::= { tmnxPppoeGroups 22 }

tmnxPPPoEV10v0NotifyGroup NOTIFICATION-GROUP
     NOTIFICATIONS {
         tmnxPppoeSessionFailure,
         tmnxPppoeNcpFailure,
         tmnxMlpppBundleIndicatorsChange
     }
     STATUS current
     DESCRIPTION
        "The group of notifications generated by the PPPoE
         feature on Alcatel-Lucent SROS series systems 10.0 release."
     ::= { tmnxPppoeGroups 23 }

tmnxPPPLcpIgnoreMagic OBJECT-GROUP
    OBJECTS {
        tmnxPppoePlcyLcpIgnoreMagic
    }
    STATUS current
    DESCRIPTION
        "The group of objects supporting management of
         PPP Policy lcp-ignore-magic-num options
         in Alcatel-Lucent SROS series systems."
    ::= { tmnxPppoeGroups 25 }

tmnxPPPoEV11v0Group OBJECT-GROUP
    OBJECTS {
        tmnxPppoeSapRxInvalidMac,
        tmnxPppoePlcySessionTimeout,
        tmnxPppoeIesIfDhcpcInclOptString
    }
    STATUS obsolete
    DESCRIPTION
        "The group of objects supporting PPPoE
         added in Alcatel-Lucent SROS series systems 11.0 release."
    ::= { tmnxPppoeGroups 26 }

tmnxPPPPlcyAllowSameCidGroup OBJECT-GROUP
    OBJECTS {
        tmnxPppoePlcyAllowSameCidForDhcp
    }
    STATUS current
    DESCRIPTION
        "The group of objects supporting management of
         multiple PPP sessions with the same MAC address in wholesale/retail,          
         in Alcatel-Lucent SROS series systems."
    ::= { tmnxPppoeGroups 27 }

tmnxPPPoEV12v0Group OBJECT-GROUP
    OBJECTS {
        tmnxPppoeSapRxInvalidMac,
        tmnxPppoePlcySessionTimeout,
        tmnxPppoePlcyReestablishSession
    }
    STATUS current
    DESCRIPTION
        "The group of objects supporting PPPoE
         (added) in Alcatel-Lucent SROS series systems 12.0 release."
    ::= { tmnxPppoeGroups 30 }

tmnxPPPoEDefaultUsernameGroup OBJECT-GROUP
    OBJECTS {
        tmnxPppoePlcyDefaultUserName,
        tmnxPppoePlcyDefaultPapPassword
    }
    STATUS current
    DESCRIPTION
        "The group of objects supporting PPPoE
         default username configuration."
    ::= { tmnxPppoeGroups 31 }

tmnxPPPoEObsoletedGroup OBJECT-GROUP
    OBJECTS {
-- obsoleted in release 7.0:
        tmnxPppoeIesIfPapChapUserDb,
-- obsoleted in release 9.0:
        tmnxPppoeManagedRouteStatus,
        tmnxPppoeSessionAleDatalink,
        tmnxPppoeSessionAleEncaps1,
        tmnxPppoeSessionAleEncaps2,
        tmnxPppoeSessionBgpAuthKeyChain,
        tmnxPppoeSessionBgpExportPolicy,
        tmnxPppoeSessionBgpImportPolicy,
        tmnxPppoeSessionBgpMD5AuthKey,
        tmnxPppoeSessionBgpPeerAS,
        tmnxPppoeSessionBgpPeeringStatus,
        tmnxPppoeSessionBgpPrngPlcyName,
        tmnxPppoeSessionEvaluateState,
        tmnxPppoeSessionModAncpStr,
        tmnxPppoeSessionModAppProfStr,
        tmnxPppoeSessionModInterDestId,
        tmnxPppoeSessionModSlaProfStr,
        tmnxPppoeSessionModSubIdent,
        tmnxPppoeSessionModSubProfStr,
        tmnxPppoeSessionOvrCBS,
        tmnxPppoeSessionOvrCIR,
        tmnxPppoeSessionOvrMBS,
        tmnxPppoeSessionOvrPIR,
        tmnxPppoeSessionRxChapResponse,
        tmnxPppoeSessionRxIpcpCodeRej,
        tmnxPppoeSessionRxIpcpConfAck,
        tmnxPppoeSessionRxIpcpConfNak,
        tmnxPppoeSessionRxIpcpConfRej,
        tmnxPppoeSessionRxIpcpConfReq,
        tmnxPppoeSessionRxIpcpTermAck,
        tmnxPppoeSessionRxIpcpTermReq,
        tmnxPppoeSessionRxIpv6cpCodeRej,
        tmnxPppoeSessionRxIpv6cpConfAck,
        tmnxPppoeSessionRxIpv6cpConfNak,
        tmnxPppoeSessionRxIpv6cpConfRej,
        tmnxPppoeSessionRxIpv6cpConfReq,
        tmnxPppoeSessionRxIpv6cpTermAck,
        tmnxPppoeSessionRxIpv6cpTermReq,
        tmnxPppoeSessionRxLcpCodeRej,
        tmnxPppoeSessionRxLcpConfAck,
        tmnxPppoeSessionRxLcpConfNak,
        tmnxPppoeSessionRxLcpConfRej,
        tmnxPppoeSessionRxLcpConfReq,
        tmnxPppoeSessionRxLcpDiscReq,
        tmnxPppoeSessionRxLcpEchoRep,
        tmnxPppoeSessionRxLcpEchoReq,
        tmnxPppoeSessionRxLcpProtRej,
        tmnxPppoeSessionRxLcpTermAck,
        tmnxPppoeSessionRxLcpTermReq,
        tmnxPppoeSessionRxPapAuthReq,
        tmnxPppoeSessionRxUnknownProto,
        tmnxPppoeSessionTxChapChallenge,
        tmnxPppoeSessionTxChapFailure,
        tmnxPppoeSessionTxChapSuccess,
        tmnxPppoeSessionTxIpcpCodeRej,
        tmnxPppoeSessionTxIpcpConfAck,
        tmnxPppoeSessionTxIpcpConfNak,
        tmnxPppoeSessionTxIpcpConfRej,
        tmnxPppoeSessionTxIpcpConfReq,
        tmnxPppoeSessionTxIpcpTermAck,
        tmnxPppoeSessionTxIpcpTermReq,
        tmnxPppoeSessionTxIpv6cpCodeRej,
        tmnxPppoeSessionTxIpv6cpConfAck,
        tmnxPppoeSessionTxIpv6cpConfNak,
        tmnxPppoeSessionTxIpv6cpConfRej,
        tmnxPppoeSessionTxIpv6cpConfReq,
        tmnxPppoeSessionTxIpv6cpTermAck,
        tmnxPppoeSessionTxIpv6cpTermReq,
        tmnxPppoeSessionTxLcpCodeRej,
        tmnxPppoeSessionTxLcpConfAck,
        tmnxPppoeSessionTxLcpConfNak,
        tmnxPppoeSessionTxLcpConfRej,
        tmnxPppoeSessionTxLcpConfReq,
        tmnxPppoeSessionTxLcpDiscReq,
        tmnxPppoeSessionTxLcpEchoRep,
        tmnxPppoeSessionTxLcpEchoReq,
        tmnxPppoeSessionTxLcpProtRej,
        tmnxPppoeSessionTxLcpTermAck,
        tmnxPppoeSessionTxLcpTermReq,
        tmnxPppoeSessionTxPapAuthAck,
        tmnxPppoeSessionTxPapAuthNak,
        tmnxPppoeManagedRouteStatus,
        tmnxPppoeSessionAleDatalink,
        tmnxPppoeSessionAleEncaps1,
        tmnxPppoeSessionAleEncaps2,
        tmnxPppoeSessionBgpAuthKeyChain,
        tmnxPppoeSessionBgpExportPolicy,
        tmnxPppoeSessionBgpImportPolicy,
        tmnxPppoeSessionBgpMD5AuthKey,
        tmnxPppoeSessionBgpPeerAS,
        tmnxPppoeSessionBgpPeeringStatus,
        tmnxPppoeSessionBgpPrngPlcyName,
        tmnxPppoeSessionEvaluateState,
        tmnxPppoeSessionModAncpStr,
        tmnxPppoeSessionModAppProfStr,
        tmnxPppoeSessionModInterDestId,
        tmnxPppoeSessionModSlaProfStr,
        tmnxPppoeSessionModSubIdent,
        tmnxPppoeSessionModSubProfStr,
        tmnxPppoeSessionOvrCBS,
        tmnxPppoeSessionOvrCIR,
        tmnxPppoeSessionOvrMBS,
        tmnxPppoeSessionOvrPIR,
        tmnxPppoeSessionUpTime,
        tmnxPppoeSessionLcpState,
        tmnxPppoeSessionIpcpState,
        tmnxPppoeSessionPppMtu,           
        tmnxPppoeSessionPppAuthProtocol,  
        tmnxPppoeSessionPppUserName,      
        tmnxPppoeSessionSubIdent,         
        tmnxPppoeSessionOriginSubIdent,   
        tmnxPppoeSessionSubProfString,    
        tmnxPppoeSessionSlaProfString,    
        tmnxPppoeSessionAncpString,       
        tmnxPppoeSessionInterDestId,
        tmnxPppoeSessionAppProfString,    
        tmnxPppoeSessionOriginStrings,    
        tmnxPppoeSessionSessionTimeout,
        tmnxPppoeSessionIpAddrType,       
        tmnxPppoeSessionIpAddr,           
        tmnxPppoeSessionPrimaryDnsType,   
        tmnxPppoeSessionPrimaryDns,       
        tmnxPppoeSessionSecondryDnsType,  
        tmnxPppoeSessionSecondryDns,      
        tmnxPppoeSessionPrimaryNbnsType,  
        tmnxPppoeSessionPrimaryNbns,      
        tmnxPppoeSessionSecondryNbnsType, 
        tmnxPppoeSessionSecondryNbns,     
        tmnxPppoeSessionOriginIpcpInfo,   
        tmnxPppoeSessionCircuitId,        
        tmnxPppoeSessionRemoteId,         
        tmnxPppoeSessionAddressPool,      
        tmnxPppoeSessionType,             
        tmnxPppoeSessionRetailerSvcId,    
        tmnxPppoeSessionRetailerIf,       
        tmnxPppoeSessionL2tpVrtrId,       
        tmnxPppoeSessionL2tpConnectionId, 
        tmnxPppoeSessionCategoryMapName,  
        tmnxPppoeSessionRadiusClassAttr,  
        tmnxPppoeSessionRadiusUserName,   
        tmnxPppoeSessionIpv6cpState,      
        tmnxPppoeSessionInterfaceId,      
        tmnxPppoeSessionOriginIpv6cpInfo, 
        tmnxPppoeSessionIpv6DnsType,      
        tmnxPppoeSessionIpv6Dns1,         
        tmnxPppoeSessionIpv6Dns2,         
        tmnxPppoeSessionIpv6DelPfxType,   
        tmnxPppoeSessionIpv6DelPfxLen,    
        tmnxPppoeSessionIpv6DelPfx,       
        tmnxPppoeSessionIpv6PrefixType,   
        tmnxPppoeSessionIpv6PrefixLen,    
        tmnxPppoeSessionIpv6Prefix,
-- obsoleted in release 12.0        
        tmnxPppoeIesIfDhcpcInclOptString
    }
    STATUS current
    DESCRIPTION
        "The group of objects obsoleted PPPoE objects."
    ::= { tmnxPppoeGroups 98 }

----------------------------------------------------------------------------
--  Compliance Info
----------------------------------------------------------------------------
tmnxPPPoE77x0V6v0MIBCompliance MODULE-COMPLIANCE
    STATUS obsolete
    DESCRIPTION
        "The compliance statement for TIMETRA-PPPOE-MIB
         on Alcatel-Lucent 7750 SR and 7710 series systems release R6.0."
    MODULE  -- this module
        MANDATORY-GROUPS {
            tmnxPPPoEV6v0Group,
            tmnxPPPoEV6v0NotifyGroup,
            tmnxPPPoEV6v0BsxGroup
        }
    ::= { tmnxPppoeCompliances 1 }

tmnxPPPoE77x0V6v1MIBCompliance MODULE-COMPLIANCE
    STATUS obsolete
    DESCRIPTION
        "The compliance statement for TIMETRA-PPPOE-MIB
         on Alcatel-Lucent 7750 SR and 7710 series systems release R6.1."
    MODULE  -- this module
        MANDATORY-GROUPS {
            tmnxPPPoEV6v1Group,
            tmnxPPPoEV6v0NotifyGroup,
            tmnxPPPoEV6v0BsxGroup,
            tmnxPPPoEManagedRoutesGroup
        }
    ::= { tmnxPppoeCompliances 2 }
            
tmnxPPPoE77x0V7v0MIBCompliance MODULE-COMPLIANCE
    STATUS obsolete
    DESCRIPTION
        "The compliance statement for TIMETRA-PPPOE-MIB
         on Alcatel-Lucent 7750 SR and 7710 series systems release R7.0."
    MODULE  -- this module
        MANDATORY-GROUPS {
            tmnxPPPoEV7v0Group,
            tmnxPPPoEV6v0NotifyGroup,
            tmnxPPPoEV6v0NotificationObjGroup,
            tmnxPPPoEV6v0BsxGroup,
            tmnxPPPoEManagedRoutesGroup,
            tmnxPPPoESessionBGPGroup
        }
    ::= { tmnxPppoeCompliances 3 }
            
tmnxPPPoE77x0V8v0MIBCompliance MODULE-COMPLIANCE
    STATUS obsolete
    DESCRIPTION
        "The compliance statement for TIMETRA-PPPOE-MIB
         on Alcatel-Lucent 7750 SR and 7710 series systems release R8.0."
    MODULE  -- this module
        MANDATORY-GROUPS {
            tmnxPPPoEV8v0Group,
            tmnxPPPoEV8v0NotifyGroup,
            tmnxPPPoEV6v0BsxGroup,
            tmnxPPPoEManagedRoutesGroup,
            tmnxPPPoESessionBGPGroup
        }
    ::= { tmnxPppoeCompliances 4 }
            
tmnxPPPoE77x0V9v0MIBCompliance MODULE-COMPLIANCE
    STATUS obsolete
    DESCRIPTION
        "The compliance statement for TIMETRA-PPPOE-MIB
         on Alcatel-Lucent 7750 SR and 7710 series systems release R9.0."
    MODULE  -- this module
        MANDATORY-GROUPS {
            tmnxPPPoEV8v0Group,
            tmnxPPPoEV9v0Group,
            tmnxPPPoEV8v0NotifyGroup,
            tmnxPPPoEV6v0BsxGroup,
            tmnxPPPV9v0Group,
            tmnxPPPPlcyAllowSameCidGroup
        }
    ::= { tmnxPppoeCompliances 5 }
    
tmnxPPPoEV10v0MIBCompliance MODULE-COMPLIANCE
    STATUS obsolete
    DESCRIPTION
        "The compliance statement for TIMETRA-PPPOE-MIB
         on Alcatel-Lucent SROS release 10.0."
    MODULE  -- this module
        MANDATORY-GROUPS {
            tmnxPPPoEV8v0Group,
            tmnxPPPoEV9v0Group,
            tmnxPPPoEV10v0NotifyGroup,
            tmnxPPPoEV6v0BsxGroup,
            tmnxPPPV9v0Group,
            tmnxPPPMlpppGroup,
            tmnxPPPRejectDisabledNcp,
            tmnxPPPPlcyAllowSameCidGroup
        }
    ::= { tmnxPppoeCompliances 6 }

tmnxPPPoEV11v0MIBCompliance MODULE-COMPLIANCE
    STATUS obsolete
    DESCRIPTION
        "The compliance statement for TIMETRA-PPPOE-MIB
         on Alcatel-Lucent SROS release 11.0."
    MODULE  -- this module
        MANDATORY-GROUPS {
            tmnxPPPoEV8v0Group,
            tmnxPPPoEV9v0Group,
            tmnxPPPoEV10v0NotifyGroup,
            tmnxPPPoEV6v0BsxGroup,
            tmnxPPPV9v0Group,
            tmnxPPPMlpppGroup,
            tmnxPPPRejectDisabledNcp,
            tmnxPPPLcpIgnoreMagic,
            tmnxPPPPlcyAllowSameCidGroup,
            tmnxPPPoEV11v0Group
        }
    ::= { tmnxPppoeCompliances 7 }
    
tmnxPPPoEV12v0MIBCompliance MODULE-COMPLIANCE
    STATUS current
    DESCRIPTION
        "The compliance statement for TIMETRA-PPPOE-MIB
         on Alcatel-Lucent SROS release 12.0."
    MODULE  -- this module
        MANDATORY-GROUPS {
            tmnxPPPoEV8v0Group,
            tmnxPPPoEV9v0Group,
            tmnxPPPoEV10v0NotifyGroup,
            tmnxPPPoEV6v0BsxGroup,
            tmnxPPPV9v0Group,
            tmnxPPPMlpppGroup,
            tmnxPPPRejectDisabledNcp,
            tmnxPPPLcpIgnoreMagic,
            tmnxPPPPlcyAllowSameCidGroup,
            tmnxPPPoEV12v0Group,
            tmnxPPPoEDefaultUsernameGroup
        }
    ::= { tmnxPppoeCompliances 8 }

END
