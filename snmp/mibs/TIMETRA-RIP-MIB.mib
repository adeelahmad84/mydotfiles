TIMETRA-RIP-MIB DEFINITIONS ::= BEGIN
 
IMPORTS
    MODULE-IDENTITY, OBJECT-TYPE, NOTIFICATION-TYPE,
    Unsigned32, Integer32, Counter32, Gauge32,
    IpAddress
        FROM SNMPv2-SMI

    MODULE-COMPLIANCE, OBJECT-GROUP, NOTIFICATION-GROUP
        FROM SNMPv2-CONF

    TEXTUAL-CONVENTION, RowStatus, TruthValue, TimeStamp
        FROM SNMPv2-TC

    InterfaceIndex
        FROM IF-MIB

    RouteTag
        FROM RIPv2-MIB

    TNamedItem, TItemDescription, TPolicyStatementNameOrEmpty,
    TmnxAdminState, TmnxOperState, TPriorityOrUndefined, TNamedItemOrEmpty
        FROM TIMETRA-TC-MIB

    timetraSRMIBModules, tmnxSRObjs, tmnxSRNotifyPrefix,
    tmnxSRConfs
        FROM TIMETRA-GLOBAL-MIB
        
    vRtrID, vRtrIfIndex
        FROM TIMETRA-VRTR-MIB
    ;

--
--
--
timetraRipMIBModule  MODULE-IDENTITY
        LAST-UPDATED "201401010000Z"
        ORGANIZATION "Alcatel-Lucent"
        CONTACT-INFO
            "Alcatel-Lucent SROS Support
             Web: http://support.alcatel-lucent.com"
        DESCRIPTION
         
        "This document is the SNMP MIB module for the Alcatel-Lucent SROS 
        implementation of RIPv2.

        Copyright 2003-2014 Alcatel-Lucent. All rights reserved.
        Reproduction of this document is authorized on the condition that
        the foregoing copyright notice is included.

        This SNMP MIB module (Specification) embodies Alcatel-Lucent's
        proprietary intellectual property.  Alcatel-Lucent retains all
        title and ownership in the Specification, including any
        revisions.

        Alcatel-Lucent grants all interested parties a non-exclusive
        license to use and distribute an unmodified copy of this
        Specification in connection with management of Alcatel-Lucent products,
        and without fee, provided this copyright notice and license
        appear on all copies.

        This Specification is supplied `as is', and Alcatel-Lucent makes
        no warranty, either express or implied, as to the use,
        operation, condition, or performance of the Specification.

        There is one RIP instance per virtual router.  Each RIP instance
        can have a number of interface groups.

        The value of most RIP configuration objects can be defaulted at
        three levels: at the per-interface level, at the interface group
        level, and at the RIP instance level.  The per-interface object
        values are determined by the following: - if the interface
        object is set, by that value. - else if its corresponding group
        object is set, by that value - else by the corresponding rip
        instance object value. "

        REVISION        "201401010000Z"   
        DESCRIPTION     "Rev 12.0               1 Jan 2014 00:00
                         12.0 release of the TIMETRA-RIP-MIB."

        REVISION        "201102010000Z"   
        DESCRIPTION     "Rev 9.0                1 Feb 2011 00:00
                         9.0 release of the TIMETRA-RIP-MIB."

        REVISION        "200501240000Z"   
        DESCRIPTION     "Rev 2.1                24 Jan 2005 00:00
                         2.1 release of the TIMETRA-RIP-MIB."

        REVISION        "200401150000Z"
        DESCRIPTION     "Rev 2.0                15 Jan 2004 00:00   
                         2.0 release of the TIMETRA-RIP-MIB."

        REVISION        "200308150000Z"
        DESCRIPTION     "Rev 1.2                15 Aug 2003 00:00   
                         1.2 release of the TIMETRA-RIP-MIB."

        REVISION        "200301200000Z"
        DESCRIPTION     "Rev 1.0                20 Jan 2003 00:00 
                         1.0 Release of the TIMETRA-RIP-MIB."

        REVISION        "200205210000Z"
        DESCRIPTION     "Rev 0.1                01 Jun 2002 00:00 
                         Initial version of the TIMETRA-RIP-MIB."

        ::= { timetraSRMIBModules 9 }


--%%%%%%%%%%%%%%%%%%%%%%%%%%%%%%%%%%%%%%%%%%%%%%%%%%%%%%%%%%%%%%%%%%%%%%
--
--  RIP extensions
--

vRtrRipObjs             OBJECT IDENTIFIER ::= { tmnxSRObjs 9 }
tmnxRipConformance      OBJECT IDENTIFIER ::= { tmnxSRConfs 9 }

vRtrRipNotifyPrefix    OBJECT IDENTIFIER ::= { tmnxSRNotifyPrefix 9 }
    vRtrRipNotifications    OBJECT IDENTIFIER ::= { vRtrRipNotifyPrefix 0 }

--
-- Textual conventions
--

TmnxRipAuthType ::= TEXTUAL-CONVENTION
    STATUS    current
    DESCRIPTION 
        "The TmnxRipAuthType TC defines the authentication method to be 
         used for RIP. Allowed values are : 
           noAuthentication(1) - No authentication method 
           simplePassword(2)   - Simple password based authentication
           md5(3)              - 16 byte MD5 Authentication 
           md20(4)             - 20 byte MD5 Authentication
        "
    REFERENCE  
        "RIP2-MIB.rip2IfConfAuthType"
    SYNTAX    INTEGER {
                  noAuthentication (1),
                  simplePassword (2),
                  md5 (3),
                  md20 (4)
              }

TmnxRipAuthKey ::= TEXTUAL-CONVENTION
    STATUS    current
    DESCRIPTION
        "The TmnxRipAuthKey TC defines the authentication key to be used
         when the authentication type has been configured to either 
         simplePassword(2), md5(3) or md20(4) (see TmnxRipAuthType)."
    REFERENCE
        "RIP2-MIB.rip2IfConfAuthKey"
    SYNTAX    OCTET STRING (SIZE(0..16))

TmnxRipMessageSize ::= TEXTUAL-CONVENTION
    STATUS    current
    DESCRIPTION
        "The TmnxRipMessageSize TC defines the maximum number of routes 
         that can be sent out per RIP update message."
    SYNTAX    Unsigned32 (25..255)


TmnxRipMetric ::= TEXTUAL-CONVENTION
    STATUS    current
    DESCRIPTION
        "The TmnxRipMetric TC defines the range for RIP route metric."
    SYNTAX    Unsigned32 (1..16)

TmnxRipPreference ::= TEXTUAL-CONVENTION
    STATUS    current
    DESCRIPTION
        "The TmnxRipPreference TC defines the preference to be assigned
         to RIP routes."
    SYNTAX    Unsigned32 (1..255)

TmnxRipReceive ::= TEXTUAL-CONVENTION
    STATUS    current
    DESCRIPTION 
        "The TmnxRipReceive TC defines the which version of RIP updates
         are to be accepted. Allowed values are : 
           rip1(1)         - Only RIPv1 packets are accepted
           rip2(2)         - Only RIPv2 packets are accepted
           rip1OrRip2(3)   - RIPv1 and v2 packets are accepted
           doNotReceive(4) - No packets are accepted
         
         Note that rip2 and rip1OrRip2 implies reception
         of multicast packets. 
        "
    REFERENCE  
        "RIP2-MIB.rip2IfConfReceive"
    SYNTAX    INTEGER {
                  rip1(1),
                  rip2(2),
                  rip1OrRip2(3),
                  doNotReceive(4)
              }

TmnxRipSend ::= TEXTUAL-CONVENTION
    STATUS    current
    DESCRIPTION 
        "The TmnxRipSend TC indicates how the router sends RIP updates on 
         an interface. Allowed values are : 
           doNotSend(1)      - No RIP updates sent
           ripVersion1(2)    - RIPv1 updates are broadcast
           rip1Compatible(3) - RIPv2 updates are broadcast
           ripVersion2(4)    - RIPv2 updates are multicast
           ripUnicast(6)     - RIPv2 updates are unicast

         RIP2-MIB (RFC 1724) also defines ripV1Demand(5) and ripV2Demand(6)
         which are not supported by the Alcatel-Lucent SROS series.
         
         ripUnicast(6) is only allowed at neighbor level."
    REFERENCE  
        "RIP2-MIB.rip2IfConfSend"
    SYNTAX    INTEGER {
                  doNotSend(1),
                  ripVersion1(2),
                  rip1Compatible(3),
                  ripVersion2(4),
                  ripUnicast(6)
              }

TmnxRipTimerFlush ::= TEXTUAL-CONVENTION
    STATUS    current
    DESCRIPTION
        "The TmnxRipTimerFlush TC defines the range for the Flush Timer 
         (or Garbage Collection timer). 
         The flush timer counts the number of seconds since the route 
         was declared invalid. When the timer expires the invalid route 
         will be flushed out from the route database."
    SYNTAX    Unsigned32 (1..1200)

TmnxRipTimerTimeout ::= TEXTUAL-CONVENTION
    STATUS    current
    DESCRIPTION
        "The TmnxRipTimerTimeout TC defines the range for the Timeout Timer. 
         The Timeout timer counts the number of seconds since the last update
         was received. When the timer expires the route will be declared 
         invalid in the route database."
    SYNTAX    Unsigned32 (1..1200)

TmnxRipTimerUpdate ::= TEXTUAL-CONVENTION
    STATUS    current
    DESCRIPTION
        "The TmnxRipTimerUpdate TC defines the range for the Update Timer. 
         The Update timer determines how often updates are sent."
    SYNTAX    Unsigned32 (1..600)

--
-- Global objects
--

vRtrRipGlobals OBJECT IDENTIFIER ::= { vRtrRipObjs 1 }

vRtrRipGlobalLearnedRoutes OBJECT-TYPE
    SYNTAX      Counter32
    MAX-ACCESS  read-only
    STATUS      current
    DESCRIPTION
        "vRtrRipGlobalLearnedRoutes is the number of routes learned
         by RIP."
    ::= { vRtrRipGlobals 1 }

vRtrRipGlobalTimedoutRoutes OBJECT-TYPE
    SYNTAX      Counter32
    MAX-ACCESS  read-only
    STATUS      current
    DESCRIPTION
        "vRtrRipGlobalTimedoutRoutes is the number of invalid
         RIP routes."
    ::= { vRtrRipGlobals 2 }

vRtrRipGlobalCurrentMemory OBJECT-TYPE
    SYNTAX      Counter32
    MAX-ACCESS  read-only
    STATUS      current
    DESCRIPTION
        "vRtrRipGlobalCurrentMemory is the amount of memory used by
         this RIP router instance."
    ::= { vRtrRipGlobals 3 }

vRtrRipGlobalMaximumMemory OBJECT-TYPE
    SYNTAX      Counter32
    MAX-ACCESS  read-only
    STATUS      current
    DESCRIPTION
        "vRtrRipGlobalMaximumMemory is the amount of memory allocated
         for this RIP router instance."
       ::= { vRtrRipGlobals 4 }

--
-- RIP Instance Table
--

vRtrRipInstanceTable OBJECT-TYPE
    SYNTAX      SEQUENCE OF VRtrRipInstanceEntry
    MAX-ACCESS  not-accessible
    STATUS      current
    DESCRIPTION 
        "vRtrRipInstanceTable contains configuration information for 
         the RIP instance on a virtual router."
    ::= { vRtrRipObjs 2 }

vRtrRipInstanceEntry OBJECT-TYPE
    SYNTAX      VRtrRipInstanceEntry
    MAX-ACCESS  not-accessible
    STATUS      current
    DESCRIPTION
        "vRtrRipInstanceEntry is an entry (conceptual row) in the
         vRtrRipInstanceTable. Each entry represents the configuration
         for a RIP instance.

         Entries in this table cannot be created and deleted via SNMP SET
         operations.  An entry in this table is created by the agent when
         vRtrRipStatus in the vRtrConfTable is set to 'create(1)'. The entry
         is destroyed when vRtrRipStatus is set to 'delete(2)'."
    INDEX  { vRtrID }
    ::= { vRtrRipInstanceTable 1 }

VRtrRipInstanceEntry ::= SEQUENCE {
    vRtrRipInstanceAuthType                   TmnxRipAuthType,
    vRtrRipInstanceAuthKey                    TmnxRipAuthKey,
    vRtrRipInstanceCheckZero                  TruthValue,
    vRtrRipInstanceMessageSize                TmnxRipMessageSize,
    vRtrRipInstanceMetricIn                   TmnxRipMetric,
    vRtrRipInstanceMetricOut                  TmnxRipMetric,
    vRtrRipInstancePreference                 TmnxRipPreference,
    vRtrRipInstanceReceive                    TmnxRipReceive,
    vRtrRipInstanceSend                       TmnxRipSend,
    vRtrRipInstanceSplitHorizon               TruthValue,
    vRtrRipInstanceTimerFlush                 TmnxRipTimerFlush,
    vRtrRipInstanceTimerTimeout               TmnxRipTimerTimeout,
    vRtrRipInstanceTimerUpdate                TmnxRipTimerUpdate,
    vRtrRipInstanceImportPolicy1              TPolicyStatementNameOrEmpty,
    vRtrRipInstanceImportPolicy2              TPolicyStatementNameOrEmpty,
    vRtrRipInstanceImportPolicy3              TPolicyStatementNameOrEmpty,
    vRtrRipInstanceImportPolicy4              TPolicyStatementNameOrEmpty,
    vRtrRipInstanceImportPolicy5              TPolicyStatementNameOrEmpty,
    vRtrRipInstanceExportPolicy1              TPolicyStatementNameOrEmpty,
    vRtrRipInstanceExportPolicy2              TPolicyStatementNameOrEmpty,
    vRtrRipInstanceExportPolicy3              TPolicyStatementNameOrEmpty,
    vRtrRipInstanceExportPolicy4              TPolicyStatementNameOrEmpty,
    vRtrRipInstanceExportPolicy5              TPolicyStatementNameOrEmpty,
    vRtrRipInstanceDescription                TItemDescription,
    vRtrRipInstanceAdminStatus                TmnxAdminState,
    vRtrRipInstanceOperStatus                 TmnxOperState,
    vRtrRipInstancePropagateMetric            TruthValue,
    vRtrRipInstanceExportLimit                Unsigned32,
    vRtrRipInstanceExpLmtLogPercent           Unsigned32,
    vRtrRipInstanceTotalExpRoutes             Gauge32
    }

vRtrRipInstanceAuthType OBJECT-TYPE
    SYNTAX      TmnxRipAuthType
    MAX-ACCESS  read-create
    STATUS      current
    DESCRIPTION
        "vRtrRipInstanceAuthType defines the type of authentication to 
         be used for the RIP instance."
    DEFVAL { noAuthentication }
    ::= { vRtrRipInstanceEntry 1 }

vRtrRipInstanceAuthKey OBJECT-TYPE
    SYNTAX      TmnxRipAuthKey
    MAX-ACCESS  read-create
    STATUS      current
    DESCRIPTION
        "vRtrRipInstanceAuthKey is the authentication key that should be
         used for the RIP instance when vRtrRipInstanceAuthType has a value 
         other than noAuthentication(1). Modifying the value of 
         vRtrRipInstanceAuthType does not modify the vRtrRipInstanceAuthKey
         value. If a string shorter than 16 octets is supplied, it will
         be left-justified and padded to 16 octets, on the right, with
         nulls (0x00).
         
         Reading this object always results in an  OCTET STRING of
         length zero; authentication may not be bypassed by reading
         the MIB object."
    DEFVAL { ''h }
    ::= { vRtrRipInstanceEntry 2 }

vRtrRipInstanceCheckZero OBJECT-TYPE
    SYNTAX      TruthValue
    MAX-ACCESS  read-create
    STATUS      current
    DESCRIPTION
        "vRtrRipInstanceCheckZero specifies whether RIP updates are 
         checked for for zero values in fields defined as Must-Be-Zero
         by the RIPv1 and v2 specifications."
    DEFVAL { false }
    ::= { vRtrRipInstanceEntry 3 }

vRtrRipInstanceMessageSize OBJECT-TYPE
    SYNTAX      TmnxRipMessageSize
    MAX-ACCESS  read-create
    STATUS      current
    DESCRIPTION
        "vRtrRipInstanceMessageSize is the maximum number of routes 
         that can be sent out per RIP update message."
    DEFVAL { 25 }
    ::= { vRtrRipInstanceEntry 4 }

vRtrRipInstanceMetricIn OBJECT-TYPE
    SYNTAX      TmnxRipMetric
    MAX-ACCESS  read-create
    STATUS      current
    DESCRIPTION
        "vRtrRipInstanceMetricIn is the value added to the metric of routes
         received from a RIP neighbor."
    DEFVAL { 1 }
    ::= { vRtrRipInstanceEntry 5 }

vRtrRipInstanceMetricOut OBJECT-TYPE
    SYNTAX      TmnxRipMetric
    MAX-ACCESS  read-create
    STATUS      current
    DESCRIPTION
        "vRtrRipInstanceMetricOut is the value added to the metric of routes
         exported into RIP and advertised to RIP neighbors."
    DEFVAL { 1 }
    ::= { vRtrRipInstanceEntry 6 }

vRtrRipInstancePreference OBJECT-TYPE
    SYNTAX      TmnxRipPreference
    MAX-ACCESS  read-create
    STATUS      current
    DESCRIPTION
        "vRtrRipInstancePreference is the route preference to be assigned
         to RIP routes. This value may be overridden via route policies."
    DEFVAL { 100 }
    ::= { vRtrRipInstanceEntry 7 }

vRtrRipInstanceReceive OBJECT-TYPE
    SYNTAX      TmnxRipReceive
    MAX-ACCESS  read-create
    STATUS      current
    DESCRIPTION
        "vRtrRipInstanceReceive indicates which version of RIP updates are
         to be accepted."
    DEFVAL { rip1OrRip2 }
    ::= { vRtrRipInstanceEntry 8 }

vRtrRipInstanceSend OBJECT-TYPE
    SYNTAX      TmnxRipSend
    MAX-ACCESS  read-create
    STATUS      current
    DESCRIPTION
        "vRtrRipInstanceSend indicates the version to be used for sending
         RIP updates."
    DEFVAL { rip1Compatible }
    ::= { vRtrRipInstanceEntry 9 }

vRtrRipInstanceSplitHorizon OBJECT-TYPE
    SYNTAX      TruthValue
    MAX-ACCESS  read-create
    STATUS      current
    DESCRIPTION
        "vRtrRipInstanceSplitHorizon indicates whether split horizon scheme
         is to be used when sending updates to RIP neighbors."
    DEFVAL { true }
    ::= { vRtrRipInstanceEntry 10 }

vRtrRipInstanceTimerFlush OBJECT-TYPE
    SYNTAX      TmnxRipTimerFlush
    UNITS       "seconds"
    MAX-ACCESS  read-create
    STATUS      current
    DESCRIPTION
        "vRtrRipInstanceTimerFlush is the number of seconds after a route
         has been declared invalid that it is flushed from the route
         database."
    DEFVAL { 120 }
    ::= { vRtrRipInstanceEntry 11 }

vRtrRipInstanceTimerTimeout OBJECT-TYPE
    SYNTAX      TmnxRipTimerTimeout
    UNITS       "seconds"
    MAX-ACCESS  read-create
    STATUS      current
    DESCRIPTION
        "vRtrRipInstanceTimerTimeout is the number of seconds after a route
         has been discovered or last updated that it is declared invalid
         in the route database."
    DEFVAL { 180 }
    ::= { vRtrRipInstanceEntry 12 }

vRtrRipInstanceTimerUpdate OBJECT-TYPE
    SYNTAX      TmnxRipTimerUpdate
    UNITS        "seconds"
    MAX-ACCESS  read-create
    STATUS      current
    DESCRIPTION
        "vRtrRipInstanceTimerUpdate determines how often updates are sent."
    DEFVAL { 30 }
    ::= { vRtrRipInstanceEntry 13 }

vRtrRipInstanceImportPolicy1 OBJECT-TYPE
    SYNTAX      TPolicyStatementNameOrEmpty
    MAX-ACCESS  read-create
    STATUS      current
    DESCRIPTION
        "vRtrRipInstanceImportPolicy1 is import policy number 1 for the
         instance level."
    DEFVAL { ''H }   -- the empty string
    ::= { vRtrRipInstanceEntry 14 }

vRtrRipInstanceImportPolicy2 OBJECT-TYPE
    SYNTAX      TPolicyStatementNameOrEmpty
    MAX-ACCESS  read-create
    STATUS      current
    DESCRIPTION
        "vRtrRipInstanceImportPolicy2 is import policy number 2 for the
         instance level."
    DEFVAL { ''H }   -- the empty string
    ::= { vRtrRipInstanceEntry 15 }

vRtrRipInstanceImportPolicy3 OBJECT-TYPE
    SYNTAX      TPolicyStatementNameOrEmpty
    MAX-ACCESS  read-create
    STATUS      current
    DESCRIPTION
        "vRtrRipInstanceImportPolicy3 is import policy number 3 for the
         instance level."
    DEFVAL { ''H }   -- the empty string
    ::= { vRtrRipInstanceEntry 16 }

vRtrRipInstanceImportPolicy4 OBJECT-TYPE
    SYNTAX      TPolicyStatementNameOrEmpty
    MAX-ACCESS  read-create
    STATUS      current
    DESCRIPTION
        "vRtrRipInstanceImportPolicy4 is import policy number 4 for the
         instance level."
    DEFVAL { ''H }   -- the empty string
    ::= { vRtrRipInstanceEntry 17 }

vRtrRipInstanceImportPolicy5 OBJECT-TYPE
    SYNTAX      TPolicyStatementNameOrEmpty
    MAX-ACCESS  read-create
    STATUS      current
    DESCRIPTION
        "vRtrRipInstanceImportPolicy5 is import policy number 5 for the
         instance level."
    DEFVAL { ''H }   -- the empty string
    ::= { vRtrRipInstanceEntry 18 }

vRtrRipInstanceExportPolicy1 OBJECT-TYPE
    SYNTAX      TPolicyStatementNameOrEmpty
    MAX-ACCESS  read-create
    STATUS      current
    DESCRIPTION
        "vRtrRipInstanceExportPolicy1 is export policy number 1 for the
         instance level."
    DEFVAL { ''H }   -- the empty string
    ::= { vRtrRipInstanceEntry 19 }

vRtrRipInstanceExportPolicy2 OBJECT-TYPE
    SYNTAX      TPolicyStatementNameOrEmpty
    MAX-ACCESS  read-create
    STATUS      current
    DESCRIPTION
        "vRtrRipInstanceExportPolicy2 is export policy number 2 for the
         instance level."
    DEFVAL { ''H }   -- the empty string
    ::= { vRtrRipInstanceEntry 20 }

vRtrRipInstanceExportPolicy3 OBJECT-TYPE
    SYNTAX      TPolicyStatementNameOrEmpty
    MAX-ACCESS  read-create
    STATUS      current
    DESCRIPTION
        "vRtrRipInstanceExportPolicy3 is export policy number 3 for the
         instance level."
    DEFVAL { ''H }   -- the empty string
    ::= { vRtrRipInstanceEntry 21 }

vRtrRipInstanceExportPolicy4 OBJECT-TYPE
    SYNTAX      TPolicyStatementNameOrEmpty
    MAX-ACCESS  read-create
    STATUS      current
    DESCRIPTION
        "vRtrRipInstanceExportPolicy4 is export policy number 4 for the
         instance level."
    DEFVAL { ''H }   -- the empty string
    ::= { vRtrRipInstanceEntry 22 }

vRtrRipInstanceExportPolicy5 OBJECT-TYPE
    SYNTAX      TPolicyStatementNameOrEmpty
    MAX-ACCESS  read-create
    STATUS      current
    DESCRIPTION
        "vRtrRipInstanceExportPolicy5 is export policy number 5 for the
         instance level."
    DEFVAL { ''H }   -- the empty string
    ::= { vRtrRipInstanceEntry 23 }

vRtrRipInstanceDescription OBJECT-TYPE
    SYNTAX      TItemDescription
    MAX-ACCESS  read-create
    STATUS      current
    DESCRIPTION
        "vRtrRipInstanceDescription specifies a textual description for
         the RIP instance."
    DEFVAL { ''H }   -- the empty string
    ::= { vRtrRipInstanceEntry 24 }

vRtrRipInstanceAdminStatus OBJECT-TYPE
    SYNTAX      TmnxAdminState
    MAX-ACCESS  read-create
    STATUS      current
    DESCRIPTION
       "The value of vRtrRipInstanceAdminStatus indicates the desired
        administrative state for this RIP group or instance.

        If the RIP instance entry object is set to outOfService, then
        all RIP groups and interfaces are shutdown operationally.

        If set to inService, the entity and all groups and interfaces
        below it are re-enabled operationally unless they have been 
        administratively shutdown at the group or interface level."
    DEFVAL { inService }
    ::= { vRtrRipInstanceEntry 25 }

vRtrRipInstanceOperStatus OBJECT-TYPE
    SYNTAX      TmnxOperState
    MAX-ACCESS  read-only
    STATUS      current
    DESCRIPTION
        "The value of vRtrRipInstanceOperStatus indicates the current
         operational status of this RIP instance"
    ::= { vRtrRipInstanceEntry 26 }

vRtrRipInstancePropagateMetric     OBJECT-TYPE
    SYNTAX      TruthValue
    MAX-ACCESS  read-create
    STATUS      current
    DESCRIPTION
        "The value of vRtrRipInstancePropagateMetric specifies whether the metric
         used by RIP or OSPF protocol should be propagated to the Provider
         Edge (PE) routers as well, in addition to the Customer Equipment
         (CE) routers.  vRtrRipInstancePropagateMetric only applies to VPRN RIP instance
         and not the base router RIP instance."
    DEFVAL { false }
    ::= { vRtrRipInstanceEntry 27 }    
        
vRtrRipInstanceExportLimit         OBJECT-TYPE
    SYNTAX      Unsigned32
    MAX-ACCESS  read-create
    STATUS      current
    DESCRIPTION
        "The value of vRtrRipInstanceExportLimit specifies the maximum number of 
        routes or prefixes that can be exported into RIP from the route table.

        A value of 0 indicates that the export limit for routes or prefixes has
        been disabled."
    DEFVAL { 0 }
    ::= { vRtrRipInstanceEntry 28 }

vRtrRipInstanceExpLmtLogPercent       OBJECT-TYPE
    SYNTAX      Unsigned32  (0..100)
    UNITS       "percentage"
    MAX-ACCESS  read-create
    STATUS      current
    DESCRIPTION
        "The value of vRtrRipInstanceExpLmtLogPercent specifies the percentage
        of the export-limit, at which a warning log message and SNMP 
        notification would be sent. This would only be a warning and additional 
        routes will be learned up to 100% of vRtrRipInstanceExportLimit.

        A value of 0 indicates that vRtrRipInstanceExpLmtLogPercent is disabled
        and no log message or SNMP notification would be sent."
    DEFVAL { 0 }
    ::= { vRtrRipInstanceEntry 29 }

vRtrRipInstanceTotalExpRoutes       OBJECT-TYPE
    SYNTAX      Gauge32
    MAX-ACCESS  read-only
    STATUS      current
    DESCRIPTION
        "The value of vRtrRipInstanceTotalExpRoutes indicates the total number
         of routes exported into RIP from the route table manager when an export
         policy is configured.

         Value of vRtrRipInstanceTotalExpRoutes would be 0 when no export policy
         is configured."
    ::= { vRtrRipInstanceEntry 30 }

--
-- RIP Group Table
--

vRtrRipGroupTable OBJECT-TYPE
    SYNTAX      SEQUENCE OF VRtrRipGroupEntry
    MAX-ACCESS  not-accessible
    STATUS      current
    DESCRIPTION
       "vRtrRipGroupTable contains configuration information for each
        group of interfaces running RIP."
    ::= { vRtrRipObjs 3 }

vRtrRipGroupEntry OBJECT-TYPE
    SYNTAX      VRtrRipGroupEntry
    MAX-ACCESS  not-accessible
    STATUS      current
    DESCRIPTION
        "vRtrRipGroupEntry is an entry (conceptual row) in the
         vRtrRipGroupTable. Each entry represents the RIP configuration
         of a group of interfaces on the router.

         Entries in this table can be created and deleted via SNMP SET
         operations to vRtrRipGroupRowStatus."
    INDEX  { vRtrID, vRtrRipGroupName }
    ::= { vRtrRipGroupTable 1 }

VRtrRipGroupEntry ::= SEQUENCE {
    vRtrRipGroupName                       TNamedItem,
    vRtrRipGroupAuthType                   TmnxRipAuthType,
    vRtrRipGroupAuthKey                    TmnxRipAuthKey,
    vRtrRipGroupCheckZero                  TruthValue,
    vRtrRipGroupMessageSize                TmnxRipMessageSize,
    vRtrRipGroupMetricIn                   TmnxRipMetric,
    vRtrRipGroupMetricOut                  TmnxRipMetric,
    vRtrRipGroupPreference                 TmnxRipPreference,
    vRtrRipGroupReceive                    TmnxRipReceive,
    vRtrRipGroupSend                       TmnxRipSend,
    vRtrRipGroupSplitHorizon               TruthValue,
    vRtrRipGroupTimerFlush                 TmnxRipTimerFlush,
    vRtrRipGroupTimerTimeout               TmnxRipTimerTimeout,
    vRtrRipGroupTimerUpdate                TmnxRipTimerUpdate,
    vRtrRipGroupImportPolicy1              TPolicyStatementNameOrEmpty,
    vRtrRipGroupImportPolicy2              TPolicyStatementNameOrEmpty,
    vRtrRipGroupImportPolicy3              TPolicyStatementNameOrEmpty,
    vRtrRipGroupImportPolicy4              TPolicyStatementNameOrEmpty,
    vRtrRipGroupImportPolicy5              TPolicyStatementNameOrEmpty,
    vRtrRipGroupExportPolicy1              TPolicyStatementNameOrEmpty,
    vRtrRipGroupExportPolicy2              TPolicyStatementNameOrEmpty,
    vRtrRipGroupExportPolicy3              TPolicyStatementNameOrEmpty,
    vRtrRipGroupExportPolicy4              TPolicyStatementNameOrEmpty,
    vRtrRipGroupExportPolicy5              TPolicyStatementNameOrEmpty,
    vRtrRipGroupDescription                TItemDescription,
    vRtrRipGroupInheritance                Unsigned32,
    vRtrRipGroupAdminStatus                TmnxAdminState,
    vRtrRipGroupOperStatus                 TmnxOperState,
    vRtrRipGroupRowStatus                  RowStatus
    }

vRtrRipGroupName OBJECT-TYPE
    SYNTAX      TNamedItem
    MAX-ACCESS  not-accessible
    STATUS      current
    DESCRIPTION
        "vRtrRipGroupName uniquely identifies a RIP group for the
         router instance."
    ::= { vRtrRipGroupEntry 1 }

vRtrRipGroupAuthType OBJECT-TYPE
    SYNTAX      TmnxRipAuthType
    MAX-ACCESS  read-create
    STATUS      current
    DESCRIPTION
       "vRtrRipGroupAuthType defines the type of authentication to be
        used for all the interfaces in this group."
    DEFVAL { noAuthentication }
    ::= { vRtrRipGroupEntry 2 }

vRtrRipGroupAuthKey OBJECT-TYPE
    SYNTAX      TmnxRipAuthKey
    MAX-ACCESS  read-create
    STATUS      current
    DESCRIPTION
        "vRtrRipGroupAuthKey is the authentication key that should be
         used for the interfaces in this group when vRtrRipInstanceAuthType
         has a value other than noAuthentication(1). Modifying the value of 
         vRtrRipGroupAuthType does not modify the vRtrRipGroupAuthKey
         value. If a string shorter than 16 octets is supplied, it will
         be left-justified and padded to 16 octets, on the right, with
         nulls (0x00).

         Reading this object always results in an  OCTET STRING of
         length zero; authentication may not be bypassed by reading
         the MIB object."
    DEFVAL { ''h }
    ::= { vRtrRipGroupEntry 3 }

vRtrRipGroupCheckZero OBJECT-TYPE
    SYNTAX      TruthValue
    MAX-ACCESS  read-create
    STATUS      current
    DESCRIPTION
       "vRtrRipGroupCheckZero specifies whether RIP updates received on
        interfaces in this group are checked for zero values in fields 
        defined as Must-Be-Zero by the RIPv1 and v2 specifications."
    DEFVAL { false }
    ::= { vRtrRipGroupEntry 4 }

vRtrRipGroupMessageSize OBJECT-TYPE
    SYNTAX      TmnxRipMessageSize
    MAX-ACCESS  read-create
    STATUS      current
    DESCRIPTION
        "vRtrRipGroupMessageSize is the maximum number of routes 
         that can be sent out per RIP update message."
    DEFVAL { 25 }
    ::= { vRtrRipGroupEntry 5 }

vRtrRipGroupMetricIn OBJECT-TYPE
    SYNTAX      TmnxRipMetric
    MAX-ACCESS  read-create
    STATUS      current
    DESCRIPTION
        "vRtrRipGroupMetricIn is the value added to the metric of routes
         received on a RIP interface which is a part of this group."
    DEFVAL { 1 }
    ::= { vRtrRipGroupEntry 6 }

vRtrRipGroupMetricOut OBJECT-TYPE
    SYNTAX      TmnxRipMetric
    MAX-ACCESS  read-create
    STATUS      current
    DESCRIPTION
        "vRtrRipGroupMetricOut is the value added to the metric of routes
         exported into RIP and advertised out on RIP interfaces in this
         group."
    DEFVAL { 1 }
    ::= { vRtrRipGroupEntry 7 }

vRtrRipGroupPreference OBJECT-TYPE
    SYNTAX      TmnxRipPreference
    MAX-ACCESS  read-create
    STATUS      current
    DESCRIPTION
        "vRtrRipGroupPreference is the route preference to be assigned
         to RIP routes received on interfaces that are a part of this 
         group. This value may be overridden via route policies."
    DEFVAL { 100 }
    ::= { vRtrRipGroupEntry 8 }

vRtrRipGroupReceive OBJECT-TYPE
    SYNTAX      TmnxRipReceive
    MAX-ACCESS  read-create
    STATUS      current
    DESCRIPTION
       "vRtrRipGroupReceive indicates which version of RIP updates are
        to be accepted for the group of interfaces."
    DEFVAL { rip1OrRip2 }
    ::= { vRtrRipGroupEntry 9 }

vRtrRipGroupSend OBJECT-TYPE
    SYNTAX      TmnxRipSend
    MAX-ACCESS  read-create
    STATUS      current
    DESCRIPTION
        "vRtrRipGroupSend indicates the version to be used for sending
         RIP updates on interfaces within the group."
    DEFVAL { rip1Compatible }
    ::= { vRtrRipGroupEntry 10 }

vRtrRipGroupSplitHorizon OBJECT-TYPE
    SYNTAX      TruthValue
    MAX-ACCESS  read-create
    STATUS      current
    DESCRIPTION
        "vRtrRipGroupSplitHorizon indicates whether split horizon scheme
         is to be used when sending updates on interfaces which are a 
         part of the group."
    DEFVAL { true }
    ::= { vRtrRipGroupEntry 11 }

vRtrRipGroupTimerFlush OBJECT-TYPE
    SYNTAX      TmnxRipTimerFlush
    UNITS       "seconds"
    MAX-ACCESS  read-create
    STATUS      current
    DESCRIPTION
        "vRtrRipGroupTimerFlush is the number of seconds after a route
         has been declared invalid that it is flushed from the route
         database."
    DEFVAL { 120 }
    ::= { vRtrRipGroupEntry 12 }

vRtrRipGroupTimerTimeout OBJECT-TYPE
    SYNTAX      TmnxRipTimerTimeout
    UNITS       "seconds"
    MAX-ACCESS  read-create
    STATUS      current
    DESCRIPTION
        "vRtrRipGroupTimerTimeout is the number of seconds after a route
         has been discovered or last updated that it is declared invalid
         in the route database."
    DEFVAL { 180 }
    ::= { vRtrRipGroupEntry 13 }

vRtrRipGroupTimerUpdate OBJECT-TYPE
    SYNTAX      TmnxRipTimerUpdate
    UNITS       "seconds"
    MAX-ACCESS  read-create
    STATUS      current
    DESCRIPTION
        "vRtrRipGroupTimerUpdate determines how often updates are sent."
    DEFVAL { 30 }
    ::= { vRtrRipGroupEntry 14 }

vRtrRipGroupImportPolicy1 OBJECT-TYPE
    SYNTAX      TPolicyStatementNameOrEmpty
    MAX-ACCESS  read-create
    STATUS      current
    DESCRIPTION
        "vRtrRipGroupImportPolicy1 is import policy number 1 for the
         group level."
    DEFVAL { ''H }   -- the empty string
    ::= { vRtrRipGroupEntry 15 }

vRtrRipGroupImportPolicy2 OBJECT-TYPE
    SYNTAX      TPolicyStatementNameOrEmpty
    MAX-ACCESS  read-create
    STATUS      current
    DESCRIPTION
        "vRtrRipGroupImportPolicy2 is import policy number 2 for the
         group level."
    DEFVAL { ''H }   -- the empty string
    ::= { vRtrRipGroupEntry 16 }

vRtrRipGroupImportPolicy3 OBJECT-TYPE
    SYNTAX      TPolicyStatementNameOrEmpty
    MAX-ACCESS  read-create
    STATUS      current
    DESCRIPTION
        "vRtrRipGroupImportPolicy3 is import policy number 3 for the
         group level."
    DEFVAL { ''H }   -- the empty string
    ::= { vRtrRipGroupEntry 17 }

vRtrRipGroupImportPolicy4 OBJECT-TYPE
    SYNTAX      TPolicyStatementNameOrEmpty
    MAX-ACCESS  read-create
    STATUS      current
    DESCRIPTION
        "vRtrRipGroupImportPolicy4 is import policy number 4 for the
         group level."
    DEFVAL { ''H }   -- the empty string
    ::= { vRtrRipGroupEntry 18 }

vRtrRipGroupImportPolicy5 OBJECT-TYPE
    SYNTAX      TPolicyStatementNameOrEmpty
    MAX-ACCESS  read-create
    STATUS      current
    DESCRIPTION
        "vRtrRipGroupImportPolicy5 is import policy number 5 for the
         group level."
    DEFVAL { ''H }   -- the empty string
    ::= { vRtrRipGroupEntry 19 }

vRtrRipGroupExportPolicy1 OBJECT-TYPE
    SYNTAX      TPolicyStatementNameOrEmpty
    MAX-ACCESS  read-create
    STATUS      current
    DESCRIPTION
        "vRtrRipGroupExportPolicy1 is export policy number 1 for the
         group level."
    DEFVAL { ''H }   -- the empty string
    ::= { vRtrRipGroupEntry 20 }

vRtrRipGroupExportPolicy2 OBJECT-TYPE
    SYNTAX      TPolicyStatementNameOrEmpty
    MAX-ACCESS  read-create
    STATUS      current
    DESCRIPTION
        "vRtrRipGroupExportPolicy2 is export policy number 2 for the
         group level."
    DEFVAL { ''H }   -- the empty string
    ::= { vRtrRipGroupEntry 21 }

vRtrRipGroupExportPolicy3 OBJECT-TYPE
    SYNTAX      TPolicyStatementNameOrEmpty
    MAX-ACCESS  read-create
    STATUS      current
    DESCRIPTION
        "vRtrRipGroupExportPolicy3 is export policy number 3 for the
         group level."
    DEFVAL { ''H }   -- the empty string
    ::= { vRtrRipGroupEntry 22 }

vRtrRipGroupExportPolicy4 OBJECT-TYPE
    SYNTAX      TPolicyStatementNameOrEmpty
    MAX-ACCESS  read-create
    STATUS      current
    DESCRIPTION
        "vRtrRipGroupExportPolicy4 is export policy number 4 for the
         group level."
    DEFVAL { ''H }   -- the empty string
    ::= { vRtrRipGroupEntry 23 }

vRtrRipGroupExportPolicy5 OBJECT-TYPE
    SYNTAX      TPolicyStatementNameOrEmpty
    MAX-ACCESS  read-create
    STATUS      current
    DESCRIPTION
        "vRtrRipGroupExportPolicy5 is export policy number 5 for the
         group level."
    DEFVAL { ''H }   -- the empty string
    ::= { vRtrRipGroupEntry 24 }

vRtrRipGroupDescription OBJECT-TYPE
    SYNTAX      TItemDescription
    MAX-ACCESS  read-create
    STATUS      current
    DESCRIPTION
        "vRtrRipGroupDescription specifies a textual description for
         the group."
    DEFVAL { ''H }   -- the empty string
    ::= { vRtrRipGroupEntry 25 }

vRtrRipGroupInheritance OBJECT-TYPE
    SYNTAX      Unsigned32
    MAX-ACCESS  read-create
    STATUS      current
    DESCRIPTION
        "vRtrRipGroupInheritance controls, for the objects listed below,
         whether to use the administratively set value for that object or
         objects, or to use the corresponding value or values from the
         vRtrRipInstanceTable entry that represents the RIP instance for
         this router. 
        
         This object is a bit-mask, and the bits correspond to
         the following objects:
        
         vRtrRipGroupAuthType            0x00000001
         vRtrRipGroupAuthKey             0x00000002
         vRtrRipGroupSend                0x00000004
         vRtrRipGroupReceive             0x00000008
         vRtrRipGroupCheckZero           0x00000010
         vRtrRipGroupMessageSize         0x00000020
         vRtrRipGroupMetricIn            0x00000040
         vRtrRipGroupMetricOut           0x00000080
         vRtrRipGroupPreference          0x00000100
         vRtrRipGroupSplitHorizon        0x00000200

         vRtrRipGroupTimerFlush          0x00000400
         vRtrRipGroupTimerTimeout
         vRtrRipGroupTimerUpdate
   
         vRtrRipGroupImportPolicy1       0x00000800
         vRtrRipGroupImportPolicy2
         vRtrRipGroupImportPolicy3
         vRtrRipGroupImportPolicy4
         vRtrRipGroupImportPolicy5
  
         vRtrRipGroupExportPolicy1       0x00001000
         vRtrRipGroupExportPolicy2
         vRtrRipGroupExportPolicy3
         vRtrRipGroupExportPolicy4
         vRtrRipGroupExportPolicy5
 
         When the bit for an object is set to one, then the object's
         value is whatever the DEFVAL or most recently SET value is.
         The corresponding mask bit will be changed to one when SNMP
         SET is performed on any of the inherited objects ( vRtrRipGroupSend, 
         vRtrRipGroupAuthType,  etc ).

         When the bit for an object is set to zero, then the object's
         value is inherited from the vRtrRipInstanceEntry that represents 
         the RIP instance for this router.
 
         Non mask bits will always have value of zero, and any attempt to
         change the value will be silently discarded.

         The bit, timer (10), applies this rule to all of the following
         objects:
             vRtrRipGroupTimerFlush
             vRtrRipGroupTimerTimeout
             vRtrRipGroupTimerUpdate

         The bit, importPolicy (11), applies this rule to all of the
         following objects:
             vRtrRipGroupImportPolicy1,
             vRtrRipGroupImportPolicy2,
             vRtrRipGroupImportPolicy3,
             vRtrRipGroupImportPolicy4,
             vRtrRipGroupImportPolicy5
 
         The bit, exportPolicy (12), applies this rule to all of the
         following objects:
             vRtrRipGroupExportPolicy1,
             vRtrRipGroupExportPolicy2,
             vRtrRipGroupExportPolicy3,
             vRtrRipGroupExportPolicy4,
             vRtrRipGroupExportPolicy5
        "
    DEFVAL { 0 }  -- by default inherit everything from the RIP instance
    ::= { vRtrRipGroupEntry 26 }

vRtrRipGroupAdminStatus OBJECT-TYPE
    SYNTAX      TmnxAdminState
    MAX-ACCESS  read-create
    STATUS      current
    DESCRIPTION
        "The value of vRtrRipGroupAdminStatus indicates the desired
         administrative state for this RIP group or instance.
         
         If a RIP group entry object is set to outOfService, then all
         interfaces in the group are shutdown operationally.
         
         If set to inService, all interfaces within the group are 
         re-enabled operationally unless they have been administratively 
         shutdown at the interface level."
    DEFVAL { inService }
    ::= { vRtrRipGroupEntry 27 }

vRtrRipGroupOperStatus OBJECT-TYPE
    SYNTAX      TmnxOperState
    MAX-ACCESS  read-only
    STATUS      current
    DESCRIPTION
        "The value of vRtrRipGroupOperStatus indicates the current
         operational status of this RIP group."
    ::= { vRtrRipGroupEntry 28 }

vRtrRipGroupRowStatus OBJECT-TYPE
    SYNTAX      RowStatus
    MAX-ACCESS  read-create
    STATUS      current
    DESCRIPTION
        "vRtrRipGroupRowStatus controls the creation and deletion of rows in 
         this table. 
         
         To create a row in the vRtrRipGroupTable, set vRtrRipGroupRowStatus
         to createAndGo(4). All objects will take on default values and the
         agent will change vRtrRipGroupRowStatus to active(1).
         
         To delete a row in the vRtrRipGroupTable, set vRtrRipGroupRowStatus
         to delete(6). However the row can only be deleted the group has been 
         shutdown (i.e. value of vRtrRipGroupAdminStatus is outOfService)."
    ::= { vRtrRipGroupEntry 29 }


--
-- RIP Interface Table
--

vRtrRipIfTable OBJECT-TYPE
    SYNTAX      SEQUENCE OF VRtrRipIfEntry
    MAX-ACCESS  not-accessible
    STATUS      current
    DESCRIPTION
       "vRtrRipIfTable contains configuration information for each
        interface running RIP."
    ::= { vRtrRipObjs 4 }

vRtrRipIfEntry OBJECT-TYPE
    SYNTAX      VRtrRipIfEntry
    MAX-ACCESS  not-accessible
    STATUS      current
    DESCRIPTION
       "vRtrRipIfEntry is an entry (conceptual row) in the vRtrRipIfTable.
        Each row entry represents an interface on the router that participates
        in the RIP protocol.

        Entries in this table can be created and deleted via SNMP SET 
        operations to vRtrRipIfRowStatus."
    INDEX { vRtrID, vRtrIfIndex }
    ::= { vRtrRipIfTable 1 }

VRtrRipIfEntry ::= SEQUENCE {
    vRtrRipIfGroupName                  TNamedItem,
    vRtrRipIfAuthType                   TmnxRipAuthType,
    vRtrRipIfAuthKey                    TmnxRipAuthKey,
    vRtrRipIfCheckZero                  TruthValue,
    vRtrRipIfMessageSize                TmnxRipMessageSize,
    vRtrRipIfMetricIn                   TmnxRipMetric,
    vRtrRipIfMetricOut                  TmnxRipMetric,
    vRtrRipIfPreference                 TmnxRipPreference,
    vRtrRipIfReceive                    TmnxRipReceive,
    vRtrRipIfSend                       TmnxRipSend,
    vRtrRipIfSplitHorizon               TruthValue,
    vRtrRipIfTimerFlush                 TmnxRipTimerFlush,
    vRtrRipIfTimerTimeout               TmnxRipTimerTimeout,
    vRtrRipIfTimerUpdate                TmnxRipTimerUpdate,
    vRtrRipIfImportPolicy1              TPolicyStatementNameOrEmpty,
    vRtrRipIfImportPolicy2              TPolicyStatementNameOrEmpty,
    vRtrRipIfImportPolicy3              TPolicyStatementNameOrEmpty,
    vRtrRipIfImportPolicy4              TPolicyStatementNameOrEmpty,
    vRtrRipIfImportPolicy5              TPolicyStatementNameOrEmpty,
    vRtrRipIfExportPolicy1              TPolicyStatementNameOrEmpty,
    vRtrRipIfExportPolicy2              TPolicyStatementNameOrEmpty,
    vRtrRipIfExportPolicy3              TPolicyStatementNameOrEmpty,
    vRtrRipIfExportPolicy4              TPolicyStatementNameOrEmpty,
    vRtrRipIfExportPolicy5              TPolicyStatementNameOrEmpty,
    vRtrRipIfDescription                TItemDescription,
    vRtrRipIfInheritance                Unsigned32,
    vRtrRipIfAdminStatus                TmnxAdminState,
    vRtrRipIfOperStatus                 TmnxOperState,
    vRtrRipIfRowStatus                  RowStatus
    }

vRtrRipIfGroupName  OBJECT-TYPE
    SYNTAX      TNamedItem
    MAX-ACCESS  read-create
    STATUS      current
    DESCRIPTION
        "vRtrRipIfGroupName is an index into the vRtrRipGroupTable.
         It identifies the RIP group to which this interface belongs.
         This object must be set to an existing group name before the 
         row status can be changed to 'active'."
    ::= { vRtrRipIfEntry 1 }

vRtrRipIfAuthType OBJECT-TYPE
    SYNTAX      TmnxRipAuthType
    MAX-ACCESS  read-create
    STATUS      current
    DESCRIPTION
       "vRtrRipIfAuthType defines the type of authentication to be
        used for this interface."
    DEFVAL { noAuthentication }
    ::= { vRtrRipIfEntry 2 }

vRtrRipIfAuthKey OBJECT-TYPE
    SYNTAX      TmnxRipAuthKey
    MAX-ACCESS  read-create
    STATUS      current
    DESCRIPTION
        "vRtrRipIfAuthKey is the authentication key that should be
         used for this interface when vRtrRipInstanceAuthType has a 
         value other than noAuthentication(1). Modifying the value of 
         vRtrRipIfAuthType does not modify the vRtrRipIfAuthKey value.
         If a string shorter than 16 octets is supplied, it will be
         left-justified and padded to 16 octets, on the right, with
         nulls (0x00).

         Reading this object always results in an  OCTET STRING of
         length zero; authentication may not be bypassed by reading
         the MIB object."
    DEFVAL { ''h }
    ::= { vRtrRipIfEntry 3 }

vRtrRipIfCheckZero OBJECT-TYPE
    SYNTAX      TruthValue
    MAX-ACCESS  read-create
    STATUS      current
    DESCRIPTION
        "vRtrRipIfCheckZero specifies whether RIP updates received on 
         this interface are checked for zero values in fields defined 
         as Must-Be-Zero by the RIPv1 and v2 specifications."
    DEFVAL { false }
    ::= { vRtrRipIfEntry 4 }

vRtrRipIfMessageSize OBJECT-TYPE
    SYNTAX      TmnxRipMessageSize
    MAX-ACCESS  read-create
    STATUS      current
    DESCRIPTION
        "vRtrRipIfMessageSize is the maximum number of routes that can 
         be sent out per RIP update message."
    DEFVAL { 25 }
    ::= { vRtrRipIfEntry 5 }

vRtrRipIfMetricIn OBJECT-TYPE
    SYNTAX      TmnxRipMetric
    MAX-ACCESS  read-create
    STATUS      current
    DESCRIPTION
        "vRtrRipIfMetricIn is the value added to the metric of routes
         received on this RIP interface."
    DEFVAL { 1 }
    ::= { vRtrRipIfEntry 6 }

vRtrRipIfMetricOut OBJECT-TYPE
    SYNTAX      TmnxRipMetric
    MAX-ACCESS  read-create
    STATUS      current
    DESCRIPTION
        "vRtrRipIfMetricOut is the value added to the metric of routes
         exported into RIP and advertised out on this RIP interface."
    DEFVAL { 1 }
    ::= { vRtrRipIfEntry 7 }

vRtrRipIfPreference OBJECT-TYPE
    SYNTAX      TmnxRipPreference
    MAX-ACCESS  read-create
    STATUS      current
    DESCRIPTION
       "vRtrRipIfPreference is the route preference to be assigned to
        routes received on this interface. This value may be overridden 
        via route policies."
    DEFVAL { 100 }
    ::= { vRtrRipIfEntry 8 }

vRtrRipIfReceive OBJECT-TYPE
    SYNTAX      TmnxRipReceive
    MAX-ACCESS  read-create
    STATUS      current
    DESCRIPTION
       "vRtrRipIfReceive indicates which version of RIP updates are
        to be accepted on the interface."
    DEFVAL { rip1OrRip2 }
    ::= { vRtrRipIfEntry 9 }

vRtrRipIfSend OBJECT-TYPE
    SYNTAX      TmnxRipSend
    MAX-ACCESS  read-create
    STATUS      current
    DESCRIPTION
        "vRtrRipIfSend indicates the version to be used for sending
         RIP updates on the interface."
    DEFVAL { rip1Compatible }
    ::= { vRtrRipIfEntry 10 }

vRtrRipIfSplitHorizon OBJECT-TYPE
    SYNTAX      TruthValue
    MAX-ACCESS  read-create
    STATUS      current
    DESCRIPTION
        "vRtrRipIfSplitHorizon indicates whether split horizon scheme is
         is to be used when sending updates on the interface."
    DEFVAL { true }
    ::= { vRtrRipIfEntry 11 }

vRtrRipIfTimerFlush OBJECT-TYPE
    SYNTAX      TmnxRipTimerFlush
    UNITS       "seconds"
    MAX-ACCESS  read-create
    STATUS      current
    DESCRIPTION
        "vRtrRipIfTimerFlush specifies the number of seconds after a
         route has been declared    invalid that it is flushed from the
         route database."
    DEFVAL { 120 }
    ::= { vRtrRipIfEntry 12 }

vRtrRipIfTimerTimeout OBJECT-TYPE
    SYNTAX      TmnxRipTimerTimeout
    UNITS       "seconds"
    MAX-ACCESS  read-create
    STATUS      current
    DESCRIPTION
        "vRtrRipIfTimerTimeout specifies the number of seconds after a
         route has been discovered or last updated that it is declared
         invalid in the route database."
    DEFVAL { 180 }
    ::= { vRtrRipIfEntry 13 }

vRtrRipIfTimerUpdate OBJECT-TYPE
    SYNTAX      TmnxRipTimerUpdate
    UNITS       "seconds"
    MAX-ACCESS  read-create
    STATUS      current
    DESCRIPTION
        "vRtrRipIfTimerUpdate specifies how often updates are sent."
    DEFVAL { 30 }
    ::= { vRtrRipIfEntry 14 }

vRtrRipIfImportPolicy1 OBJECT-TYPE
    SYNTAX      TPolicyStatementNameOrEmpty
    MAX-ACCESS  read-create
    STATUS      current
    DESCRIPTION
        "vRtrRipIfImportPolicy1 is import policy number 1 for the interface." 
    DEFVAL { ''H }   -- the empty string
    ::= { vRtrRipIfEntry 15 }

vRtrRipIfImportPolicy2 OBJECT-TYPE
    SYNTAX      TPolicyStatementNameOrEmpty
    MAX-ACCESS  read-create
    STATUS      current
    DESCRIPTION
        "vRtrRipIfImportPolicy2 is import policy number 2 for the interface."
    DEFVAL { ''H }   -- the empty string
    ::= { vRtrRipIfEntry 16 }

vRtrRipIfImportPolicy3 OBJECT-TYPE
    SYNTAX      TPolicyStatementNameOrEmpty
    MAX-ACCESS  read-create
    STATUS      current
    DESCRIPTION
        "vRtrRipIfImportPolicy3 is import policy number 3 for the interface."
    DEFVAL { ''H }   -- the empty string
    ::= { vRtrRipIfEntry 17 }

vRtrRipIfImportPolicy4 OBJECT-TYPE
    SYNTAX      TPolicyStatementNameOrEmpty
    MAX-ACCESS  read-create
    STATUS      current
    DESCRIPTION
        "vRtrRipIfImportPolicy4 is import policy number 4 for the interface."
    DEFVAL { ''H }   -- the empty string
    ::= { vRtrRipIfEntry 18 }

vRtrRipIfImportPolicy5 OBJECT-TYPE
    SYNTAX      TPolicyStatementNameOrEmpty
    MAX-ACCESS  read-create
    STATUS      current
    DESCRIPTION
        "vRtrRipIfImportPolicy5 is import policy number 5 for the interface."
    DEFVAL { ''H }   -- the empty string
    ::= { vRtrRipIfEntry 19 }

vRtrRipIfExportPolicy1 OBJECT-TYPE
    SYNTAX      TPolicyStatementNameOrEmpty
    MAX-ACCESS  read-create
    STATUS      current
    DESCRIPTION
        "vRtrRipIfExportPolicy1 is export policy number 1 for the interface."
    DEFVAL { ''H }   -- the empty string
    ::= { vRtrRipIfEntry 20 }

vRtrRipIfExportPolicy2 OBJECT-TYPE
    SYNTAX      TPolicyStatementNameOrEmpty
    MAX-ACCESS  read-create
    STATUS      current
    DESCRIPTION
        "vRtrRipIfExportPolicy2 is export policy number 2 for the interface."
    DEFVAL { ''H }   -- the empty string
    ::= { vRtrRipIfEntry 21 }

vRtrRipIfExportPolicy3 OBJECT-TYPE
    SYNTAX      TPolicyStatementNameOrEmpty
    MAX-ACCESS  read-create
    STATUS      current
    DESCRIPTION
        "vRtrRipIfExportPolicy3 is export policy number 3 for the interface."
    DEFVAL { ''H }   -- the empty string
    ::= { vRtrRipIfEntry 22 }

vRtrRipIfExportPolicy4 OBJECT-TYPE
    SYNTAX      TPolicyStatementNameOrEmpty
    MAX-ACCESS  read-create
    STATUS      current
    DESCRIPTION
        "vRtrRipIfExportPolicy4 is export policy number 4 for the interface."
    DEFVAL { ''H }   -- the empty string
    ::= { vRtrRipIfEntry 23 }

vRtrRipIfExportPolicy5 OBJECT-TYPE
    SYNTAX      TPolicyStatementNameOrEmpty
    MAX-ACCESS  read-create
    STATUS      current
    DESCRIPTION
        "vRtrRipIfExportPolicy5 is export policy number 5 for the interface."
    DEFVAL { ''H }   -- the empty string
    ::= { vRtrRipIfEntry 24 }

vRtrRipIfDescription OBJECT-TYPE
    SYNTAX      TItemDescription
    MAX-ACCESS  read-create
    STATUS      current
    DESCRIPTION
        "vRtrRipIfDescription specifies a textual description for
         the interface."
    DEFVAL { ''H }   -- the empty string
    ::= { vRtrRipIfEntry 25 }

vRtrRipIfInheritance OBJECT-TYPE
    SYNTAX      Unsigned32
    MAX-ACCESS  read-create
    STATUS      current
    DESCRIPTION
        "vRtrRipIfInheritance controls, for the objects listed below,
         whether to use the administratively set value for that object
         or objects or to use the corresponding value or values from the
         vRtrRipGroupTable entry that represents the RIP group to which 
         this interface belongs.
         
         This object is a bit-mask, and the bits correspond to
         the following objects:
        
         vRtrRipIfAuthType      0x00000001
         vRtrRipIfAuthKey       0x00000002
         vRtrRipIfSend          0x00000004
         vRtrRipIfReceive       0x00000008
         vRtrRipIfCheckZero      0x00000010
         vRtrRipIfMessageSize    0x00000020
         vRtrRipIfMetricIn       0x00000040
         vRtrRipIfMetricOut      0x00000080
         vRtrRipIfPreference     0x00000100
         vRtrRipIfSplitHorizon   0x00000200
 
         vRtrRipIfTimerFlush     0x00000400
         vRtrRipIfTimerTimeout
         vRtrRipIfTimerUpdate
   
         vRtrRipIfImportPolicy1  0x00000800
         vRtrRipIfImportPolicy2
         vRtrRipIfImportPolicy3
         vRtrRipIfImportPolicy4
         vRtrRipIfImportPolicy5
   
         vRtrRipIfExportPolicy1  0x00001000
         vRtrRipIfExportPolicy2
         vRtrRipIfExportPolicy3
         vRtrRipIfExportPolicy4
         vRtrRipIfExportPolicy5
 
         When the bit for an object is set to one, then the object's
         value is whatever the DEFVAL or most recently SET value is.
         The corresponding mask bit will be changed to one when SNMP
         SET is performed on any of the inherited objects ( vRtrRipIfSend, 
         vRtrRipIfAuthType,  etc ).

         When the bit for an object is set to zero, then the object's
         value is inherited from the corresponding object in
         vRtrRipGroupTable whose index is the value of
         vRtrRipIfGroupName.
 
         Non mask bits will always have value of zero, and any attempt to
         change the value will be silently discarded.

         The bit, 'timer(10)', applies this rule to all of the following
         objects:
             vRtrRipIfTimerFlush
             vRtrRipIfTimerTimeout
             vRtrRipIfTimerUpdate
 
         The bit, 'importPolicy(11)', applies this rule to all of the
         following objects:
             vRtrRipIfImportPolicy1,
             vRtrRipIfImportPolicy2,
             vRtrRipIfImportPolicy3,
             vRtrRipIfImportPolicy4,
             vRtrRipIfImportPolicy5
 
         The bit, 'exportPolicy(12)', applies this rule to all of the
         following objects:
             vRtrRipIfExportPolicy1,
             vRtrRipIfExportPolicy2,
             vRtrRipIfExportPolicy3,
             vRtrRipIfExportPolicy4,
             vRtrRipIfExportPolicy5
         "
    DEFVAL { 0 } -- by default inherit everything from
                  -- the vRtrRipGroupTable entry whose index is
                  -- vRtrRipIfGroupName.
    ::= { vRtrRipIfEntry 26 }

vRtrRipIfAdminStatus OBJECT-TYPE
    SYNTAX      TmnxAdminState
    MAX-ACCESS  read-create
    STATUS      current
    DESCRIPTION
        "The value of vRtrRipIfAdminStatus indicates the desired
         administrative state for this RIP interface."
    DEFVAL { inService }
    ::= { vRtrRipIfEntry 27 }

vRtrRipIfOperStatus OBJECT-TYPE
    SYNTAX      TmnxOperState
    MAX-ACCESS  read-only
    STATUS      current
    DESCRIPTION
        "The value of vRtrRipIfOperStatus indicates the current
         operational status of this RIP interface."
    DEFVAL { inService }
    ::= { vRtrRipIfEntry 28 }

vRtrRipIfRowStatus OBJECT-TYPE
    SYNTAX      RowStatus
    MAX-ACCESS  read-create
    STATUS      current
    DESCRIPTION
        "vRtrRipIfRowStatus controls the creation and deletion of rows in 
         this table. 
         
         To create a row in the vRtrRipIfTable, set vRtrRipIfRowStatus
         to createAndGo(4). vRtrRipIfGroupName for the interface must be 
         set to the name of an existant group in the vRtrRipGroupTable 
         before the row status can be set to active(1).
         
         To delete a row in the vRtrRipIfTable, set vRtrRipIfRowStatus
         to delete(6). However the row can only be deleted the group has been 
         shutdown (i.e. value of vRtrRipIfAdminStatus is outOfService)."
    ::= { vRtrRipIfEntry 29 }


--
-- RIP Route Database
--

vRtrRipRouteTable OBJECT-TYPE
    SYNTAX      SEQUENCE OF VRtrRipRouteEntry
    MAX-ACCESS  not-accessible
    STATUS      current
    DESCRIPTION
        "The vRtrRipRouteTable has an entry for each route in the RIP
         database." 
    ::= { vRtrRipObjs 5 }

vRtrRipRouteEntry OBJECT-TYPE
    SYNTAX      VRtrRipRouteEntry
    MAX-ACCESS  not-accessible
    STATUS      current
    DESCRIPTION
        "vRtrRipRouteEntry is an entry (conceptual row) in the
         vRtrRipRouteTable.  Each entry represents information for 
         a RIP route received from a peer."
    INDEX    { vRtrID, 
               vRtrRipRouteDest, 
               vRtrRipRouteMask, 
               vRtrRipRouteIfIndex,
               vRtrRipRoutePeerAddr }
    ::= { vRtrRipRouteTable 1 }

VRtrRipRouteEntry ::= SEQUENCE {
    vRtrRipRouteDest                  IpAddress,
    vRtrRipRouteMask                  IpAddress,
    vRtrRipRouteIfIndex               InterfaceIndex,
    vRtrRipRoutePeerAddr              IpAddress,
    vRtrRipRouteNextHop               IpAddress,
    vRtrRipRouteMetric                TmnxRipMetric,
    vRtrRipRouteTag                   RouteTag,
    vRtrRipRouteStatus                INTEGER,
    vRtrRipRouteTimerRemaining        Unsigned32,
    vRtrRipRouteFC                    TNamedItemOrEmpty,
    vRtrRipRouteFCPriority            TPriorityOrUndefined
    }

vRtrRipRouteDest OBJECT-TYPE
    SYNTAX      IpAddress
    MAX-ACCESS  not-accessible
    STATUS      current
    DESCRIPTION
        "vRtrRipRouteDest is the destination IP Address of the RIP route."
    ::= { vRtrRipRouteEntry 1 }

vRtrRipRouteMask OBJECT-TYPE
    SYNTAX      IpAddress
    MAX-ACCESS  not-accessible
    STATUS      current
    DESCRIPTION
        "vRtrRipRouteMask contains the subnet mask which is applied
         to the vRtrRipRouteDest to yield the non-host portion of the
         destination  address.  If this field is zero, then no subnet
         mask has  been included for this entry."
    ::= { vRtrRipRouteEntry 2 }

vRtrRipRouteIfIndex OBJECT-TYPE
    SYNTAX      InterfaceIndex
    MAX-ACCESS  not-accessible
    STATUS      current
    DESCRIPTION
        "vRtrRipRouteIfIndex specifies the index of the interface on
         which this route was received."
    ::= { vRtrRipRouteEntry 3 }

vRtrRipRoutePeerAddr OBJECT-TYPE
    SYNTAX      IpAddress
    MAX-ACCESS  not-accessible
    STATUS      current
    DESCRIPTION
        "vRtrRipRoutePeerAddr specifies the IP address of the peer from
         whom this route was received."
    ::= { vRtrRipRouteEntry 4 }

vRtrRipRouteNextHop OBJECT-TYPE
    SYNTAX      IpAddress
    MAX-ACCESS  read-only
    STATUS      current
    DESCRIPTION
        "vRtrRipRouteNextHop specifies the IP address in the Next
         Hop field of the RIPv2 update received for this route. 
         The Next Hop field is the immediate next hop IP address to
         which packets to the destination specified by this route
         entry should be forwarded. Specifying a value of 0.0.0.0
         in this field indicates that routing should be via the
         originator of the RIP advertisement. An address specified
         as a next hop must, per force, be directly reachable on 
         the logical subnet over which the advertisement is made."
    ::= { vRtrRipRouteEntry 5 }

vRtrRipRouteMetric OBJECT-TYPE
    SYNTAX      TmnxRipMetric
    MAX-ACCESS  read-only
    STATUS      current
    DESCRIPTION
        "vRtrRipRouteMetric gives the distance to the destination
         as advertised by the peer that sent this route."
    ::= { vRtrRipRouteEntry 6 }

vRtrRipRouteTag OBJECT-TYPE
    SYNTAX      RouteTag
    MAX-ACCESS  read-only
    STATUS      current
    DESCRIPTION
        "vRtrRipRouteTag gives the value in the Route Tag field of
         the update received for this route,"
    ::= { vRtrRipRouteEntry 7 }

vRtrRipRouteStatus    OBJECT-TYPE
    SYNTAX      INTEGER {
                    active (1),
                    inactive (2)
                }
    MAX-ACCESS  read-only
    STATUS      current
    DESCRIPTION
        "The value of vRtrRipRouteStatus indicates whether or not the 
         route entry is active in the system. vRtrRipRouteStatus will
         be active(1) if the route entry has been added to the Route
         Table Manager(RTM)."
    ::= { vRtrRipRouteEntry 8 }

vRtrRipRouteTimerRemaining OBJECT-TYPE
    SYNTAX      Unsigned32
    MAX-ACCESS  read-only
    STATUS      current
    DESCRIPTION
        "The value of vRtrRipRouteTimerRemaining is the number of seconds 
         till the timeout timer expires."
    ::= { vRtrRipRouteEntry 9 }

vRtrRipRouteFC  OBJECT-TYPE
    SYNTAX       TNamedItemOrEmpty
    MAX-ACCESS   read-only
    STATUS       current
    DESCRIPTION 
        "The value of vRtrRipRouteFC indicates the forwarding class
         associated with the rip route.
        
        This object takes one of the following eight values - 'be', 'l2', 
        'af', 'l1', 'h2', 'ef', 'h1', 'nc' - when the forwarding class is valid.
         If the forwarding class is not valid the object is a null string."
    ::= { vRtrRipRouteEntry 10 }

vRtrRipRouteFCPriority  OBJECT-TYPE
    SYNTAX       TPriorityOrUndefined
    MAX-ACCESS   read-only
    STATUS       current
    DESCRIPTION 
        "The value of vRtrRipRouteFCPriority indicates the priority that is 
         assigned to the rip routes."
    ::= { vRtrRipRouteEntry 11 }

-- 
--  RIP Interface Statistics Table
--

vRtrRipIfStatTable OBJECT-TYPE
    SYNTAX     SEQUENCE OF VRtrRipIfStatEntry
    MAX-ACCESS  not-accessible
    STATUS      current
    DESCRIPTION
        "vRtrRipIfStatTable is a read-only table which keeps statistical
         information about the interfaces monitoring RIP."
    ::= { vRtrRipObjs 6 }

vRtrRipIfStatEntry OBJECT-TYPE
    SYNTAX     VRtrRipIfStatEntry
    MAX-ACCESS  not-accessible
    STATUS      current
    DESCRIPTION
        "vRtrRipIfStatEntry is an entry (conceptual row) in the
         vRtrRipIfStatTable. Each entry represents statistical information 
         for a RIP interface."
    INDEX { vRtrID, vRtrIfIndex }
    ::= { vRtrRipIfStatTable 1 }

VRtrRipIfStatEntry ::= SEQUENCE {
    vRtrRipIfStatAllSentUpdates            Counter32,
    vRtrRipIfStatAllTriggeredUpdates       Counter32,
    vRtrRipIfStatAllRcvBadPackets          Counter32,
    vRtrRipIfStatV1RcvUpdates              Counter32,
    vRtrRipIfStatV1RcvRequests             Counter32,
    vRtrRipIfStatV1BadUpdates              Counter32,
    vRtrRipIfStatV1BadRequests             Counter32,
    vRtrRipIfStatV1BadRoutes               Counter32,
    vRtrRipIfStatV2RcvUpdates              Counter32,
    vRtrRipIfStatV2RcvRequests             Counter32,
    vRtrRipIfStatV2BadUpdates              Counter32,
    vRtrRipIfStatV2BadRequests             Counter32,
    vRtrRipIfStatV2BadRoutes               Counter32,
    vRtrRipIfStatAuthErrors                Counter32,

    vRtrRipIfStatAllSentUpdates5Min        Counter32,
    vRtrRipIfStatAllTriggeredUpdates5Min   Counter32,
    vRtrRipIfStatAllRcvBadPackets5Min      Counter32,
    vRtrRipIfStatV1RcvUpdates5Min          Counter32,
    vRtrRipIfStatV1RcvRequests5Min         Counter32,
    vRtrRipIfStatV1BadUpdates5Min          Counter32,
    vRtrRipIfStatV1BadRequests5Min         Counter32,
    vRtrRipIfStatV1BadRoutes5Min           Counter32,
    vRtrRipIfStatV2RcvUpdates5Min          Counter32,
    vRtrRipIfStatV2RcvRequests5Min         Counter32,
    vRtrRipIfStatV2BadUpdates5Min          Counter32,
    vRtrRipIfStatV2BadRequests5Min         Counter32,
    vRtrRipIfStatV2BadRoutes5Min           Counter32,
    vRtrRipIfStatAuthErrors5Min            Counter32,

    vRtrRipIfStatAllSentUpdates1Min        Counter32,
    vRtrRipIfStatAllTriggeredUpdates1Min   Counter32,
    vRtrRipIfStatAllRcvBadPackets1Min      Counter32,
    vRtrRipIfStatV1RcvUpdates1Min          Counter32,
    vRtrRipIfStatV1RcvRequests1Min         Counter32,
    vRtrRipIfStatV1BadUpdates1Min          Counter32,
    vRtrRipIfStatV1BadRequests1Min         Counter32,
    vRtrRipIfStatV1BadRoutes1Min           Counter32,
    vRtrRipIfStatV2RcvUpdates1Min          Counter32,
    vRtrRipIfStatV2RcvRequests1Min         Counter32,
    vRtrRipIfStatV2BadUpdates1Min          Counter32,
    vRtrRipIfStatV2BadRequests1Min         Counter32,
    vRtrRipIfStatV2BadRoutes1Min           Counter32,
    vRtrRipIfStatAuthErrors1Min            Counter32
    }

vRtrRipIfStatAllSentUpdates OBJECT-TYPE
    SYNTAX      Counter32
    MAX-ACCESS  read-only
    STATUS      current
    DESCRIPTION
        "vRtrRipIfStatAllSentUpdates is the number of all RIP
         updates actually sent on this interface. This explicitly
         does include full updates sent containing new information."
    ::= { vRtrRipIfStatEntry 1 }

vRtrRipIfStatAllTriggeredUpdates OBJECT-TYPE
    SYNTAX      Counter32
    MAX-ACCESS  read-only
    STATUS      current
    DESCRIPTION
        "vRtrRipIfStatAllTriggeredUpdates is the number of triggered
         RIP updates actually sent on this interface.  This explicitly
         does include full updates sent containing new information."
    ::= { vRtrRipIfStatEntry 2 }

vRtrRipIfStatAllRcvBadPackets OBJECT-TYPE
    SYNTAX      Counter32
    MAX-ACCESS  read-only
    STATUS      current
    DESCRIPTION
        "vRtrRipIfStatAllRcvBadPackets is the number of RIP updates
         received on this interface that were discarded as 
         invalid."
    ::= { vRtrRipIfStatEntry 3 }

vRtrRipIfStatV1RcvUpdates OBJECT-TYPE
    SYNTAX      Counter32
    MAX-ACCESS  read-only
    STATUS   current
    DESCRIPTION
        "vRtrRipIfStatV1RcvUpdates is the number of RIPv1 response
         packets received by the RIP process."
    ::= { vRtrRipIfStatEntry 4 }

vRtrRipIfStatV1RcvRequests OBJECT-TYPE
    SYNTAX      Counter32
    MAX-ACCESS  read-only
    STATUS   current
    DESCRIPTION
        "vRtrRipIfStatV1RcvRequests is the number of RIPv1 request
         packets received by the RIP process."
    ::= { vRtrRipIfStatEntry 5 }

vRtrRipIfStatV1BadUpdates OBJECT-TYPE
    SYNTAX      Counter32
    MAX-ACCESS  read-only
    STATUS      current
    DESCRIPTION
        "vRtrRipIfStatV1BadUpdates is the number of RIPv1 response
         packets received by the RIP process which were subsequently
         discarded for any reason."
    ::= { vRtrRipIfStatEntry 6 }

vRtrRipIfStatV1BadRequests OBJECT-TYPE
    SYNTAX      Counter32
    MAX-ACCESS  read-only
    STATUS      current
    DESCRIPTION
        "vRtrRipIfStatV1BadRequests is the number of RIPv1 request
         packets received by the RIP process that were subsequently
         discarded for any reason."
    ::= { vRtrRipIfStatEntry 7 }

vRtrRipIfStatV1BadRoutes OBJECT-TYPE
    SYNTAX      Counter32
    MAX-ACCESS  read-only
    STATUS      current
    DESCRIPTION
        "vRtrRipIfStatV1BadRoutes is the number of routes, in valid
         RIPv1 packets, which were ignored for any reason (e.g.
         unknown address family, or invalid metric)."
    ::= { vRtrRipIfStatEntry 8 }

vRtrRipIfStatV2RcvUpdates OBJECT-TYPE
    SYNTAX      Counter32
    MAX-ACCESS  read-only
    STATUS      current
    DESCRIPTION
        "vRtrRipIfStatV2RcvUpdates is the number of RIPv2 response
         packets received by the RIP process."
    ::= { vRtrRipIfStatEntry 9 }

vRtrRipIfStatV2RcvRequests OBJECT-TYPE
    SYNTAX      Counter32
    MAX-ACCESS  read-only
    STATUS      current
    DESCRIPTION
        "vRtrRipIfStatV2RcvRequests is the number of RIPv2 request
         packets received by the RIP process."
    ::= { vRtrRipIfStatEntry 10 }

vRtrRipIfStatV2BadUpdates OBJECT-TYPE
    SYNTAX      Counter32
    MAX-ACCESS  read-only
    STATUS      current
    DESCRIPTION
        "vRtrRipIfStatV2BadUpdates is the number of RIPv2 response
         packets received by the RIP process which were subsequently
         discarded for any reason."
    ::= { vRtrRipIfStatEntry 11 }

vRtrRipIfStatV2BadRequests OBJECT-TYPE
    SYNTAX      Counter32
    MAX-ACCESS  read-only
    STATUS      current
    DESCRIPTION
        "vRtrRipIfStatV2BadRequests is the number of RIPv2 request
         packets received by the RIP process that were subsequently
         discarded for any reason."
    ::= { vRtrRipIfStatEntry 12 }

vRtrRipIfStatV2BadRoutes OBJECT-TYPE
    SYNTAX      Counter32
    MAX-ACCESS  read-only
    STATUS      current
    DESCRIPTION
        "vRtrRipIfStatV2BadRoutes is the number of routes, in valid
         RIPv2 packets, which were ignored for any reason (e.g.
         unknown address family, or invalid metric)."
    ::= { vRtrRipIfStatEntry 13 }

vRtrRipIfStatAuthErrors OBJECT-TYPE
    SYNTAX      Counter32
    MAX-ACCESS  read-only
    STATUS      current
    DESCRIPTION
        "vRtrRipIfStatAuthErrors is the  number of RIPv2 packets
         received by the RIP process which were subsequently
         discarded because of an error authenticating the packet."
    ::= { vRtrRipIfStatEntry 14 }

vRtrRipIfStatAllSentUpdates5Min OBJECT-TYPE
    SYNTAX      Counter32
    MAX-ACCESS  read-only
    STATUS      current
    DESCRIPTION
        "vRtrRipIfStatAllSentUpdates5Min is the number of all RIP
         updates actually sent on this interface in the last 5 minutes.  
         This explicitly does include full updates sent containing 
         new information."
    ::= { vRtrRipIfStatEntry 15 }

vRtrRipIfStatAllTriggeredUpdates5Min OBJECT-TYPE
    SYNTAX      Counter32
    MAX-ACCESS  read-only
    STATUS      current
    DESCRIPTION
        "vRtrRipIfStatAllTriggeredUpdates5Min is the number of triggered
         updates actually sent on this interface in the last 5 minutes.  
         This explicitly does NOT include full updates sent containing 
         new information."
    ::= { vRtrRipIfStatEntry 16 }

vRtrRipIfStatAllRcvBadPackets5Min OBJECT-TYPE
    SYNTAX      Counter32
    MAX-ACCESS  read-only
    STATUS      current
    DESCRIPTION
        "vRtrRipIfStatAllRcvBadPackets5Min is the number of RIP response
         packets discarded (for any reason e.g. a version 0 packet, or an
         unknown command type) in the last 5 minutes by the RIP process."
    ::= { vRtrRipIfStatEntry 17 }

vRtrRipIfStatV1RcvUpdates5Min OBJECT-TYPE
    SYNTAX      Counter32
    MAX-ACCESS  read-only
    STATUS      current
    DESCRIPTION
        "vRtrRipIfStatV1RcvUpdates5Min is the number of RIPv1 response
         packets received by the RIP process in the last 5 minutes."
    ::= { vRtrRipIfStatEntry 18 }

vRtrRipIfStatV1RcvRequests5Min OBJECT-TYPE
    SYNTAX      Counter32
    MAX-ACCESS  read-only
    STATUS      current
    DESCRIPTION
        "vRtrRipIfStatV1RcvRequests5Min is the number of RIPv1 request
         packets received by the RIP process in the last 5 minutes."
    ::= { vRtrRipIfStatEntry 19 }

vRtrRipIfStatV1BadUpdates5Min OBJECT-TYPE
    SYNTAX      Counter32
    MAX-ACCESS  read-only
    STATUS      current
    DESCRIPTION
        "vRtrRipIfStatV1BadUpdates5Min is the number of RIPv1 response
         packets received by the RIP process in the last 5 minutes which
         were subsequently discarded for any reason."
    ::= { vRtrRipIfStatEntry 20 }

vRtrRipIfStatV1BadRequests5Min OBJECT-TYPE
    SYNTAX      Counter32
    MAX-ACCESS  read-only
    STATUS      current
    DESCRIPTION
        "vRtrRipIfStatV1BadRequests5Min is the number of RIPv1 request
         packets received by the RIP process in the last 5 minutes that 
         were subsequently discarded for any reason."
    ::= { vRtrRipIfStatEntry 21 }

vRtrRipIfStatV1BadRoutes5Min OBJECT-TYPE
    SYNTAX      Counter32
    MAX-ACCESS  read-only
    STATUS      current
    DESCRIPTION
        "vRtrRipIfStatV1BadRoutes5Min is the number of routes, in valid
         RIPv1 packets, which were ignored for any reason (e.g.
         unknown address family, or invalid metric) in the last 5 minutes."
    ::= { vRtrRipIfStatEntry 22 }

vRtrRipIfStatV2RcvUpdates5Min OBJECT-TYPE
    SYNTAX      Counter32
    MAX-ACCESS  read-only
    STATUS      current
    DESCRIPTION
        "vRtrRipIfStatV2RcvUpdates5Min is the number of RIPv2 response
         packets received by the RIP process in the last 5 minutes."
    ::= { vRtrRipIfStatEntry 23 }

vRtrRipIfStatV2RcvRequests5Min OBJECT-TYPE
    SYNTAX      Counter32
    MAX-ACCESS  read-only
    STATUS      current
    DESCRIPTION
        "vRtrRipIfStatV2RcvRequests5Min is the number of RIPv2 request
         packets received by the RIP process in the last 5 minutes."
    ::= { vRtrRipIfStatEntry 24 }

vRtrRipIfStatV2BadUpdates5Min OBJECT-TYPE
    SYNTAX      Counter32
    MAX-ACCESS  read-only
    STATUS      current
    DESCRIPTION
        "vRtrRipIfStatV2BadUpdates5Min is the number of RIPv2 response
         packets received by the RIP process which were subsequently
         discarded for any reason in the last 5 minutes."
    ::= { vRtrRipIfStatEntry 25 }

vRtrRipIfStatV2BadRequests5Min OBJECT-TYPE
    SYNTAX      Counter32
    MAX-ACCESS  read-only
    STATUS      current
    DESCRIPTION
        "vRtrRipIfStatV2BadRequests5Min is the number of RIPv2 request
         packets received by the RIP process that were subsequently
         discarded for any reason in the last 5 minutes."
    ::= { vRtrRipIfStatEntry 26 }

vRtrRipIfStatV2BadRoutes5Min OBJECT-TYPE
    SYNTAX      Counter32
    MAX-ACCESS  read-only
    STATUS      current
    DESCRIPTION
        "vRtrRipIfStatV2BadRoutes5Min is the number of routes, in 
         valid RIPv2 packets, which were ignored for any reason (e.g.
         unknown address family, or invalid metric) in the last 5 
         minutes."
    ::= { vRtrRipIfStatEntry 27 }

vRtrRipIfStatAuthErrors5Min OBJECT-TYPE
    SYNTAX      Counter32
    MAX-ACCESS  read-only
    STATUS      current
    DESCRIPTION
        "vRtrRipIfStatAuthErrors5Min is the  number of RIPv2 packets
         received by the RIP process which were subsequently
         discarded because of an error authenticating the packet in 
         the last 5 minutes."
    ::= { vRtrRipIfStatEntry 28 }

vRtrRipIfStatAllSentUpdates1Min OBJECT-TYPE
    SYNTAX      Counter32
    MAX-ACCESS  read-only
    STATUS      current
    DESCRIPTION
        "vRtrRipIfStatAllSentUpdates1Min is the number of all RIP
         updates actually sent on this interface in the last 1 minute.  
         This explicitly does include full updates sent containing 
         new information."
    ::= { vRtrRipIfStatEntry 29 }

vRtrRipIfStatAllTriggeredUpdates1Min OBJECT-TYPE
    SYNTAX      Counter32
    MAX-ACCESS  read-only
    STATUS      current
    DESCRIPTION
        "vRtrRipIfStatAllTriggeredUpdates1Min is the number of triggered
         updates actually sent on this interface in the last 1 minute.  
         This explicitly does NOT include full updates sent containing 
         new information."
    ::= { vRtrRipIfStatEntry 30 }

vRtrRipIfStatAllRcvBadPackets1Min OBJECT-TYPE
    SYNTAX      Counter32
    MAX-ACCESS  read-only
    STATUS      current
    DESCRIPTION
        "vRtrRipIfStatAllRcvBadPackets1Min is the number of RIP response
         packets discarded (for any reason e.g. a version 0 packet, or an
         unknown command type) in the last 1 minute by the RIP process."
    ::= { vRtrRipIfStatEntry 31 }

vRtrRipIfStatV1RcvUpdates1Min OBJECT-TYPE
    SYNTAX      Counter32
    MAX-ACCESS  read-only
    STATUS      current
    DESCRIPTION
        "vRtrRipIfStatV1RcvUpdates1Min is the number of RIPv1 response
         packets received by the RIP process in the last 1 minute."
    ::= { vRtrRipIfStatEntry 32 }

vRtrRipIfStatV1RcvRequests1Min OBJECT-TYPE
    SYNTAX      Counter32
    MAX-ACCESS  read-only
    STATUS      current
    DESCRIPTION
        "vRtrRipIfStatV1RcvRequests1Min is the number of RIPv1 request
         packets received by the RIP process in the last 1 minute."
    ::= { vRtrRipIfStatEntry 33 }

vRtrRipIfStatV1BadUpdates1Min OBJECT-TYPE
    SYNTAX      Counter32
    MAX-ACCESS  read-only
    STATUS      current
    DESCRIPTION
        "vRtrRipIfStatV1BadUpdates1Min is the number of RIPv1 response
         packets received by the RIP process in the last 1 minute which
         were subsequently discarded for any reason."
    ::= { vRtrRipIfStatEntry 34 }

vRtrRipIfStatV1BadRequests1Min OBJECT-TYPE
    SYNTAX      Counter32
    MAX-ACCESS  read-only
    STATUS      current
    DESCRIPTION
        "vRtrRipIfStatV1BadRequests1Min is the number of RIPv1 request
         packets received by the RIP process in the last 1 minute that 
         were subsequently discarded for any reason."
    ::= { vRtrRipIfStatEntry 35 }

vRtrRipIfStatV1BadRoutes1Min OBJECT-TYPE
    SYNTAX      Counter32
    MAX-ACCESS  read-only
    STATUS      current
    DESCRIPTION
        "vRtrRipIfStatV1BadRoutes1Min is the number of routes, in valid
         RIPv1 packets, which were ignored for any reason (e.g.
         unknown address family, or invalid metric) in the last 1 minute."
    ::= { vRtrRipIfStatEntry 36 }

vRtrRipIfStatV2RcvUpdates1Min OBJECT-TYPE
    SYNTAX      Counter32
    MAX-ACCESS  read-only
    STATUS      current
    DESCRIPTION
        "vRtrRipIfStatV2RcvUpdates1Min is the number of RIPv2 response
         packets received by the RIP process in the last 1 minute."
    ::= { vRtrRipIfStatEntry 37 }

vRtrRipIfStatV2RcvRequests1Min OBJECT-TYPE
    SYNTAX      Counter32
    MAX-ACCESS  read-only
    STATUS      current
    DESCRIPTION
        "vRtrRipIfStatV2RcvRequests1Min is the number of RIPv2 request
         packets received by the RIP process in the last 1 minute."
    ::= { vRtrRipIfStatEntry 38 }

vRtrRipIfStatV2BadUpdates1Min OBJECT-TYPE
    SYNTAX      Counter32
    MAX-ACCESS  read-only
    STATUS      current
    DESCRIPTION
        "vRtrRipIfStatV2BadUpdates1Min is the number of RIPv2 response
         packets received by the RIP process which were subsequently
         discarded for any reason in the last 1 minute."
    ::= { vRtrRipIfStatEntry 39 }

vRtrRipIfStatV2BadRequests1Min OBJECT-TYPE
    SYNTAX      Counter32
    MAX-ACCESS  read-only
    STATUS      current
    DESCRIPTION
        "vRtrRipIfStatV2BadRequests1Min is the number of RIPv2 request
         packets received by the RIP process that were subsequently
         discarded for any reason in the last 1 minute."
    ::= { vRtrRipIfStatEntry 40 }

vRtrRipIfStatV2BadRoutes1Min OBJECT-TYPE
    SYNTAX      Counter32
    MAX-ACCESS  read-only
    STATUS      current
    DESCRIPTION
        "vRtrRipIfStatV2BadRoutes1Min is the number of routes, in 
         valid RIPv2 packets, which were ignored for any reason (e.g.
         unknown address family, or invalid metric) in the last 1 
         minute."
    ::= { vRtrRipIfStatEntry 41 }

vRtrRipIfStatAuthErrors1Min OBJECT-TYPE
    SYNTAX      Counter32
    MAX-ACCESS  read-only
    STATUS      current
    DESCRIPTION
        "vRtrRipIfStatAuthErrors1Min is the  number of RIPv2 packets
         received by the RIP process which were subsequently
         discarded because of an error authenticating the packet in 
         the last 1 minute."
    ::= { vRtrRipIfStatEntry 42 }


-- 
--  RIP Peer Table
--

vRtrRipPeerTable OBJECT-TYPE
    SYNTAX      SEQUENCE OF VRtrRipPeerEntry
    MAX-ACCESS  not-accessible
    STATUS      current
    DESCRIPTION
       "vRtrRipPeerTable is a read-only table which keeps information 
        about RIP peers."
    ::= { vRtrRipObjs 7 }

vRtrRipPeerEntry OBJECT-TYPE
    SYNTAX      VRtrRipPeerEntry
    MAX-ACCESS  not-accessible
    STATUS      current
    DESCRIPTION
       "vRtrRipPeerEntry is an entry (conceptual row) in the
        vRtrRipPeerTable. Each entry represents information for a 
        RIP peer."
    INDEX    { vRtrID,
               vRtrRipPeerIfIndex,
               vRtrRipPeerAddress }
    ::= { vRtrRipPeerTable 1 }

VRtrRipPeerEntry ::= SEQUENCE {
    vRtrRipPeerIfIndex                  InterfaceIndex,
    vRtrRipPeerAddress                  IpAddress,
    vRtrRipPeerLastUpdate               TimeStamp,
    vRtrRipPeerVersion                  Unsigned32,
    vRtrRipPeerRcvBadPackets            Counter32,
    vRtrRipPeerRcvBadRoutes             Counter32
    }

vRtrRipPeerIfIndex OBJECT-TYPE
    SYNTAX      InterfaceIndex
    MAX-ACCESS  not-accessible
    STATUS      current
    DESCRIPTION
        "vRtrRipPeerIfIndex specifies the index of the interface on which
         this peer was discovered."
    ::= { vRtrRipPeerEntry 1 }

vRtrRipPeerAddress OBJECT-TYPE
    SYNTAX      IpAddress
    MAX-ACCESS  not-accessible
    STATUS      current
    DESCRIPTION
        "vRtrRipPeerAddress specifies the IP Address that the peer is 
         using as its source address."
    ::= { vRtrRipPeerEntry 2 }

vRtrRipPeerLastUpdate OBJECT-TYPE
    SYNTAX      TimeStamp
    MAX-ACCESS  read-only
    STATUS      current
    DESCRIPTION
        "vRtrRipPeerLastUpdate specifies the value of sysUpTime when 
         the most recent RIP update was received from this peer."
    ::= { vRtrRipPeerEntry 3 }

vRtrRipPeerVersion OBJECT-TYPE
    SYNTAX      Unsigned32 (0..255)
    MAX-ACCESS  read-only
    STATUS      current
    DESCRIPTION
        "vRtrRipPeerVersion specifies the RIP version in the header 
         of the last packet received from this peer."
    ::= { vRtrRipPeerEntry 4 }

vRtrRipPeerRcvBadPackets OBJECT-TYPE
    SYNTAX      Counter32
    MAX-ACCESS  read-only
    STATUS      current
    DESCRIPTION
        "vRtrRipPeerRcvBadPackets is the number of RIP updates
         received from this peer that were discarded as invalid."
    ::= { vRtrRipPeerEntry 5 }

vRtrRipPeerRcvBadRoutes OBJECT-TYPE
    SYNTAX      Counter32
    MAX-ACCESS  read-only
    STATUS      current
    DESCRIPTION
        "vRtrRipPeerRcvBadRoutes is the number of routes received
         from this peer that were discarded as invalid."
    ::= { vRtrRipPeerEntry 6 }

--
-- Advertised Routes Table  
--
vRtrRipAdvertisedRouteTable OBJECT-TYPE
    SYNTAX      SEQUENCE OF VRtrRipAdvertisedRouteEntry
    MAX-ACCESS  not-accessible
    STATUS      current
    DESCRIPTION
       "vRtrRipAdvertisedRouteTable is a read-only table which gives the 
        routes that are advertised by RIP to its neighbors."
    ::= { vRtrRipObjs 8 }

vRtrRipAdvertisedRouteEntry OBJECT-TYPE
    SYNTAX      VRtrRipAdvertisedRouteEntry
    MAX-ACCESS  not-accessible
    STATUS      current
    DESCRIPTION
       "vRtrRipAdvertisedRouteEntry is an entry (conceptual row) in the
        vRtrRipAdvertisedRouteTable. Each entry represents information about
        a route that is advertised by RIP on a particular interface."

    INDEX  { vRtrID,
             vRtrRipAdvertisedRouteDest, 
             vRtrRipAdvertisedRouteMask, 
             vRtrRipAdvertisedRouteIfIndex,
             vRtrRipAdvertisedRouteIfAddr }
    ::= { vRtrRipAdvertisedRouteTable 1 }

VRtrRipAdvertisedRouteEntry ::= SEQUENCE {
    vRtrRipAdvertisedRouteDest              IpAddress,
    vRtrRipAdvertisedRouteMask              IpAddress,
    vRtrRipAdvertisedRouteIfIndex           InterfaceIndex,
    vRtrRipAdvertisedRouteIfAddr            IpAddress,
    vRtrRipAdvertisedRouteNextHop           IpAddress,
    vRtrRipAdvertisedRouteMetric            Unsigned32,
    vRtrRipAdvertisedRouteTag               RouteTag,
    vRtrRipAdvertisedRouteTimerRemaining    Integer32
    }

vRtrRipAdvertisedRouteDest  OBJECT-TYPE
    SYNTAX      IpAddress
    MAX-ACCESS  not-accessible
    STATUS      current
    DESCRIPTION
        "vRtrRipAdvertisedRouteDest is the destination IP address 
         of the advertised route."
    ::= { vRtrRipAdvertisedRouteEntry 1 }

vRtrRipAdvertisedRouteMask  OBJECT-TYPE
    SYNTAX      IpAddress
    MAX-ACCESS  not-accessible
    STATUS      current
    DESCRIPTION
        "vRtrRipAdvertisedRouteMask contains the subnet mask which is 
         applied to the to the vRtrRipAdvertisedRouteDest to yield the
         non-host portion of the destination address.  If this field 
         is zero, then no subnet mask has  been included for this entry."
    ::= { vRtrRipAdvertisedRouteEntry 2 }

vRtrRipAdvertisedRouteIfIndex  OBJECT-TYPE
    SYNTAX      InterfaceIndex
    MAX-ACCESS  not-accessible
    STATUS      current
    DESCRIPTION
        "vRtrRipAdvertisedRouteIfIndex specifies the index of the
         interface on which the route is advertised."
    ::= { vRtrRipAdvertisedRouteEntry 3 }

vRtrRipAdvertisedRouteIfAddr  OBJECT-TYPE
    SYNTAX      IpAddress
    MAX-ACCESS  not-accessible
    STATUS      current
    DESCRIPTION
        "vRtrRipAdvertisedRouteIfAddr specifies the IP address of the 
         subnet to which the route is advertised."
    ::= { vRtrRipAdvertisedRouteEntry 4 }

vRtrRipAdvertisedRouteNextHop  OBJECT-TYPE
    SYNTAX      IpAddress
    MAX-ACCESS  read-only
    STATUS      current
    DESCRIPTION
        "vRtrRipAdvertisedRouteNextHop gives the IP address which is  
         advertised in the Next Hop field of the RIPv2 updates."
    ::= { vRtrRipAdvertisedRouteEntry 5 }

vRtrRipAdvertisedRouteMetric  OBJECT-TYPE
    SYNTAX      Unsigned32 (1..16)
    MAX-ACCESS  read-only
    STATUS      current
    DESCRIPTION
        "vRtrRipAdvertisedRouteMetric gives the metric with which the 
         route is advertised."
    ::= { vRtrRipAdvertisedRouteEntry 6 }

vRtrRipAdvertisedRouteTag  OBJECT-TYPE
    SYNTAX      RouteTag
    MAX-ACCESS  read-only
    STATUS      current
    DESCRIPTION
        "vRtrRipAdvertisedRouteTag gives the value which is advertised in
         the Route Tag field for the route."
    ::= { vRtrRipAdvertisedRouteEntry 7 }

vRtrRipAdvertisedRouteTimerRemaining OBJECT-TYPE
    SYNTAX      Integer32
    MAX-ACCESS  read-only
    STATUS      current
    DESCRIPTION
        "The value of vRtrRipAdvertisedRouteTimerRemaining gives the  
         number of seconds till the flush timer expires. The flush 
         timer is active for only those routes which are no longer  
         valid. Such routes will be advertised with a metric of 16
         till the flush timer expires after which they will be removed
         from the database.
         
         vRtrRipAdvertisedRouteTimerRemaining will have a value of -1
         for valid routes for which the flush timer is not active."
    ::= { vRtrRipAdvertisedRouteEntry 8 }

--
-- Trap Definitions
--
vRtrRipAuthTypeMismatch NOTIFICATION-TYPE
    OBJECTS {
        vRtrRipPeerLastUpdate
    }
    STATUS  current
    DESCRIPTION
        "A vRtrRipAuthTypeMismatch trap is generated when the 
         authentication type field in a received RIPv2 packet 
         conflicts with the authentication type configured for
         this router."
    ::= { vRtrRipNotifications 1 }

vRtrRipAuthFailure NOTIFICATION-TYPE
    OBJECTS {
        vRtrRipPeerLastUpdate
    }
    STATUS  current
    DESCRIPTION
        "A vRtrRipAuthFailure trap is generated when the 
         authentication key in a received RIPv2 packet conflicts 
         with the authentication key configured for this router."
    ::= { vRtrRipNotifications 2 }

vRtrRipInstanceShuttingDown NOTIFICATION-TYPE
    OBJECTS {
        vRtrRipInstanceOperStatus
    }
    STATUS  current
    DESCRIPTION
        "A vRtrRipInstanceShuttingDown trap is generated when the RIP  
         instance shuts down on its own accord when the protocol runs  
         out of resources such as memory. The instance will attempt to
         restart within 30 seconds of shutting down."
    ::= { vRtrRipNotifications 3 }

vRtrRipInstanceRestarted NOTIFICATION-TYPE
    OBJECTS {
        vRtrRipInstanceOperStatus
    }
    STATUS  current
    DESCRIPTION
        "When a RIP protocol instance runs out of resources, the instance 
         will shut down and then attempt to restart within 30 seconds. A 
         vRtrRipInstanceRestarted trap is generated when the RIP instance 
         has restarted."
    ::= { vRtrRipNotifications 4 }

vRtrRipInstanceExpLmtReached  NOTIFICATION-TYPE
    OBJECTS {
        vRtrRipInstanceExportLimit
    }
    STATUS  current
    DESCRIPTION
        "A vRtrRipInstanceExpLmtReached notification is generated when the 
         configured value of exported routes, vRtrRipInstanceExportLimit is 
         reached. Additional routes would not be exported into RIP from the 
         route table."
    ::= { vRtrRipNotifications 5 }

vRtrRipInstanceExpLmtWarning  NOTIFICATION-TYPE
    OBJECTS {
        vRtrRipInstanceExportLimit,
        vRtrRipInstanceExpLmtLogPercent
    }
    STATUS  current
    DESCRIPTION
        "A vRtrRipInstanceExpLmtWarning notification is generated when the 
         number of exported routes is equal to the configured percent, 
         vRtrRipInstanceExpLmtLogPercent of the export limit, 
         vRtrRipInstanceExportLimit. Additional routes will continue to be 
         exported into RIP from the route table till the export limit is 
         reached."
    ::= { vRtrRipNotifications 6 }

vRtrRipInstanceRtsExpLmtDropped  NOTIFICATION-TYPE
    OBJECTS {
        vRtrRipInstanceExportLimit
    }
    STATUS  current
    DESCRIPTION
        "A vRtrRipInstanceRtsExpLmtDropped notification is generated when the 
         number of exported routes drops below the export limit, 
         vRtrRipInstanceExportLimit."
    ::= { vRtrRipNotifications 7 }

--
-- Conformance Information
--
tmnxRipCompliances OBJECT IDENTIFIER ::= { tmnxRipConformance 1 }
tmnxRipGroups      OBJECT IDENTIFIER ::= { tmnxRipConformance 2 }

-- compliance statements
tmnxRipCompliance  MODULE-COMPLIANCE
    STATUS  current
    DESCRIPTION
            "The compliance statement for management of RIP features
             on Alcatel-Lucent SROS series systems."
    MODULE  -- this module
        MANDATORY-GROUPS { 
            tmnxRipGlobalGroup,
            tmnxRipInstanceGroup,
            tmnxRipGroupGroup,
            tmnxRipInterfaceGroup,
            tmnxRipRoutesGroup,
            tmnxRipPeerGroup,
            tmnxRipNotificationGroup,
            tmnxRipV6v1Group,
            tmnxRipV7v0Group,
            tmnxRipNotificationV7v0Group,
            tmnxRipRoutesV9v0R4Group
        }
    ::= { tmnxRipCompliances 1 }

-- units of conformance

tmnxRipGlobalGroup   OBJECT-GROUP
    OBJECTS {   vRtrRipGlobalLearnedRoutes,
                vRtrRipGlobalTimedoutRoutes,
                vRtrRipGlobalCurrentMemory,
                vRtrRipGlobalMaximumMemory
            }
    STATUS        current
    DESCRIPTION
        "The group of objects supporting general management of RIP features 
         on Alcatel-Lucent SROS series systems."
    ::= { tmnxRipGroups 1 }

tmnxRipInstanceGroup     OBJECT-GROUP
    OBJECTS {   vRtrRipInstanceAuthType,
                vRtrRipInstanceAuthKey,
                vRtrRipInstanceCheckZero,
                vRtrRipInstanceMessageSize,
                vRtrRipInstanceMetricIn,
                vRtrRipInstanceMetricOut,
                vRtrRipInstancePreference,
                vRtrRipInstanceReceive,
                vRtrRipInstanceSend,
                vRtrRipInstanceSplitHorizon,
                vRtrRipInstanceTimerFlush,
                vRtrRipInstanceTimerTimeout,
                vRtrRipInstanceTimerUpdate,
                vRtrRipInstanceImportPolicy1,
                vRtrRipInstanceImportPolicy2,
                vRtrRipInstanceImportPolicy3,
                vRtrRipInstanceImportPolicy4,
                vRtrRipInstanceImportPolicy5,
                vRtrRipInstanceExportPolicy1,
                vRtrRipInstanceExportPolicy2,
                vRtrRipInstanceExportPolicy3,
                vRtrRipInstanceExportPolicy4,
                vRtrRipInstanceExportPolicy5,
                vRtrRipInstanceDescription,
                vRtrRipInstanceAdminStatus,
                vRtrRipInstanceOperStatus
            }
    STATUS        current
    DESCRIPTION
        "The group of objects supporting management of RIP instances 
         on Alcatel-Lucent SROS series systems."
    ::= { tmnxRipGroups 2 }

tmnxRipGroupGroup     OBJECT-GROUP
    OBJECTS {   vRtrRipGroupAuthType,
                vRtrRipGroupAuthKey,
                vRtrRipGroupCheckZero,
                vRtrRipGroupMessageSize,
                vRtrRipGroupMetricIn,
                vRtrRipGroupMetricOut,
                vRtrRipGroupPreference,
                vRtrRipGroupReceive,
                vRtrRipGroupSend,
                vRtrRipGroupSplitHorizon,
                vRtrRipGroupTimerFlush,
                vRtrRipGroupTimerTimeout,
                vRtrRipGroupTimerUpdate,
                vRtrRipGroupImportPolicy1,
                vRtrRipGroupImportPolicy2,
                vRtrRipGroupImportPolicy3,
                vRtrRipGroupImportPolicy4,
                vRtrRipGroupImportPolicy5,
                vRtrRipGroupExportPolicy1,
                vRtrRipGroupExportPolicy2,
                vRtrRipGroupExportPolicy3,
                vRtrRipGroupExportPolicy4,
                vRtrRipGroupExportPolicy5,
                vRtrRipGroupDescription,
                vRtrRipGroupInheritance,
                vRtrRipGroupAdminStatus,
                vRtrRipGroupOperStatus,
                vRtrRipGroupRowStatus
            }
    STATUS        current
    DESCRIPTION
        "The group of objects supporting management of RIP Groups 
         on Alcatel-Lucent SROS series systems."
    ::= { tmnxRipGroups 3 }


tmnxRipInterfaceGroup   OBJECT-GROUP
    OBJECTS {   vRtrRipIfGroupName,
                vRtrRipIfAuthType,
                vRtrRipIfAuthKey,
                vRtrRipIfCheckZero,
                vRtrRipIfMessageSize,
                vRtrRipIfMetricIn,
                vRtrRipIfMetricOut,
                vRtrRipIfPreference,
                vRtrRipIfReceive,
                vRtrRipIfSend,
                vRtrRipIfSplitHorizon,
                vRtrRipIfTimerFlush,
                vRtrRipIfTimerTimeout,
                vRtrRipIfTimerUpdate,
                vRtrRipIfImportPolicy1,
                vRtrRipIfImportPolicy2,
                vRtrRipIfImportPolicy3,
                vRtrRipIfImportPolicy4,
                vRtrRipIfImportPolicy5,
                vRtrRipIfExportPolicy1,
                vRtrRipIfExportPolicy2,
                vRtrRipIfExportPolicy3,
                vRtrRipIfExportPolicy4,
                vRtrRipIfExportPolicy5,
                vRtrRipIfDescription,
                vRtrRipIfInheritance,
                vRtrRipIfAdminStatus,
                vRtrRipIfOperStatus,
                vRtrRipIfRowStatus,
                vRtrRipIfStatAllSentUpdates,
                vRtrRipIfStatAllTriggeredUpdates,
                vRtrRipIfStatAllRcvBadPackets,
                vRtrRipIfStatV1RcvUpdates,
                vRtrRipIfStatV1RcvRequests,
                vRtrRipIfStatV1BadUpdates,
                vRtrRipIfStatV1BadRequests,
                vRtrRipIfStatV1BadRoutes,
                vRtrRipIfStatV2RcvUpdates,
                vRtrRipIfStatV2RcvRequests,
                vRtrRipIfStatV2BadUpdates,
                vRtrRipIfStatV2BadRequests,
                vRtrRipIfStatV2BadRoutes,
                vRtrRipIfStatAuthErrors,
                vRtrRipIfStatAllSentUpdates5Min,
                vRtrRipIfStatAllTriggeredUpdates5Min,
                vRtrRipIfStatAllRcvBadPackets5Min,
                vRtrRipIfStatV1RcvUpdates5Min,
                vRtrRipIfStatV1RcvRequests5Min,
                vRtrRipIfStatV1BadUpdates5Min,
                vRtrRipIfStatV1BadRequests5Min,
                vRtrRipIfStatV1BadRoutes5Min,
                vRtrRipIfStatV2RcvUpdates5Min,
                vRtrRipIfStatV2RcvRequests5Min,
                vRtrRipIfStatV2BadUpdates5Min,
                vRtrRipIfStatV2BadRequests5Min,
                vRtrRipIfStatV2BadRoutes5Min,
                vRtrRipIfStatAuthErrors5Min,
                vRtrRipIfStatAllSentUpdates1Min,
                vRtrRipIfStatAllTriggeredUpdates1Min,
                vRtrRipIfStatAllRcvBadPackets1Min,
                vRtrRipIfStatV1RcvUpdates1Min,
                vRtrRipIfStatV1RcvRequests1Min,
                vRtrRipIfStatV1BadUpdates1Min,
                vRtrRipIfStatV1BadRequests1Min,
                vRtrRipIfStatV1BadRoutes1Min,
                vRtrRipIfStatV2RcvUpdates1Min,
                vRtrRipIfStatV2RcvRequests1Min,
                vRtrRipIfStatV2BadUpdates1Min,
                vRtrRipIfStatV2BadRequests1Min,
                vRtrRipIfStatV2BadRoutes1Min,
                vRtrRipIfStatAuthErrors1Min
            }
    STATUS        current
    DESCRIPTION
        "The group of objects supporting management of RIP interfaces 
         on Alcatel-Lucent SROS series systems."
    ::= { tmnxRipGroups 4 }


tmnxRipRoutesGroup   OBJECT-GROUP
    OBJECTS {   vRtrRipRouteNextHop,
                vRtrRipRouteMetric,
                vRtrRipRouteTag,
                vRtrRipRouteStatus,
                vRtrRipRouteTimerRemaining,
                vRtrRipAdvertisedRouteNextHop,
                vRtrRipAdvertisedRouteMetric,
                vRtrRipAdvertisedRouteTag,
                vRtrRipAdvertisedRouteTimerRemaining
            }   
    STATUS        current
    DESCRIPTION
        "The group of objects supporting RIP Routes 
         on Alcatel-Lucent SROS series systems."
    ::= { tmnxRipGroups 5 }

tmnxRipPeerGroup   OBJECT-GROUP
    OBJECTS {   vRtrRipPeerLastUpdate,
                vRtrRipPeerVersion,
                vRtrRipPeerRcvBadPackets,
                vRtrRipPeerRcvBadRoutes
            }
    STATUS        current
    DESCRIPTION
        "The group of objects supporting RIP Peers 
         on Alcatel-Lucent SROS series systems."
    ::= { tmnxRipGroups 6 }

--tmnxRipNotifyObjsGroup   OBJECT-GROUP
--    OBJECTS {   
--             }
--    STATUS        current
--    DESCRIPTION
--        "The group of objects supporting RIP notifications 
--         on Alcatel-Lucent SROS series systems."
--    ::= { tmnxRipGroups 7 }

tmnxRipNotificationGroup NOTIFICATION-GROUP
    NOTIFICATIONS   {   vRtrRipAuthTypeMismatch,
                        vRtrRipAuthFailure,
                        vRtrRipInstanceShuttingDown,
                        vRtrRipInstanceRestarted
                    }
    STATUS        current
    DESCRIPTION
        "The group of notifications supporting the RIP feature
         on Alcatel-Lucent SROS series systems."
    ::= { tmnxRipGroups 8 }

tmnxRipV6v1Group    OBJECT-GROUP
    OBJECTS {
                vRtrRipInstancePropagateMetric
            }
     STATUS     current
     DESCRIPTION
         "The group of objects supporting new functionality 
          on version 6.1 Alcatel-Lucent SROS series systems."
     ::= { tmnxRipGroups 9 }      

tmnxRipV7v0Group    OBJECT-GROUP
    OBJECTS {
                vRtrRipInstanceExportLimit,
                vRtrRipInstanceExpLmtLogPercent,
                vRtrRipInstanceTotalExpRoutes
            }
     STATUS     current
     DESCRIPTION
         "The group of objects supporting new functionality 
          on version 7.0 Alcatel-Lucent SROS series systems."
     ::= { tmnxRipGroups 10 }

tmnxRipNotificationV7v0Group NOTIFICATION-GROUP
    NOTIFICATIONS   {   
                vRtrRipInstanceExpLmtReached,
                vRtrRipInstanceExpLmtWarning,
                vRtrRipInstanceRtsExpLmtDropped
                    }
    STATUS        current
    DESCRIPTION
        "The group of notifications supporting management of RIP on 7.0 release 
         of Alcatel-Lucent SROS series systems."
    ::= { tmnxRipGroups 11 }

tmnxRipRoutesV9v0R4Group   OBJECT-GROUP
    OBJECTS {  
                vRtrRipRouteFC,
                vRtrRipRouteFCPriority                
            }   
    STATUS        current
    DESCRIPTION
        "The group of objects supporting RIP Routes on version 9.0R4 
         Alcatel-Lucent SROS series systems."
    ::= { tmnxRipGroups 12 }

END
