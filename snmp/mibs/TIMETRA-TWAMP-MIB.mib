TIMETRA-TWAMP-MIB DEFINITIONS ::= BEGIN

IMPORTS
        InetAddress, InetAddressPrefixLength,
        InetAddressType                             FROM INET-ADDRESS-MIB

        MODULE-COMPLIANCE, NOTIFICATION-GROUP,
        OBJECT-GROUP                                FROM SNMPv2-CONF

        Counter32, MODULE-IDENTITY,
        NOTIFICATION-TYPE, OBJECT-TYPE, Unsigned32  FROM SNMPv2-SMI

        RowStatus, TEXTUAL-CONVENTION, TimeStamp    FROM SNMPv2-TC

        timetraSRMIBModules, tmnxSRConfs,
        tmnxSRNotifyPrefix, tmnxSRObjs              FROM TIMETRA-GLOBAL-MIB

        TItemDescription, TmnxAdminState,
        TmnxOperState                               FROM TIMETRA-TC-MIB
        ;

timetraTwampMIBModule          MODULE-IDENTITY
        LAST-UPDATED "201102010000Z"
        ORGANIZATION "Alcatel-Lucent"
        CONTACT-INFO
            "Alcatel-Lucent SROS Support
             Web: http://support.alcatel-lucent.com"
        DESCRIPTION
        "This document is the SNMP MIB module to manage and provision the Two
        Way Active Measurement Protocol (TWAMP, RFC5357) components of
        Alcatel-Lucent SROS.

        Copyright (c) 2010-2014 Alcatel-Lucent.  All rights reserved.
        Reproduction of this document is authorized on the condition that
        the foregoing copyright notice is included.

        This SNMP MIB module (Specification) embodies Alcatel-Lucent's
        proprietary intellectual property.  Alcatel-Lucent retains
        all title and ownership in the Specification, including any
        revisions.

        Alcatel-Lucent grants all interested parties a non-exclusive
        license to use and distribute an unmodified copy of this
        Specification in connection with management of Alcatel-Lucent
        products, and without fee, provided this copyright notice and
        license appear on all copies.

        This Specification is supplied 'as is', and Alcatel-Lucent
        makes no warranty, either express or implied, as to the use,
        operation, condition, or performance of the Specification."

        REVISION                 "201102010000Z"
        DESCRIPTION              "Rev 1.0                1 Feb 2011 00:00
                                  Initial release of the TIMETRA-TWAMP-MIB
                                  in SROS release  9.0."
        ::= { timetraSRMIBModules 76 }

-- #############################################################################
--
--  OBJECT IDENTIFIER Statements
--
-- #############################################################################

tmnxTwampObjs                 OBJECT IDENTIFIER ::= {tmnxSRObjs             76}
tmnxTwampNotifyPrefix         OBJECT IDENTIFIER ::= {tmnxSRNotifyPrefix     76}
tmnxTwampConformance          OBJECT IDENTIFIER ::= {tmnxSRConfs            76}

tmnxTwampTableLastChangeObjs  OBJECT IDENTIFIER ::= {tmnxTwampObjs           1}
tmnxTwampConfigObjs           OBJECT IDENTIFIER ::= {tmnxTwampObjs           2}
tmnxTwampStatisticsObjs       OBJECT IDENTIFIER ::= {tmnxTwampObjs           3}
tmnxTwampNotificationObjs     OBJECT IDENTIFIER ::= {tmnxTwampObjs           4}

tmnxTwampNotifications        OBJECT IDENTIFIER ::= {tmnxTwampNotifyPrefix   0}

tmnxTwampComplianceObjs       OBJECT IDENTIFIER ::= {tmnxTwampConformance    1}
tmnxTwampGroupObjs            OBJECT IDENTIFIER ::= {tmnxTwampConformance    2}

tmnxTwampConfigScalarObjs     OBJECT IDENTIFIER ::= {tmnxTwampConfigObjs     1}
tmnxTwampConfigTableObjs      OBJECT IDENTIFIER ::= {tmnxTwampConfigObjs     2}

tmnxTwampStatisticsScalarObjs OBJECT IDENTIFIER ::= {tmnxTwampStatisticsObjs 1}
tmnxTwampStatisticsTableObjs  OBJECT IDENTIFIER ::= {tmnxTwampStatisticsObjs 2}

tmnxTwampV9v0GroupObjs        OBJECT IDENTIFIER ::= {tmnxTwampGroupObjs      1}

-- #############################################################################
--
--  Textual Conventions
--

TmnxTwampSrvConnectionCount      ::= TEXTUAL-CONVENTION
    STATUS      current
    DESCRIPTION
        "A TmnxTwampSrvConnectionCount value counts the concurrent control
         connections supported by a TWAMP server."
    SYNTAX      Unsigned32 (0..64)

TmnxTwampSrvSessionCount         ::= TEXTUAL-CONVENTION
    STATUS      current
    DESCRIPTION
        "A TmnxTwampSrvSessionCount value counts the concurrent test sessions
         supported by a TWAMP server."
    SYNTAX      Unsigned32 (0..128)

-- #############################################################################
--
--  Table Last Changed TimeStamp Scalars
--

tmnxTwampSrvPrefixTblLastChg     OBJECT-TYPE
    SYNTAX      TimeStamp
    MAX-ACCESS  read-only
    STATUS      current
    DESCRIPTION
        "The value of tmnxTwampSrvPrefixTblLastChg indicates the time, since
         system startup, when tmnxTwampSrvPrefixTable last changed."
    ::= { tmnxTwampTableLastChangeObjs 1 }

-- #############################################################################
--
--  Configuration Scalars
--

tmnxTwampSrvAdminState           OBJECT-TYPE
    SYNTAX      TmnxAdminState
    MAX-ACCESS  read-write
    STATUS      current
    DESCRIPTION
        "The value of tmnxTwampSrvAdminState specifies if the TWAMP server is
         administratively 'inService(2)', or 'outOfService(3)'.  'noop(1)' is a
         write-only value which does not change the current setting."
    DEFVAL { outOfService }
    ::= { tmnxTwampConfigScalarObjs 1 }

tmnxTwampSrvInactTimeout         OBJECT-TYPE
    SYNTAX      Unsigned32 (60..3600)
    UNITS       "seconds"
    MAX-ACCESS  read-write
    STATUS      current
    DESCRIPTION
        "The value of tmnxTwampSrvInactTimeout specifies the system-wide
         inactivity timeout for each TWAMP server control connection."
    DEFVAL { 900 }
    ::= { tmnxTwampConfigScalarObjs 2 }

tmnxTwampSrvMaxConnections       OBJECT-TYPE
    SYNTAX      TmnxTwampSrvConnectionCount
    MAX-ACCESS  read-write
    STATUS      current
    DESCRIPTION
        "The value of tmnxTwampSrvMaxConnections specifies the system-wide
         maximum number of concurrent TWAMP server control connections."
    DEFVAL { 32 }
    ::= { tmnxTwampConfigScalarObjs 3 }

tmnxTwampSrvMaxSessions          OBJECT-TYPE
    SYNTAX      TmnxTwampSrvSessionCount
    MAX-ACCESS  read-write
    STATUS      current
    DESCRIPTION
        "The value of tmnxTwampSrvMaxSessions specifies the system-wide
         maximum number of concurrent TWAMP server test sesssions."
    DEFVAL { 32 }
    ::= { tmnxTwampConfigScalarObjs 4 }

-- #############################################################################
--
--  Configuration Tables
--

tmnxTwampSrvPrefixTable          OBJECT-TYPE
    SYNTAX      SEQUENCE OF TmnxTwampSrvPrefixEntry
    MAX-ACCESS  not-accessible
    STATUS      current
    DESCRIPTION
        "tmnxTwampSrvPrefixTable contains per-prefix TWAMP server configuration
         information."
    ::= { tmnxTwampConfigTableObjs 1 }

tmnxTwampSrvPrefixEntry          OBJECT-TYPE
    SYNTAX      TmnxTwampSrvPrefixEntry
    MAX-ACCESS  not-accessible
    STATUS      current
    DESCRIPTION
        "tmnxTwampSrvPrefixEntry contains the TWAMP server configuration
         information for the IP prefix specified by the index values.

         Rows in this table are created and destroyed using the
         tmnxTwampSrvPrefixRowStatus object."
    INDEX { tmnxTwampSrvPrefixAddrType,
            tmnxTwampSrvPrefixAddr,
            tmnxTwampSrvPrefixLen
    }
    ::= { tmnxTwampSrvPrefixTable 1 }

TmnxTwampSrvPrefixEntry          ::= SEQUENCE {
    tmnxTwampSrvPrefixAddrType       InetAddressType,
    tmnxTwampSrvPrefixAddr           InetAddress,
    tmnxTwampSrvPrefixLen            InetAddressPrefixLength,
    tmnxTwampSrvPrefixRowStatus      RowStatus,
    tmnxTwampSrvPrefixLastChg        TimeStamp,
    tmnxTwampSrvPrefixDescription    TItemDescription,
    tmnxTwampSrvPrefixMaxConnections TmnxTwampSrvConnectionCount,
    tmnxTwampSrvPrefixMaxSessions    TmnxTwampSrvSessionCount
}

tmnxTwampSrvPrefixAddrType       OBJECT-TYPE
    SYNTAX      InetAddressType
    MAX-ACCESS  not-accessible
    STATUS      current
    DESCRIPTION
        "The value of tmnxTwampSrvPrefixAddrType specifies the type of
         tmnxTwampSrvPrefixAddr.  This is the first index for
         tmnxTwampSrvPrefixTable."
    ::= { tmnxTwampSrvPrefixEntry 1 }

tmnxTwampSrvPrefixAddr           OBJECT-TYPE
    SYNTAX      InetAddress (SIZE (4|16))
    MAX-ACCESS  not-accessible
    STATUS      current
    DESCRIPTION
        "The value of tmnxTwampSrvPrefixAddr specifies, in conjuction with
         tmnxTwampSrvPrefixAddrType and tmnxTwampSrvPrefixLen, a prefix to be
         matched against a TWAMP client address.  This is the second index for
         tmnxTwampSrvPrefixTable."
    ::= { tmnxTwampSrvPrefixEntry 2 }

tmnxTwampSrvPrefixLen            OBJECT-TYPE
    SYNTAX      InetAddressPrefixLength (0..128)
    UNITS       "bits"
    MAX-ACCESS  not-accessible
    STATUS      current
    DESCRIPTION
        "The value of tmnxTwampSrvPrefixLen specifies the number of bits to
         match when comparing a TWAMP client address in an incoming message to
         tmnxTwampSrvPrefixAddr.  This is the third index for
         tmnxTwampSrvPrefixTable.

         Best-fit is used when matching a TWAMP client's IP address against the
         set of configured prefixes.  For example, suppose the first row of this
         table has the prefix 138.120.0.0/16, and the second row has the prefix
         138.120.214.0/24.  The TWAMP client address 138.120.214.52 matches the
         second row."
    ::= { tmnxTwampSrvPrefixEntry 3 }

tmnxTwampSrvPrefixRowStatus      OBJECT-TYPE
    SYNTAX      RowStatus
    MAX-ACCESS  read-create
    STATUS      current
    DESCRIPTION
        "The value of tmnxTwampSrvPrefixRowStatus specifies the status of the
         row for the TWAMP prefix identified by the index values.  This object
         controls the creation and deletion of rows in the
         tmnxTwampSrvPrefixTable."
    ::= { tmnxTwampSrvPrefixEntry 4 }

tmnxTwampSrvPrefixLastChg        OBJECT-TYPE
    SYNTAX      TimeStamp
    MAX-ACCESS  read-only
    STATUS      current
    DESCRIPTION
        "The value of tmnxTwampSrvPrefixLastChg indicates the time, since system
         startup, that this row was created or modified."
    ::= { tmnxTwampSrvPrefixEntry 5 }

tmnxTwampSrvPrefixDescription    OBJECT-TYPE
    SYNTAX      TItemDescription
    MAX-ACCESS  read-create
    STATUS      current
    DESCRIPTION
        "The value of tmnxTwampSrvPrefixDescription specifies the description
         for the TWAMP prefix identified by the index values."
    DEFVAL      { ''H }   -- the empty string
    ::= { tmnxTwampSrvPrefixEntry 6 }

tmnxTwampSrvPrefixMaxConnections OBJECT-TYPE
    SYNTAX      TmnxTwampSrvConnectionCount
    MAX-ACCESS  read-create
    STATUS      current
    DESCRIPTION
        "The value of tmnxTwampSrvPrefixMaxConnections specifies the maximum
         number of concurrent TWAMP control connections allowed for the TWAMP
         prefix identified by the index values.

         In addition, the number of concurrent TWAMP control connections for
         this prefix is limited by the system maximum 
         (tmnxTwampSrvMaxConnections)."
    DEFVAL { 32 }
    ::= { tmnxTwampSrvPrefixEntry 7 }

tmnxTwampSrvPrefixMaxSessions    OBJECT-TYPE
    SYNTAX      TmnxTwampSrvSessionCount
    MAX-ACCESS  read-create
    STATUS      current
    DESCRIPTION
        "The value of tmnxTwampSrvPrefixMaxSessions specifies the maximum
         number of concurrent TWAMP test sessions allowed for the TWAMP prefix
         identified by the index values.

         In addition, the number of concurrent TWAMP test sessions for
         this prefix is limited by the system maximum 
         (tmnxTwampSrvMaxSessions)."
    DEFVAL { 32 }
    ::= { tmnxTwampSrvPrefixEntry 8 }


-- #############################################################################
--
--  Statistics Scalars
--

tmnxTwampSrvOperState            OBJECT-TYPE
    SYNTAX      TmnxOperState
    MAX-ACCESS  read-only
    STATUS      current
    DESCRIPTION
        "The value of tmnxTwampSrvOperState indicates if the TWAMP server is
         operationally 'inService(2)', or 'outOfService(3)'."
    ::= { tmnxTwampStatisticsScalarObjs 1 }

tmnxTwampSrvUpTime               OBJECT-TYPE
    SYNTAX      Counter32
    UNITS       "seconds"
    MAX-ACCESS  read-only
    STATUS      current
    DESCRIPTION
        "The value of tmnxTwampSrvUpTime indicates the time elapsed, in seconds,
         since the most recent transition of tmnxTwampSrvOperState to
         'inService(2)'.  If tmnxTwampSrvOperState is not 'inService(2)', zero
         is returned."
    ::= { tmnxTwampStatisticsScalarObjs 2 }

tmnxTwampSrvConnectionCount      OBJECT-TYPE
    SYNTAX      TmnxTwampSrvConnectionCount
    MAX-ACCESS  read-only
    STATUS      current
    DESCRIPTION
        "The value of tmnxTwampSrvConnectionCount indicates the number of
         control connections currently managed by the TWAMP server."
    ::= { tmnxTwampStatisticsScalarObjs 3 }

tmnxTwampSrvConnectionsRejected  OBJECT-TYPE
    SYNTAX      Counter32
    MAX-ACCESS  read-only
    STATUS      current
    DESCRIPTION
        "The value of tmnxTwampSrvConnectionsRejected indicates the total number
         of control connection requests which have been rejected by the TWAMP
         server.  Example reject reasons:  the server's limit on the number of
         active connections has been reached; the client's IP address does not
         match any of the prefixes configured on the TWAMP server."
    ::= { tmnxTwampStatisticsScalarObjs 4 }

tmnxTwampSrvSessionCount         OBJECT-TYPE
    SYNTAX      TmnxTwampSrvSessionCount
    MAX-ACCESS  read-only
    STATUS      current
    DESCRIPTION
        "The value of tmnxTwampSrvSessionCount indicates the number of currently
         in-progress TWAMP test sesssions."
    ::= { tmnxTwampStatisticsScalarObjs 5 }

tmnxTwampSrvTestSessCompleted    OBJECT-TYPE
    SYNTAX      Counter32
    MAX-ACCESS  read-only
    STATUS      current
    DESCRIPTION
        "The value of tmnxTwampSrvTestSessCompleted indicates the total number
         of test sessions completed by the TWAMP server."
    ::= { tmnxTwampStatisticsScalarObjs 6 }

tmnxTwampSrvTestSessRejected     OBJECT-TYPE
    SYNTAX      Counter32
    MAX-ACCESS  read-only
    STATUS      current
    DESCRIPTION
        "The value of tmnxTwampSrvTestSessRejected indicates the total number of
         test sessions rejected by the TWAMP server."
    ::= { tmnxTwampStatisticsScalarObjs 7 }

tmnxTwampSrvTestSessAborted      OBJECT-TYPE
    SYNTAX      Counter32
    MAX-ACCESS  read-only
    STATUS      current
    DESCRIPTION
        "The value of tmnxTwampSrvTestSessAborted indicates the total number of
         test sessions aborted by the TWAMP server."
    ::= { tmnxTwampStatisticsScalarObjs 8 }

tmnxTwampSrvTestPacketsRx        OBJECT-TYPE
    SYNTAX      Counter32
    MAX-ACCESS  read-only
    STATUS      current
    DESCRIPTION
        "The value of tmnxTwampSrvTestPacketsRx indicates the total number of
         TWAMP test packets received by the TWAMP server."
    ::= { tmnxTwampStatisticsScalarObjs 9 }

tmnxTwampSrvTestPacketsTx        OBJECT-TYPE
    SYNTAX      Counter32
    MAX-ACCESS  read-only
    STATUS      current
    DESCRIPTION
        "The value of tmnxTwampSrvTestPacketsTx indicates the total number of
         TWAMP test packets sent by the TWAMP server."
    ::= { tmnxTwampStatisticsScalarObjs 10 }

-- #############################################################################
--
--  Statistics Tables
--

tmnxTwampSrvPrefixStatsTable     OBJECT-TYPE
    SYNTAX      SEQUENCE OF TmnxTwampSrvPrefixStatsEntry
    MAX-ACCESS  not-accessible
    STATUS      current
    DESCRIPTION
        "tmnxTwampSrvPrefixStatsTable contains per-prefix TWAMP server
         statistics."
    ::= { tmnxTwampStatisticsTableObjs 1 }

tmnxTwampSrvPrefixStatsEntry     OBJECT-TYPE
    SYNTAX      TmnxTwampSrvPrefixStatsEntry
    MAX-ACCESS  not-accessible
    STATUS      current
    DESCRIPTION
        "tmnxTwampSrvPrefixStatsEntry contains the TWAMP server statistics for
         the IP prefix specified by the index values."
    AUGMENTS { tmnxTwampSrvPrefixEntry }
    ::= { tmnxTwampSrvPrefixStatsTable 1 }

TmnxTwampSrvPrefixStatsEntry     ::= SEQUENCE {
    tmnxTwampSrvPfxConnCount         TmnxTwampSrvConnectionCount,
    tmnxTwampSrvPfxConnsRejected     Counter32,
    tmnxTwampSrvPfxSessionCount      TmnxTwampSrvSessionCount,
    tmnxTwampSrvPfxTestSessCompleted Counter32,
    tmnxTwampSrvPfxTestSessRejected  Counter32,
    tmnxTwampSrvPfxTestSessAbort     Counter32,
    tmnxTwampSrvPfxTestPacketsRx     Counter32,
    tmnxTwampSrvPfxTestPacketsTx     Counter32
}

tmnxTwampSrvPfxConnCount         OBJECT-TYPE
    SYNTAX      TmnxTwampSrvConnectionCount
    MAX-ACCESS  read-only
    STATUS      current
    DESCRIPTION
        "The value of tmnxTwampSrvPfxConnCount indicates, for the prefix
         specified by the index values, the number of control connections
         currently managed by the TWAMP server."
    ::= { tmnxTwampSrvPrefixStatsEntry 1 }

tmnxTwampSrvPfxConnsRejected     OBJECT-TYPE
    SYNTAX      Counter32
    MAX-ACCESS  read-only
    STATUS      current
    DESCRIPTION
        "The value of tmnxTwampSrvPfxConnsRejected indicates, for the prefix
         specified by the index values, the number of control connection
         requests which have been rejected by the TWAMP server.  An example
         reject reason:  the prefix's limit on the number of active connections
         has been reached."
    ::= { tmnxTwampSrvPrefixStatsEntry 2 }

tmnxTwampSrvPfxSessionCount      OBJECT-TYPE
    SYNTAX      TmnxTwampSrvSessionCount
    MAX-ACCESS  read-only
    STATUS      current
    DESCRIPTION
        "The value of tmnxTwampSrvPfxSessionCount indicates, for the prefix
         specified by the index values, the number of currently in-progress
         TWAMP test sesssions."
    ::= { tmnxTwampSrvPrefixStatsEntry 3 }

tmnxTwampSrvPfxTestSessCompleted OBJECT-TYPE
    SYNTAX      Counter32
    MAX-ACCESS  read-only
    STATUS      current
    DESCRIPTION
        "The value of tmnxTwampSrvPfxTestSessCompleted indicates, for the prefix
         specified by the index values, the number of test sessions completed by
         the TWAMP server."
    ::= { tmnxTwampSrvPrefixStatsEntry 4 }

tmnxTwampSrvPfxTestSessRejected  OBJECT-TYPE
    SYNTAX      Counter32
    MAX-ACCESS  read-only
    STATUS      current
    DESCRIPTION
        "The value of tmnxTwampSrvPfxTestSessRejected indicates, for the prefix
         specified by the index values, the number of test sessions rejected by
         the TWAMP server."
    ::= { tmnxTwampSrvPrefixStatsEntry 5 }

tmnxTwampSrvPfxTestSessAbort     OBJECT-TYPE
    SYNTAX      Counter32
    MAX-ACCESS  read-only
    STATUS      current
    DESCRIPTION
        "The value of tmnxTwampSrvPfxTestSessAbort indicates, for the prefix
         specified by the index values, the number of test sessions aborted by
         the TWAMP server."
    ::= { tmnxTwampSrvPrefixStatsEntry 6 }

tmnxTwampSrvPfxTestPacketsRx     OBJECT-TYPE
    SYNTAX      Counter32
    MAX-ACCESS  read-only
    STATUS      current
    DESCRIPTION
        "The value of tmnxTwampSrvPfxTestPacketsRx indicates, for the prefix
         specified by the index values, the number of TWAMP test packets
         received by the TWAMP server."
    ::= { tmnxTwampSrvPrefixStatsEntry 7 }

tmnxTwampSrvPfxTestPacketsTx     OBJECT-TYPE
    SYNTAX      Counter32
    MAX-ACCESS  read-only
    STATUS      current
    DESCRIPTION
        "The value of tmnxTwampSrvPfxTestPacketsTx indicates, for the prefix
         specified by the index values, the number of TWAMP test packets sent by
         the TWAMP server."
    ::= { tmnxTwampSrvPrefixStatsEntry 8 }


tmnxTwampSrvConnStatsTable       OBJECT-TYPE
    SYNTAX      SEQUENCE OF TmnxTwampSrvConnStatsEntry
    MAX-ACCESS  not-accessible
    STATUS      current
    DESCRIPTION
        "tmnxTwampSrvConnStatsTable contains the statistics for each active
         control connection managed by the TWAMP server."
    ::= { tmnxTwampStatisticsTableObjs 2 }

tmnxTwampSrvConnStatsEntry       OBJECT-TYPE
    SYNTAX      TmnxTwampSrvConnStatsEntry
    MAX-ACCESS  not-accessible
    STATUS      current
    DESCRIPTION
        "tmnxTwampSrvConnStatsEntry contains the statistics for the TWAMP
         control connection specified by the index values.  A row is created
         by the system when a TWAMP control connection is established."
    INDEX { tmnxTwampSrvPrefixAddrType,
            tmnxTwampSrvPrefixAddr,
            tmnxTwampSrvPrefixLen,
            tmnxTwampSrvConnClientAddrType,
            tmnxTwampSrvConnClientAddr,
            tmnxTwampSrvConnSeqNum }

    ::= { tmnxTwampSrvConnStatsTable 1 }

TmnxTwampSrvConnStatsEntry       ::= SEQUENCE {
    tmnxTwampSrvConnClientAddrType   InetAddressType,
    tmnxTwampSrvConnClientAddr       InetAddress,
    tmnxTwampSrvConnSeqNum           Unsigned32,
    tmnxTwampSrvConnState            INTEGER,
    tmnxTwampSrvConnIdleTime         Unsigned32,
    tmnxTwampSrvConnSessionCount     TmnxTwampSrvSessionCount,
    tmnxTwampSrvConnTestSessComplete Counter32,
    tmnxTwampSrvConnTestSessRejected Counter32,
    tmnxTwampSrvConnTestPacketsRx    Counter32,
    tmnxTwampSrvConnTestPacketsTx    Counter32
}

tmnxTwampSrvConnClientAddrType   OBJECT-TYPE
    SYNTAX      InetAddressType
    MAX-ACCESS  not-accessible
    STATUS      current
    DESCRIPTION
        "The value of tmnxTwampSrvConnClientAddrType specifies the type of
         tmnxTwampSrvConnClientAddr.  This is the fourth index for
         tmnxTwampSrvConnStatsTable."
    ::= { tmnxTwampSrvConnStatsEntry 1 }

tmnxTwampSrvConnClientAddr       OBJECT-TYPE
    SYNTAX      InetAddress (SIZE (4|16))
    MAX-ACCESS  not-accessible
    STATUS      current
    DESCRIPTION
        "The value of tmnxTwampSrvConnClientAddr specifies the TWAMP client's
         address.  This is the fifth index for tmnxTwampSrvConnStatsTable."
    ::= { tmnxTwampSrvConnStatsEntry 2 }

tmnxTwampSrvConnSeqNum           OBJECT-TYPE
    SYNTAX      Unsigned32 (1..4294967295)
    MAX-ACCESS  not-accessible
    STATUS      current
    DESCRIPTION
        "The value of tmnxTwampSrvConnSeqNum specifies this control connection's
         sequence number.  This is the sixth index for
         tmnxTwampSrvConnStatsTable - it allows n>1 rows (i.e. n>1 connections)
         for one client."
    ::= { tmnxTwampSrvConnStatsEntry 3 }

tmnxTwampSrvConnState            OBJECT-TYPE
    SYNTAX      INTEGER {
                    settingUp (1),
                    ready (2),
                    running (3)
                }
    MAX-ACCESS  read-only
    STATUS      current
    DESCRIPTION
        "The value of tmnxTwampSrvConnState indicates the operational state of a
         control connection managed by the TWAMP server.

         Code points:
            settingUp(1) - the connection is being established
            ready(2)     - the connection is ready to accept test sessions
            running(3)   - the connection is running a test."
    ::= { tmnxTwampSrvConnStatsEntry 4 }

tmnxTwampSrvConnIdleTime         OBJECT-TYPE
    SYNTAX      Unsigned32
    UNITS       "seconds"
    MAX-ACCESS  read-only
    STATUS      current
    DESCRIPTION
        "The value of tmnxTwampSrvConnIdleTime specifies the elapsed time, in
         seconds, since a TWAMP message was received on this control connection.
         When this value exceeds tmnxTwampSrvInactTimeout, the connection will
         be torn down."
    ::= { tmnxTwampSrvConnStatsEntry 5 }

tmnxTwampSrvConnSessionCount     OBJECT-TYPE
    SYNTAX      TmnxTwampSrvSessionCount
    MAX-ACCESS  read-only
    STATUS      current
    DESCRIPTION
        "The value of tmnxTwampSrvConnSessionCount indicates, for the connection
         specified by the index values, the number of currently in-progress
         TWAMP test sesssions."
    ::= { tmnxTwampSrvConnStatsEntry 6 }

tmnxTwampSrvConnTestSessComplete OBJECT-TYPE
    SYNTAX      Counter32
    MAX-ACCESS  read-only
    STATUS      current
    DESCRIPTION
        "The value of tmnxTwampSrvConnTestSessComplete indicates, for the
         connection specified by the index values, the number of test sessions
         completed by the TWAMP server."
    ::= { tmnxTwampSrvConnStatsEntry 7 }

tmnxTwampSrvConnTestSessRejected OBJECT-TYPE
    SYNTAX      Counter32
    MAX-ACCESS  read-only
    STATUS      current
    DESCRIPTION
        "The value of tmnxTwampSrvConnTestSessRejected indicates, for the
         connection specified by the index values, the number of test sessions
         rejected by the TWAMP server."
    ::= { tmnxTwampSrvConnStatsEntry 8 }

tmnxTwampSrvConnTestPacketsRx    OBJECT-TYPE
    SYNTAX      Counter32
    MAX-ACCESS  read-only
    STATUS      current
    DESCRIPTION
        "The value of tmnxTwampSrvConnTestPacketsRx indicates, for the
         connection specified by the index values, the number of TWAMP test
         packets received by the TWAMP server."
    ::= { tmnxTwampSrvConnStatsEntry 9 }

tmnxTwampSrvConnTestPacketsTx    OBJECT-TYPE
    SYNTAX      Counter32
    MAX-ACCESS  read-only
    STATUS      current
    DESCRIPTION
        "The value of tmnxTwampSrvConnTestPacketsTx indicates, for the
         connection specified by the index values, the number of TWAMP test
         packets sent by the TWAMP server."
    ::= { tmnxTwampSrvConnStatsEntry 10 }

-- #############################################################################
--
-- accessible-for-notify Objects
--

tmnxTwampSrvNotifClientAddrType  OBJECT-TYPE
    SYNTAX      InetAddressType
    MAX-ACCESS  accessible-for-notify
    STATUS      current
    DESCRIPTION
        "The value of tmnxTwampSrvNotifClientAddrType indicates the address type
         of tmnxTwampSrvNotifClientAddr."
    ::= { tmnxTwampNotificationObjs 1 }

tmnxTwampSrvNotifClientAddr      OBJECT-TYPE
    SYNTAX      InetAddress (SIZE (4|16))
    MAX-ACCESS  accessible-for-notify
    STATUS      current
    DESCRIPTION
        "The value of tmnxTwampSrvNotifClientAddr indicates, along with
         tmnxTwampSrvNotifClientAddrType, the address of a TWAMP client which
         could not be connected to the TWAMP server."
    ::= { tmnxTwampNotificationObjs 2 }

-- #############################################################################
--
-- Notifications
--

tmnxTwampSrvInactivityTimeout    NOTIFICATION-TYPE
    OBJECTS {
        tmnxTwampSrvConnIdleTime
    }
    STATUS  current
    DESCRIPTION
        "[CAUSE] The tmnxTwampSrvInactivityTimeout notification is generated
         when a TWAMP control connection was disconnected by the TWAMP server
         because the connection was inactive for a period exceeding the server's
         inactivity timeout (tmnxTwampSrvInactTimeout).

         [EFFECT] The TWAMP client cannot request test runs on the disconnected
         connection.

         [RECOVERY] Check the IP connectivity between this node and the TWAMP
         client."
    ::= { tmnxTwampNotifications 1 }

tmnxTwampSrvMaxConnsExceeded     NOTIFICATION-TYPE
    OBJECTS {
        tmnxTwampSrvConnectionCount,
        tmnxTwampSrvNotifClientAddrType,
        tmnxTwampSrvNotifClientAddr
    }
    STATUS  current
    DESCRIPTION
        "[CAUSE] The tmnxTwampSrvMaxConnsExceeded notification is generated when
         a TWAMP control connection could not be established by the TWAMP server
         because the system-level maximum number of concurrent TWAMP control
         connections (tmnxTwampSrvMaxConnections) has been reached.

         [EFFECT] The TWAMP client cannot request test runs on the rejected
         connection.

         [RECOVERY] Configure the system-level maximum number of concurrent
         TWAMP control connections to a larger value, or disconnect any TWAMP
         control connection."
    ::= { tmnxTwampNotifications 2 }

tmnxTwampSrvPfxMaxConnsExceeded  NOTIFICATION-TYPE
    OBJECTS {
        tmnxTwampSrvPfxConnCount,
        tmnxTwampSrvNotifClientAddrType,
        tmnxTwampSrvNotifClientAddr
    }
    STATUS  current
    DESCRIPTION
        "[CAUSE] The tmnxTwampSrvPfxMaxConnsExceeded notification is generated
         when a TWAMP control connection could not be established by the TWAMP
         server because the maximum number of concurrent TWAMP control
         connections configured against the TWAMP client's prefix
         (tmnxTwampSrvPrefixMaxConnections) has been reached.

         [EFFECT] The TWAMP client cannot request test runs on the rejected
         connection.

         [RECOVERY] Configure the prefix's maximum number of concurrent TWAMP
         control connections to a larger value, or disconnect a TWAMP control
         connection which uses the prefix."
    ::= { tmnxTwampNotifications 3 }

tmnxTwampSrvMaxSessExceeded      NOTIFICATION-TYPE
    OBJECTS {
        tmnxTwampSrvSessionCount,
        tmnxTwampSrvNotifClientAddrType,
        tmnxTwampSrvNotifClientAddr
    }
    STATUS  current
    DESCRIPTION
        "[CAUSE] The tmnxTwampSrvMaxSessExceeded notification is generated when
         a TWAMP session could not be established by the TWAMP server because
         the system-level maximum number of concurrent TWAMP sessions
         (tmnxTwampSrvMaxSessions) has been reached.

         [EFFECT] The TWAMP client cannot request test runs on the rejected
         session.

         [RECOVERY] Configure the system-level maximum number of concurrent
         TWAMP sessions to a larger value, or disconnect any TWAMP session."
    ::= { tmnxTwampNotifications 4 }

tmnxTwampSrvPfxMaxSessExceeded   NOTIFICATION-TYPE
    OBJECTS {
        tmnxTwampSrvPfxSessionCount,
        tmnxTwampSrvNotifClientAddrType,
        tmnxTwampSrvNotifClientAddr
    }
    STATUS  current
    DESCRIPTION
        "[CAUSE] The tmnxTwampSrvPfxMaxSessExceeded notification is generated
         when a TWAMP session could not be established by the TWAMP server
         because the maximum number of concurrent TWAMP sessions configured
         against the TWAMP client's prefix (tmnxTwampSrvPrefixMaxSessions) has
         been reached.

         [EFFECT] The TWAMP client cannot request test runs on the rejected
         session.

         [RECOVERY] Configure the prefix's maximum number of concurrent TWAMP
         sessions to a larger value, or disconnect a TWAMP session which uses
         the prefix."
    ::= { tmnxTwampNotifications 5 }

-- #############################################################################
--
--  Compliance Statements
--
tmnxTwampCompliance              MODULE-COMPLIANCE
    STATUS      current
    DESCRIPTION
        "The compliance statement for the management of TWAMP for Release 9.0 on
         SROS series systems."
    MODULE -- this module
        MANDATORY-GROUPS {
            tmnxTwampSrvV9v0Group,
            tmnxTwampSrvNotifyV9v0Group,
            tmnxTwampSrvNotifyObjsV9v0Group
        }
    ::= { tmnxTwampComplianceObjs 1 }

-- #############################################################################
--
--  Group Statements
--

tmnxTwampSrvV9v0Group            OBJECT-GROUP
    OBJECTS {
        tmnxTwampSrvAdminState,
        tmnxTwampSrvInactTimeout,
        tmnxTwampSrvMaxConnections,
        tmnxTwampSrvMaxSessions,
        tmnxTwampSrvPrefixTblLastChg,
        tmnxTwampSrvPrefixRowStatus,
        tmnxTwampSrvPrefixLastChg,
        tmnxTwampSrvPrefixDescription,
        tmnxTwampSrvPrefixMaxConnections,
        tmnxTwampSrvPrefixMaxSessions,
        tmnxTwampSrvOperState,
        tmnxTwampSrvUpTime,
        tmnxTwampSrvConnectionCount,
        tmnxTwampSrvConnectionsRejected,
        tmnxTwampSrvSessionCount,
        tmnxTwampSrvTestSessCompleted,
        tmnxTwampSrvTestSessRejected,
        tmnxTwampSrvTestSessAborted,
        tmnxTwampSrvTestPacketsRx,
        tmnxTwampSrvTestPacketsTx,
        tmnxTwampSrvPfxConnCount,
        tmnxTwampSrvPfxConnsRejected,
        tmnxTwampSrvPfxSessionCount,
        tmnxTwampSrvPfxTestSessCompleted,
        tmnxTwampSrvPfxTestSessRejected,
        tmnxTwampSrvPfxTestSessAbort,
        tmnxTwampSrvPfxTestPacketsRx,
        tmnxTwampSrvPfxTestPacketsTx,
        tmnxTwampSrvConnState,
        tmnxTwampSrvConnIdleTime,
        tmnxTwampSrvConnSessionCount,
        tmnxTwampSrvConnTestSessComplete,
        tmnxTwampSrvConnTestSessRejected,
        tmnxTwampSrvConnTestPacketsRx,
        tmnxTwampSrvConnTestPacketsTx
    }
    STATUS      current
    DESCRIPTION
        "The group of objects supporting management of the TWAMP server
         on Alcatel-Lucent SROS Release 9.0."
    ::= { tmnxTwampV9v0GroupObjs 1 }

tmnxTwampSrvNotifyV9v0Group      NOTIFICATION-GROUP
    NOTIFICATIONS {
        tmnxTwampSrvInactivityTimeout,
        tmnxTwampSrvMaxConnsExceeded,
        tmnxTwampSrvPfxMaxConnsExceeded,
        tmnxTwampSrvMaxSessExceeded,
        tmnxTwampSrvPfxMaxSessExceeded
    }
    STATUS      current
    DESCRIPTION
        "The group of notifications supporting management of the TWAMP server on
         Alcatel-Lucent SROS Release 9.0."
    ::= { tmnxTwampV9v0GroupObjs 2 }

tmnxTwampSrvNotifyObjsV9v0Group  OBJECT-GROUP
    OBJECTS {
        tmnxTwampSrvNotifClientAddrType,
        tmnxTwampSrvNotifClientAddr
    }
    STATUS      current
    DESCRIPTION
        "The group of accessible-for-notify objects supporting management of the
         TWAMP server on Alcatel-Lucent SROS Release 9.0."
    ::= { tmnxTwampV9v0GroupObjs 3 }

END
